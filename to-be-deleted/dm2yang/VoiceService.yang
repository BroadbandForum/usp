module VoiceService {
  namespace "urn:tbd";
  prefix TBD;
  
  import ietf-yang-types {
    prefix yang;
  }
  
  import tr-106-types {
    prefix types;
  }
  
  organization
    "TBD";
  
  contact
    "TBD";
  
  description
    "";
  
  revision 1970-01-01 {
    description
      "TBD";
    reference
      "TBD";
  }

  list VoiceService {
    key "Alias";
    description
      "The top-level object for CPE with voice capabilities.";

    container Capabilities {
      config false;
      description
        "The overall capabilities of the VoIP CPE.";
      leaf MaxLineCount {
        type int32 {
          range "-1..max";
        }
        description
          "Maximum total number of {{object|.CallControl.Line}}
           objects supported.
        
           A value of -1 indicates no specific limit on the
           number of lines.";
      }
      leaf MaxExtensionCount {
        type int32 {
          range "-1..max";
        }
        description
          "Maximum total number of {{object|.CallControl.Extension}}
           objects supported.
        
           A value of -1 indicates no specific limit on the
           number of extensions.";
      }
      leaf MaxCallLogCount {
        type int32 {
          range "-1..max";
        }
        description
          "Maximum total number of {{object|.CallLog}} objects
           supported.
        
           A value of -1 indicates no specific limit on the
           number of call logs.";
      }
      leaf MaxSessionsPerLine {
        type int32 {
          range "-1..max";
        }
        description
          "Maximum number of voice sessions supported for any given
           {{object|.CallControl.Line}} object.  A value greater
           than one indicates support for CPE-provided conference
           calling.
        
           A value of -1 indicates no specific limit on the
           number of voice sessions per line.";
      }
      leaf MaxSessionsPerExtension {
        type int32 {
          range "-1..max";
        }
        description
          "Maximum number of voice sessions supported for any given
           {{object|.CallControl.Extension}} object.  A value
           greater than one indicates support for CPE-provided
           conference calling.
        
           A value of -1 indicates no specific limit on the
           number of voice sessions per extension.";
      }
      leaf MaxSessionCount {
        type int32 {
          range "-1..max";
        }
        description
          "Maximum total number of voice sessions supported across
           all {{object|.CallControl.Line}} objects.  (This might
           differ from {{param|MaxLineCount}} if each line can
           support more than one session for CPE-provided
           conference calling.  This value MAY be less than the
           product of {{param|MaxLineCount}} and
           {{param|MaxSessionsPerLine}}.)
        
           A value of -1 indicates no specific limit on the
           number of voice sessions.";
      }
      leaf NetworkConnectionModes {
        type string {
          pattern "SIP(/\d+\.\d+)?";
          pattern "MGCP(/\d+\.\d+)?";
          pattern "MGCP-NCS(/\d+\.\d+)?";
          pattern "H\.248(/\d+\.\d+)?";
          pattern "H\.323(/\d+\.\d+)?";
          pattern "DSS1";
          pattern "FXO";
          pattern "X_.+";
        }
        description
          "{{list}} Each item is a supported network connection
           mode.  {{pattern}}
        
           Most entries MAY be appended with a version indicator
           in the form \"/X.Y\".  For example:
        
           \"SIP/2.0\"
        
           The list MAY include vendor-specific modes, which MUST
           be in the format defined in {{bibref|TR-106}}.  For
           example:
        
           \"X_EXAMPLE-COM_MyMode\"";
      }
      leaf UserConnectionModes {
        type string {
          pattern "SIP(/\d+\.\d+)?";
          pattern "DSS1";
          pattern "FXS";
          pattern "DECT(/\d+\.\d+)?";
          pattern "Button";
          pattern "Virtual";
          pattern "X_.+";
        }
        description
          "{{list}} Each item is a supported user connection mode.
           {{pattern}}
        
           Most entries MAY be appended with a version indicator
           in the form \"/X.Y\".  For example:
        
           \"SIP/2.0\"
        
           The list MAY include vendor-specific modes, which MUST
           be in the format defined in {{bibref|TR-106}}.  For
           example:
        
           \"X_EXAMPLE-COM_MyMode\"";
      }
      leaf ToneFileFormats {
        type enumeration {
          enum "G.711MuLaw";
          enum "G.711ALaw";
          enum "G.729";
          enum "MP3";
          enum "WAV";
          enum "AMR";
        }
        description
          "{{list}} Each item is a supported tone file format.  The
           specified file formats are raw codec data files, using
           one of the codecs listed below.  {{enum}}
        
           The list MAY include vendor-specific -specific
           extensions, which MUST use the format defined in
           {{bibref|TR-106}}.
        
           Example:
        
           \"G.711MuLaw, MP3, X_EXAMPLE-COM_MyFileFormat\"
        
           If the CPE does not support tone files, this parameter
           MUST be {{empty}}.";
      }
      leaf RingFileFormats {
        type enumeration {
          enum "MIDI";
          enum "SMAF";
          enum "RTTTL";
          enum "MP3";
          enum "WAV";
          enum "AMR";
        }
        description
          "{{list}} Each item is a supported ring file format.
           {{enum}}
        
           The list MAY include vendor-specific-specific
           extensions, which MUST use the format defined in
           {{bibref|TR-106}}.
        
           Example:
        
           \"MIDI, AMR, X_EXAMPLE-COM_MyFileFormat\"
        
           If the CPE does not support ring files, this parameter
           MUST be {{empty}}.";
      }
      leaf FacilityActions {
        type enumeration {
          enum "AA_REGISTER";
          enum "AA_ERASE";
          enum "AA_INTERROGATE";
          enum "CA_ACTIVATE";
          enum "CCBS_ACTIVATE";
          enum "CCBS_DEACTIVATE";
          enum "CCBS_INTERROGATE";
          enum "CCNR_ACTIVATE";
          enum "CCNR_DEACTIVATE";
          enum "CCNR_INTERROGATE";
          enum "CFB_REGISTER";
          enum "CFB_ACTIVATE";
          enum "CFB_DEACTIVATE";
          enum "CFB_ERASE";
          enum "CFB_INTERROGATE";
          enum "CFNR_REGISTER";
          enum "CFNR_ACTIVATE";
          enum "CFNR_DEACTIVATE";
          enum "CFNR_ERASE";
          enum "CFNR_INTERROGATE";
          enum "CFNR_TIMER";
          enum "CFT_ACTIVATE";
          enum "CFT_DEACTIVATE";
          enum "CFT_INTERROGATE";
          enum "CFU_REGISTER";
          enum "CFU_ACTIVATE";
          enum "CFU_DEACTIVATE";
          enum "CFU_ERASE";
          enum "CFU_INTERROGATE";
          enum "CLIR_ACTIVATE";
          enum "CLIR_DEACTIVATE";
          enum "CLIR_INTERROGATE";
          enum "CP_INVOKE";
          enum "CW_ACTIVATE";
          enum "CW_DEACTIVATE";
          enum "CW_INVOKE";
          enum "DND_ACTIVATE";
          enum "DND_DEACTIVATE";
          enum "DND_INTERROGATE";
          enum "EXT_INVOKE";
          enum "LINE_INVOKE";
          enum "MAILBOX_INVOKE";
          enum "OCB_ACTIVATE";
          enum "OCB_DEACTIVATE";
          enum "OCB_INTERROGATE";
          enum "PSO_ACTIVATE";
          enum "PW_SET";
          enum "SCF_ACTIVATE";
          enum "SCF_DEACTIVATE";
          enum "SCF_INTERROGATE";
          enum "SCREJ_ACTIVATE";
          enum "SCREJ_DEACTIVATE";
          enum "SCREJ_INTERROGATE";
          enum "SR_ACTIVATE";
          enum "SR_DEACTIVATE";
          enum "SR_INTERROGATE";
        }
        description
          "The facility actions supported by this VoiceService.
           {{enum}}
        
           The list MAY include vendor-specific Facility Actions,
           which MUST use the format defined in
           {{bibref|TR-106}}.
        
           Facility Actions are referenced in the VoiceService
           data model in the objects
           {{object|.CallControl.NumberingPlan.{i}.PrefixInfo.{i}.}}
           and {{object|.Terminal.{i}.ButtonMap.Button.{i}.}}.";
      }

      container SIP {
        description
          "SIP-specific capabilities (as defined in
           {{bibref|RFC3261}}).";

        container Client {
          description
            "SIP client capabilities.";
          leaf Extensions {
            type string;
            description
              "{{list}} Each item is a supported SIP extension
               method among the methods listed in the IANA SIP
               parameters registry (see
               {{bibref|IANA_SIP_Methods}}).  SIP extension
               methods MUST be in the form of the method name in
               upper case.
            
               The list MAY include vendor-specific extensions,
               which MUST use the format defined in
               {{bibref|TR-106}}.
            
               Examples:
            
               : \"REFER\"
            
               : \"INFO\"
            
               : \"X_EXAMPLE-COM_MyExt\"";
          }
          leaf URISchemes {
            type string;
            description
              "{{list}} Each item is a supported URI scheme beyond
               the URI schemes REQUIRED by the SIP specification
               ({{bibref|RFC3261}}).  Each URI scheme is given by
               the URI prefix, without the colon separator.
               Example:
            
               \"tel, fax\"";
          }
          leaf EventTypes {
            type string;
            description
              "{{list}} Each item is a supported event package among
               the event packages listed in the IANA registry for
               SIP Event Type Namespace (see
               {{bibref|IANA_Event_Packages}}).
            
               The list MAY include vendor-specific event
               packages, which MUST use the format defined in
               {{bibref|TR-106}}.
            
               Examples:
            
               : \"call-completion\"
            
               : \"presence\"
            
               : \"X_EXAMPLE-COM_MyEvtPkg\"";
          }
          leaf TLSAuthenticationProtocols {
            type enumeration {
              enum "Null";
              enum "MD5";
              enum "SHA-1";
              enum "SHA-2";
              enum "AEAD";
            }
            description
              "{{list}} Each item is a supported authentication
               protocol for TLS transport.  {{enum}}
            
               The list MAY include vendor-specific protocols,
               which MUST use the format defined in
               {{bibref|TR-106}}.";
          }
          leaf TLSAuthenticationKeySizes {
            type uint32;
            description
              "{{list}} Each item represents a supported TLS
               authentication key size.";
          }
          leaf TLSEncryptionProtocols {
            type enumeration {
              enum "Null";
              enum "RC4";
              enum "RC2";
              enum "DES";
              enum "3DES";
              enum "AES";
              enum "Camellia";
            }
            description
              "{{list}} Each item is a supported encryption protocol
               for TLS transport.  {{enum}}
            
               The list MAY include vendor-specific protocols,
               which MUST use the format defined in
               {{bibref|TR-106}}.";
          }
          leaf TLSEncryptionKeySizes {
            type uint32;
            description
              "{{list}} Each item is a supported TLS encryption key
               size.";
          }
          leaf TLSKeyExchangeProtocols {
            type enumeration {
              enum "RSA";
              enum "DSS";
              enum "DHE-RSA";
              enum "DHE-DSS";
              enum "ECDHE-RSA";
              enum "ECDHE-ECDSA";
            }
            description
              "{{list}} Each item is a supported key exchange
               protocol for TLS transport.  {{enum}}
            
               The list MAY include vendor-specific protocols,
               which MUST use the format defined in
               {{bibref|TR-106}}.";
          }
        }

        container Registrar {
          description
            "SIP registrar capabilities.";
          leaf Extensions {
            type string;
            description
              "{{list}} Each item is a supported SIP extension
               method among the methods listed in the IANA SIP
               parameters registry (see
               {{bibref|IANA_SIP_Methods}}).  SIP extension
               methods MUST be in the form of the method name in
               upper case.
            
               The list MAY include vendor-specific extensions,
               which MUST use the format defined in
               {{bibref|TR-106}}.
            
               Examples:
            
               : \"REFER\"
            
               : \"INFO\"
            
               : \"X_EXAMPLE-COM_MyExt\"";
          }
          leaf URISchemes {
            type string;
            description
              "{{list}} Each item is a supported URI scheme beyond
               the URI schemes REQUIRED by the SIP specification.
               Each URI scheme is given by the URI prefix,
               without the colon separator.  Example:
            
               \"tel, fax\"";
          }
          leaf EventTypes {
            type string;
            description
              "{{list}} Each item is a supported event package among
               the event packages listed in the IANA registry for
               SIP Event Type Namespace (see
               {{bibref|IANA_Event_Packages}}).
            
               The list MAY include vendor-specific event
               packages, which MUST use the format defined in
               {{bibref|TR-106}}.
            
               Examples:
            
               : \"call-completion\"
            
               : \"presence\"
            
               : \"X_EXAMPLE-COM_MyEvtPkg\"";
          }
          leaf TLSAuthenticationProtocols {
            type enumeration {
              enum "Null";
              enum "MD5";
              enum "SHA-1";
              enum "SHA-2";
              enum "AEAD";
            }
            description
              "{{list}} Each item is a supported authentication
               protocol for TLS transport.  {{enum}}
            
               The list MAY include vendor-specific protocols,
               which MUST use the format defined in
               {{bibref|TR-106}}.";
          }
          leaf TLSAuthenticationKeySizes {
            type uint32;
            description
              "{{list}} Each item represents a supported TLS
               authentication key size.";
          }
          leaf TLSEncryptionProtocols {
            type enumeration {
              enum "Null";
              enum "RC4";
              enum "RC2";
              enum "DES";
              enum "3DES";
              enum "AES";
              enum "Camellia";
            }
            description
              "{{list}} Each item is a supported encryption protocol
               for TLS transport.  {{enum}}
            
               The list MAY include vendor-specific protocols,
               which MUST use the format defined in
               {{bibref|TR-106}}.";
          }
          leaf TLSEncryptionKeySizes {
            type uint32;
            description
              "{{list}} Each item is a supported TLS encryption key
               size.";
          }
          leaf TLSKeyExchangeProtocols {
            type enumeration {
              enum "RSA";
              enum "DSS";
              enum "DHE-RSA";
              enum "DHE-DSS";
              enum "ECDHE-RSA";
              enum "ECDHE-ECDSA";
            }
            description
              "{{list}} Each item is a supported key exchange
               protocol for TLS transport.  {{enum}}
            
               The list MAY include vendor-specific protocols,
               which MUST use the format defined in
               {{bibref|TR-106}}.";
          }
        }
      }

      container MGCP {
        description
          "MGCP-specific capabilities (as defined in
           {{bibref|RFC3435}}).";
        leaf Extensions {
          type string;
          description
            "{{list}} Each item is a supported optional MGCP
             package.  MGCP packages are listed using the
             uppercase package abbreviation.
          
             The list MAY include vendor-specific extensions,
             which MUST use the format defined in
             {{bibref|TR-106}}.
          
             Examples:
          
             : \"BP\"
          
             : \"X_EXAMPLE-COM_MyExt\"";
        }
      }

      container H323 {
        description
          "H.323-specific capabilities (as defined in
           {{bibref|H.323}}).";
        leaf FastStart {
          type boolean;
          description
            "Support for H.323 fast start.  If {{true}} indicates
             support for fast start.";
        }
        leaf H235AuthenticationMethods {
          type enumeration {
            enum "dhExch";
            enum "pwdSymEnc";
            enum "pwdHash";
            enum "certSign";
            enum "ipsec";
            enum "tls";
          }
          description
            "{{list}} Each item is a supported authentication
             method.  {{enum}}
          
             The list MAY include vendor-specific protocols,
             which MUST use the format defined in
             {{bibref|TR-106a7}}.";
        }
      }

      container ISDN {
        description
          "The overall ISDN capabilities of external ports of the
           CPE.";
        leaf MSN {
          type boolean;
          description
            "The external ISDN ports support {{bibref|I.251.2}}
             Number identification supplementary services:
             Multiple Subscriber Number";
        }
        leaf DDI {
          type boolean;
          description
            "The external ISDN ports support {{bibref|I.251.1}}
             Number identification supplementary services:
             Direct-dialling-In";
        }
        leaf MCID {
          type boolean;
          description
            "The external ISDN ports support {{bibref|I.251.7}}
             Number identification supplementary services:
             Malicious call Identification";
        }
        leaf MWI {
          type boolean;
          description
            "The external ISDN ports support Message Waiting
             Indication (MWI)";
        }
        leaf AoC {
          type boolean;
          description
            "The external ISDN ports support one or more of the
             followings AOC-services:
          
             {{bibref|I.256.2a}} Charging supplementary services:
             Advice of charge: charging information at call
             set-up time (AOC-S)
          
             {{bibref|I.256.2b}} Charging supplementary services:
             Advice of charge: charging information during the
             call (AOC-D)
          
             {{bibref|I.256.2c}} Charging supplementary services:
             Advice of charge: charging information at the end of
             the call (AOC-E)";
        }
        leaf ECT {
          type boolean;
          description
            "The external ISDN ports support {{bibref|I.252.7}} Call
             offering supplementary services:
          
             Explicit call transfer (ECT)";
        }
      }

      container POTS {
        description
          "The overall POTS capabilities of external ports of the
           CPE.";
        leaf DialType {
          type enumeration {
            enum "Tone";
            enum "Pulse";
            enum "Tone and Pulse";
          }
          description
            "The supported supported dial type.";
        }
        leaf ClipGeneration {
          type boolean;
          description
            "The external POTS ports support Calling Line
             identification (CLIP).";
        }
        leaf ChargingPulse {
          type boolean;
          description
            "The external POTS ports support transmittal of a
             charging pulse according to TR1 TR 110.";
        }
      }

      list Codec {
        key "Codec BitRate";
        description
          "Table to describe the set of supported codecs.";
        leaf Codec {
          type enumeration {
            enum "AMR";
            enum "Clearmode";
            enum "EVRC1";
            enum "EVRCB1";
            enum "G.711MuLaw";
            enum "G.711ALaw";
            enum "G.726";
            enum "G.729";
            enum "G.729.1";
            enum "G.729a";
            enum "G.729e";
            enum "G.728";
            enum "G.723.1";
            enum "G.722";
            enum "G.722.1";
            enum "G.722.2";
            enum "Generic Comfort Noise";
            enum "GSM-FR";
            enum "GSM-HR";
            enum "GSM-EFR";
            enum "iLBC";
            enum "Speex";
          }
          description
            "Identifier of the type of codec.  {{enum}}
          
             The parameter MAY instead be a vendor-specific
             codec, which MUST be in the format defined in
             {{bibref|TR-106}}.  For example:
          
             \"X_EXAMPLE-COM_MyCodec\"";
        }
        leaf BitRate {
          type uint32;
          description
            "Bit rate, specified in {{units}}.  The value MUST be
             among the values appropriate for the specified
             codec.";
        }
        leaf PacketizationPeriod {
          type string {
            length "0..64";
          }
          description
            "{{list}} Each item is a supported packetization period,
             in milliseconds, or a continuous range of
             packetization periods.  Ranges are indicated as a
             hyphen-separated pair of unsigned integers.
             Examples:
          
             : \"20\" indicates a single discrete value.
          
             : \"10, 20, 30\" indicates a set of discrete values.
          
             : \"5-40\" indicates a continuous inclusive range.
          
             : \"5-10, 20, 30\" indicates a continuous range in
             addition to a set of discrete values.
          
             A range MUST only be indicated if all values within
             the range are supported.";
        }
        leaf SilenceSuppression {
          type boolean;
          description
            "If {{true}} indicates support for silence suppression
             for this codec.";
        }
      }

      container QualityIndicator {
        description
          "Specific capabilities concerning quality indicators.";
        leaf QIModelsSupported {
          type string;
          description
            "Comma-separated list of supported models for evaluation
             of VoIP Quality Indicator.  {{empty}} indicates that
             CPE does not support evaluation of this indicator.
          
             The entry MAY include vendor-specific models, which
             MUST be in the format defined in {{bibref|TR-106}}.
          
             For example: “P.564,G.107,X_EXAMPLE-COM_MyModel”";
        }
        leaf MaxQIValues {
          type uint32 {
            range "0..127";
          }
          description
            "Specifies the maximum number of QI values which can be
             reported for a session.  If this parameter is empty
             there is no specified maximum limit.
          
             If possible this limit SHOULD be large enough to
             handle at least 10 to 15 minutes of call time, which
             would typically mean 60 to 90 quality values for
             commonly used quality models.";
        }
        leaf MaxWorstQIValues {
          type uint32 {
            range "0..127";
          }
          description
            "Maximum number of worst QI values which the CPE is able
             to store and report.  A value of 0 indicates no
             specific maximum number of worst QI values.";
        }
      }
    }

    container ReservedPorts {
      description
        "The list of IP ports on the CPE WAN and LAN interfaces that
         will not be allocated by the ACS and therefore are
         available to be allocated by the CPE.  The CPE can
         dynamically allocate ports from this range for things
         like signaling listening ports or local RTP ports.";
      leaf WANPortRange {
        type string;
        description
          "Range of ports reserved for use by the CPE on any WAN
           interface.  {{list}} Each range consists of a
           ''Start'' part consisting of 1 to n digits (string
           representation) followed by an OPTIONAL ''End'' part
           consisting of 1 to n digits prefixed by a \"-\"
           symbol.
        
           Example:
        
           : 12345-12350,23580";
      }
      leaf LANPortRange {
        type string;
        description
          "Range of ports reserved for use by the CPE on any LAN
           interfaces.  {{list}} Each range consists of a
           ''Start'' part consisting of 1 to n digits (string
           representation) followed by an OPTIONAL ''End'' part
           consisting of 1 to n digits prefixed by a \"-\"
           symbol.
        
           Example:
        
           : 12345-12350,23580";
      }
    }

    container ISDN {
      description
        "This object models ISDN physical interfaces (BRI and PRI)
         supporting {{bibref|Q.931}} based signalling.";

      list BRI {
        key "Name";
        description
          "ISDN BRI physical interfaces table (a voice physical
           interface as described in {{bibref|TR-104i2|Section
           4.1}}).";
        leaf Enable {
          type boolean;
          description
            "Enables or disables this ISDN BRI interface.";
        }
        leaf Status {
          type enumeration {
            enum "Up";
            enum "Error";
            enum "Testing";
            enum "Disabled";
          }
          config false;
          description
            "Indicates the status of this physical interface.";
        }
        leaf Name {
          type string {
            length "0..64";
          }
          config false;
          description
            "The textual name of the interface as assigned by the
             CPE.";
        }
        leaf ToneEventProfile {
          type string {
            length "0..256";
          }
          description
            "Reference to the {{object|.Tone.EventProfile}} to use
             with this interface.  If this parameter is
             {{empty}}, the value of
             {{param|.Tone.DefautEventProfile}} is used instead.";
        }
        leaf ApplicationInterface {
          type enumeration {
            enum "VoIP";
            enum "VoATM";
            enum "Data";
          }
          description
            "Specify the type of application that uses the
             interface.";
        }
        leaf Protocol {
          type enumeration {
            enum "EuroISDN";
            enum "NI-1";
            enum "NI-2";
            enum "5ESS";
            enum "NTT";
            enum "VN3";
            enum "VN4";
            enum "Q.SIG";
          }
          description
            "Specifies the protocol variant used for the interface.
             {{enum}}
          
             The list MAY include vendor-specific protocols,
             which MUST use the format defined in
             {{bibref|TR-106}}.";
        }
        leaf ProtocolEmulation {
          type enumeration {
            enum "TE";
            enum "NT";
          }
          description
            "Protocol emulation for the interface.";
        }
        leaf PermanentLayer2 {
          type boolean;
          description
            "If {{true}}, avoid the disconnection of the ISDN layer
             2 when the ISDN terminal or the ISDN network
             disconnects the layer 2 (in static TEI mode); it
             will be maintained established.";
        }
        leaf PermanentLayer1 {
          type boolean;
          description
            "Maintain the ISDN layer 1 up; it is useful for clocking
             and management.";
        }
        leaf LapdDisconnectionTimeout {
          type boolean;
          description
            "Avoid the disconnection of the ISDN layer 1 or 2 up
             when there is no call in progress in dynamic TEI
             mode.";
        }
        leaf TEINegotiation {
          type enumeration {
            enum "Static";
            enum "Dynamic";
          }
          description
            "TEI management mode.  It MUST be set to
             {{enum|Dynamic}} for ISDN phones or connection to an
             ISDN network and {{enum|Static}} for PBX.";
        }
        leaf StaticTEI {
          type uint32 {
            range "min..63";
          }
          description
            "TEI value in static mode.";
        }
        leaf LifeLineHold {
          type boolean;
          description
            "Enable or disable the lifeline bypass on the BRI S0
             voice module.  If the interface is used by the VoIP
             gateway, the bypass is enabled if the CPE is not
             registered on registration server.";
        }
        leaf PowerSourceOne {
          type boolean;
          description
            "To enable (disable) the power source one (PS1) on the
             BRI interfaces.";
        }
        leaf MaxNumBChannels {
          type uint32 {
            range "min..2";
          }
          description
            "Maximum number of simultaneous B channels.";
        }
        leaf OutboundOnlyBChannels {
          type uint32 {
            range "1..2";
          }
          description
            "{{list|reserved B-channels which can be used only for
             outbound calls}}";
        }
        leaf InboundOnlyBChannels {
          type uint32 {
            range "1..2";
          }
          description
            "{{list|reserved B-channels which can be used only for
             inbound calls}}";
        }
        leaf BidirectionalBChannels {
          type uint32 {
            range "1..2";
          }
          description
            "{{list|reserved B-channels which can be used
             bidirectional}}";
        }
      }

      list PRI {
        key "Name";
        description
          "ISDN PRI physical interfaces table (a voice physical
           interface as described in {{bibref|TR-104i2|Section
           4.1}}).";
        leaf Enable {
          type boolean;
          description
            "Enables or disables this ISDN PRI interface.";
        }
        leaf Status {
          type enumeration {
            enum "Up";
            enum "Error";
            enum "Testing";
            enum "Disabled";
          }
          config false;
          description
            "Indicates the status of this physical interface.";
        }
        leaf Name {
          type string {
            length "0..64";
          }
          config false;
          description
            "The textual name of the interface as assigned by the
             CPE.";
        }
        leaf ToneEventProfile {
          type string {
            length "0..256";
          }
          description
            "Reference to the {{object|.Tone.EventProfile}} to use
             with this interface.  If this parameter is
             {{empty}}, the value of
             {{param|.Tone.DefautEventProfile}} is used instead.";
        }
        leaf ApplicationInterface {
          type enumeration {
            enum "VoIP";
            enum "VoATM";
            enum "Data";
          }
          description
            "Specify the type of application that uses the
             interface.";
        }
        leaf Protocol {
          type enumeration {
            enum "EuroISDN";
            enum "NI-1";
            enum "NI-2";
            enum "4ESS";
            enum "5ESS";
            enum "NTT";
            enum "Q.SIG";
          }
          description
            "Specifies the protocol variant used for the interface.
             {{enum}}
          
             The list MAY include vendor-specific protocols,
             which MUST use the format defined in
             {{bibref|TR-106}}.";
        }
        leaf ProtocolEmulation {
          type enumeration {
            enum "TE";
            enum "NT";
          }
          description
            "Specify the protocol emulation for this interface.";
        }
        leaf PermanentLayer2 {
          type boolean;
          description
            "If {{true}}, avoid the disconnection of the ISDN layer
             2 when the ISDN terminal or the ISDN network
             disconnects the layer 2 (in static TEI mode); it
             will be maintained established.";
        }
        leaf Linecode {
          type enumeration {
            enum "ami";
            enum "hdb3";
            enum "b8zs";
          }
          description
            "Specify the physical line coding to be used.";
        }
        leaf ESF {
          type enumeration {
            enum "None";
            enum "DF";
            enum "MF";
            enum "EMF";
            enum "SF";
            enum "ESF";
            enum "AutoDetect";
          }
          description
            "Specify the framing type.";
        }
        leaf PhysicalInterfaceType {
          type enumeration {
            enum "T1";
            enum "E1";
          }
          description
            "{{enum}}";
        }
        leaf MaxNumBChannels {
          type uint32 {
            range "min..30";
          }
          description
            "Maximum number of simultaneous B channels.";
        }
        leaf OutboundOnlyBChannels {
          type uint32 {
            range "0..31";
          }
          description
            "{{list|reserved B-channels which can be used only for
             outbound calls}}";
        }
        leaf InboundOnlyBChannels {
          type uint32 {
            range "0..31";
          }
          description
            "{{list|reserved B-channels which can be used only for
             inbound calls}}";
        }
        leaf BidirectionalBChannels {
          type uint32 {
            range "0..31";
          }
          description
            "{{list|reserved B-channels which can be used
             bidirectional}}";
        }
        leaf ClockMode {
          type enumeration {
            enum "Master";
            enum "Slave";
          }
          description
            "Determines the role of the CPE for the purpose of clock
             synchronisation on this interface.";
        }
      }
    }

    container POTS {
      description
        "This object models analogue lines.  Both FXO and FXS are
         handled.";
      leaf Region {
        type string {
          length "0..2";
        }
        description
          "The geographic region associated to POTS (MUST be an
           alpha-2 (two-character alphabetic) country code as
           specified by {{bibref|ISO3166-1}}).  This MAY be used
           by the CPE to customize localization settings.
        
           If {{empty}}, indicates that the region is unspecified
           and the CPE SHOULD use default localization settings.";
      }

      list FXO {
        key "Name";
        description
          "FXO physical interfaces table (a voice physical interface
           as described in {{bibref|TR-104i2|Section 4.1}}).
        
           Each entry in the table models an analogue physical
           interface as defined by {{bibref|ETSI_ES_203_021}}";
        leaf Enable {
          type boolean;
          description
            "Enables or disables this FXO interface.";
        }
        leaf Status {
          type enumeration {
            enum "Up";
            enum "Error";
            enum "Testing";
            enum "Disabled";
          }
          config false;
          description
            "Indicates the status of this physical interface.";
        }
        leaf Name {
          type string {
            length "0..64";
          }
          config false;
          description
            "The textual name of the interface as assigned by the
             CPE.";
        }
        leaf ToneEventProfile {
          type string {
            length "0..256";
          }
          description
            "Reference to the {{object|.Tone.EventProfile}} to use
             with this interface.  If this parameter is
             {{empty}}, the value of
             {{param|.Tone.DefautEventProfile}} is used instead.";
        }
        leaf SecondStepDialing {
          type boolean;
          default "false";
          description
            "Enables the second step dialing mode.
          
             If {{false}}, incoming dialed digits are processed
             through the voice routing table.
          
             If {{true}}, the FXO port goes directly to the
             off-hook state and works as a FXS port for the
             dialing reception (a dial-tone is transmitted).  The
             received digits are processed through the routing
             table until a match is found.  If a match is found,
             the call is routed to the appropriate subscriber.";
        }
        leaf TimeoutBeforeDialing {
          type uint32 {
            range "1..60";
          }
          description
            "Specifies the time in {{units}} between off-hook and
             the transmission of the first digit for FXO
             interface.";
        }
        leaf RingingTimeout {
          type uint32 {
            range "1..30";
          }
          description
            "Defines the timeout in {{units}} for incoming call on
             this FXO port: after receiving a ringing signal, the
             call is disconnected if no ringing signal is
             received anymore during this time.";
        }
        leaf RingNumber {
          type uint32 {
            range "1..40";
          }
          description
            "Defines the number of pulses for ringing signal
             detection on FXO port.";
        }
        leaf OnHookMinDuration {
          type uint32 {
            range "20..10000";
          }
          description
            "Specify the minimum duration in {{units}} of the
             \"on-hook\" state between two successive calls.";
        }
        leaf SignalingMode {
          type enumeration {
            enum "LoopStart";
            enum "GroundStart";
          }
          default "LoopStart";
          description
            "Signaling mode used for line seizure by the CPE.";
        }
        leaf DTMFDialoutInterval {
          type uint32 {
            range "20..10000";
          }
          description
            "The time interval in {{units}} between dialing DTMF
             digits to PSTN.  See also {{bibref|ETSI_ES_203_021}}";
        }
        leaf CallerIdDetectionEnable {
          type boolean;
          description
            "Enables the detection of CallerId for incoming calls.
             See also {{bibref|ETSI_ES_203_021}}.";
        }
        leaf Active {
          type boolean;
          config false;
          description
            "Determines if this physical interface is plugged.";
        }

        container DiagTests {
          description
            "FXO port tests.";
          leaf DiagnosticsState {
            type enumeration {
              enum "None";
              enum "Requested";
              enum "Complete";
              enum "Error_Internal";
              enum "Error_Other";
            }
            description
              "Indicates availability of diagnostic data.  {{enum}}
            
               If the ACS sets the value of this parameter to
               {{enum|Requested}}, the CPE MUST initiate the
               corresponding diagnostic test.  When writing, the
               only allowed value is {{enum|Requested}}.  To
               ensure the use of the proper test parameters (the
               writable parameters in this object), the test
               parameters MUST be set either prior to or at the
               same time as (in the same SetParameterValues)
               setting the {{param}} to {{enum|Requested}}.
            
               When requested, the CPE SHOULD wait until after
               completion of the communication session with the
               ACS before starting the diagnostic.
            
               When the test is completed, the value of this
               parameter MUST be either {{enum|Complete}} (if the
               test completed successfully), or one of the Error
               values listed above.
            
               After the diagnostic is complete, the value of all
               result parameters (all read-only parameters in
               this object) MUST be retained by the CPE until
               either this diagnostic is run again, or the CPE
               reboots.  After a reboot, if the CPE has not
               retained the result parameters from the most
               recent test, it MUST set the value of this
               parameter to {{enum|None}}.
            
               Modifying any of the writable parameters in this
               object except for this one MUST result in the
               value of this parameter being set to None.
            
               While the test is in progress, modifying any of
               the writable parameters in this object except for
               this one MUST result in the test being terminated
               and the value of this parameter being set to
               {{enum|None}}.
            
               While the test is in progress, setting this
               parameter to {{enum|Requested}} (and possibly
               modifying other writable parameters in this
               object) MUST result in the test being terminated
               and then restarted using the current values of the
               test parameters.";
          }
          leaf TestSelector {
            type enumeration {
              enum "Battery";
              enum "DialTone";
            }
            description
              "Indicates which test to perform.  {{enum}}
            
               The parameter MAY instead indicate a
               vendor-specific test, which MUST use the format
               defined in {{bibref|TR-106}}.  For example:
               \"X_EXAMPLE-COM_MyTest\"";
          }
          leaf TestResult {
            type enumeration {
              enum "Success";
              enum "Failure";
            }
            config false;
            description
              "Result of the selected test.  {{enum}}
            
               The parameter MAY instead indicate a
               vendor-specific result, which MUST use the format
               defined in {{bibref|TR-106}}.  For example:
               \"X_EXAMPLE-COM_MyResult\"";
          }
        }
      }

      list FXS {
        key "Name";
        description
          "FXS physical interfaces table (a voice physical interface
           as described in {{bibref|TR-104i2|Section 4.1}}).
        
           Each entry in the table models an analogue physical
           interface as defined by {{bibref|ETSI_ES_201_970}}";
        leaf Enable {
          type boolean;
          description
            "Enables or disables this FXS interface.";
        }
        leaf Status {
          type enumeration {
            enum "Up";
            enum "Error";
            enum "Testing";
            enum "Disabled";
          }
          config false;
          description
            "Indicates the status of this physical interface.";
        }
        leaf Name {
          type string {
            length "0..64";
          }
          config false;
          description
            "The textual name of the interface as assigned by the
             CPE.";
        }
        leaf ToneEventProfile {
          type string {
            length "0..256";
          }
          description
            "Reference to the {{object|.Tone.EventProfile}} to use
             with this interface.  If this parameter is
             {{empty}}, the value of
             {{param|.Tone.DefautEventProfile}} is used instead.";
        }
        leaf FaxPassThrough {
          type enumeration {
            enum "Disable";
            enum "Auto";
            enum "Force";
          }
          description
            "Indicates the support for pass-through of fax data of
             this interface.  {{enum}}";
        }
        leaf ModemPassThrough {
          type enumeration {
            enum "Disable";
            enum "Auto";
            enum "Force";
          }
          description
            "Indicates the support for pass-through of modem data of
             this interface.  {{enum}}";
        }
        leaf DialType {
          type enumeration {
            enum "Tone";
            enum "Pulse";
          }
          description
            "Dial type used on the line.";
        }
        leaf ClipGeneration {
          type boolean;
          description
            "Whether the Calling Line identification (CLIP) is
             enabled.";
        }
        leaf ChargingPulse {
          type boolean;
          description
            "Whether a charging pulse is transmitted on the line.";
        }
        leaf Active {
          type boolean;
          config false;
          description
            "Indicates whether a terminal is plugged on this
             physical interface.";
        }
        leaf TerminalType {
          type enumeration {
            enum "Audio";
            enum "Fax";
            enum "Modem";
            enum "Any";
          }
          description
            "Defines the terminal type plugged on this interface to
             determine the correct signaling to be used to
             contact the terminal.";
        }

        container VoiceProcessing {
          description
            "Parameters related to voice processing
             (analogue/digital conversion) capabilities.";
          leaf TransmitGain {
            type int32;
            description
              "Gain in {{units}} to apply to the transmitted voice
               signal prior to encoding.  This gain is a modifier
               of the default transmit-gain, which is
               unspecified.";
          }
          leaf ReceiveGain {
            type int32;
            description
              "Gain in {{units}} to apply to the received voice
               signal after decoding.  This gain is a modifier of
               the default receive-gain, which is unspecified.";
          }
          leaf EchoCancellationEnable {
            type boolean;
            description
              "Enable or disable echo cancellation for this line.";
          }
          leaf EchoCancellationInUse {
            type boolean;
            config false;
            description
              "Indication of whether or not echo cancellation is
               currently in use for this line.";
          }
          leaf EchoCancellationTail {
            type uint32;
            config false;
            description
              "Tail length in {{units}} of the echo canceller
               associated with this line (whether or not it is
               currently in use).";
          }
        }

        container DiagTests {
          description
            "FXS port tests.";
          leaf DiagnosticsState {
            type enumeration {
              enum "None";
              enum "Requested";
              enum "Complete";
              enum "Error_Internal";
              enum "Error_Other";
            }
            description
              "Indicates availability of diagnostic data.  {{enum}}
            
               If the ACS sets the value of this parameter to
               {{enum|Requested}}, the CPE MUST initiate the
               corresponding diagnostic test.  When writing, the
               only allowed value is {{enum|Requested}}.  To
               ensure the use of the proper test parameters (the
               writable parameters in this object), the test
               parameters MUST be set either prior to or at the
               same time as (in the same SetParameterValues)
               setting the DiagnosticsState to
               {{enum|Requested}}.
            
               When requested, the CPE SHOULD wait until after
               completion of the communication session with the
               ACS before starting the diagnostic.
            
               When the test is completed, the value of this
               parameter MUST be either {{enum|Complete}} (if the
               test completed successfully), or one of the Error
               values listed above.
            
               After the diagnostic is complete, the value of all
               result parameters (all read-only parameters in
               this object) MUST be retained by the CPE until
               either this diagnostic is run again, or the CPE
               reboots.  After a reboot, if the CPE has not
               retained the result parameters from the most
               recent test, it MUST set the value of this
               parameter to {{enum|None}}.
            
               Modifying any of the writable parameters in this
               object except for this one MUST result in the
               value of this parameter being set to None.
            
               While the test is in progress, modifying any of
               the writable parameters in this object except for
               this one MUST result in the test being terminated
               and the value of this parameter being set to
               {{enum|None}}.
            
               While the test is in progress, setting this
               parameter to {{enum|Requested}} (and possibly
               modifying other writable parameters in this
               object) MUST result in the test being terminated
               and then restarted using the current values of the
               test parameters.";
          }
          leaf TestSelector {
            type enumeration {
              enum "Hazard Potential";
              enum "Foreign Voltage";
              enum "Resistive Faults";
              enum "Off-hook";
              enum "REN";
            }
            description
              "Indicates which GR-909 test to perform.";
          }
          leaf TestResult {
            type enumeration {
              enum "Success";
              enum "Failure";
            }
            config false;
            description
              "Result of the selected test.";
          }
        }
      }

      container Ringer {
        description
          "This object contains the ring sequences configured for
           analogue lines.";

        list Event {
          key "Function";
          description
            "Table of events for which a ring pattern is defined.
             The table is pre-populated with the complete list of
             events for which the CPE supports definition of ring
             patterns.";
          leaf Function {
            type enumeration {
              enum "Default";
              enum "CCBSCallBack";
              enum "CCNRCallBack";
              enum "InternalCall";
              enum "RingSplash";
              enum "Group";
            }
            config false;
            description
              "The event for which the ring pattern is to apply.
               {{enum}}
            
               The parameter MAY instead indicate a
               vendor-specific event name, which MUST use the
               format defined in {{bibref|TR-106}}.";
          }
          leaf Cadence {
            type uint32;
            description
              "{{list}} The values represent an alternating pattern
               of times (in {{units}}) when the ringer is ON or
               OFF.
            
               Example: \"1000,5000\"
            
               See also {{bibref|ETSI_TR_101_183}}.";
          }
        }
      }
    }

    container DECT {
      description
        "This object models DECT bases and portables.";

      list Base {
        key "RFPI";
        description
          "DECT base table (a voice physical interface as described
           in {{bibref|TR-104i2|Section 4.1}}).";
        leaf Enable {
          type boolean;
          description
            "Enables or disables this base.";
        }
        leaf Status {
          type enumeration {
            enum "Up";
            enum "Error";
            enum "Testing";
            enum "Disabled";
          }
          config false;
          description
            "Indicates the status of this base.";
        }
        leaf Name {
          type string {
            length "0..64";
          }
          config false;
          description
            "The textual name of the interface as assigned by the
             CPE.";
        }
        leaf ToneEventProfile {
          type string {
            length "0..256";
          }
          description
            "Reference to the {{object|.Tone.EventProfile}} to use
             with this interface.  If this parameter is
             {{empty}}, the value of
             {{param|.Tone.DefautEventProfile}} is used instead.";
        }
        leaf Standard {
          type enumeration {
            enum "GAP";
            enum "CAT-iq 1.0";
            enum "CAT-iq 2.0";
            enum "CAT-iq 2.1";
            enum "CAT-iq 3.0";
            enum "CAT-iq 4.0";
          }
          config false;
          description
            "The highest DECT protocol version supported by the
             base.";
        }
        leaf RFPI {
          type yang:hex-string {
            length "0..5";
          }
          config false;
          description
            "The Radio Fixed Part Identity which uniquely identifies
             the Base.  The RFPI is a 40 bits number stored in a
             hexbinary string.  The format of the number is
             class-dependant and is defined in
             {{bibref|ETSI_EN_300_175-6|sections 5.1 to 5.5}}.";
        }
        leaf MaxSupportedPP {
          type uint32;
          description
            "The maximum number of Portable Parts (PP) supported by
             the DECT base of the CPE.";
        }
        leaf PIN {
          type yang:hex-string {
            length "0..4";
          }
          description
            "The PIN is an hexbinary string of 32 bits, as defined
             in {{bibref|ETSI_TS_102_527-3}}.";
        }
        leaf RepeaterSupportEnabled {
          type boolean;
          config false;
          description
            "If {{true}}, the DECT system supports the REP feature,
             as defined in {{bibref|ETSI_EN_300_175-8}}.";
        }
        leaf NEMOEnable {
          type boolean;
          description
            "Enable or disable NEMO (No Emission Mode as defined in
             {{bibref|ETSI_TS_102_527-3}}) operation of the base.
             Note: NEMO operations can be successfully enabled
             only if all PPs registered to the CPE support the
             NEMO operations.";
        }
        leaf SubscriptionEnable {
          type boolean;
          description
            "Enables the subscription mode of the DECT base.  If
             {{true}}, the ''subscription window'' is open,
             otherwise it is closed.  When the ''subscription
             window'' is open, a DECT portable part can be
             subscribed / registered to the DECT base.  When
             written as {{true}}, it forces the device to open
             the ''subscription window''.  When the
             ''subscription window'' timeslot expires, the value
             MUST be changed back to {{false}}.
          
             If the CPE user can open the ''subscription window''
             with a specific command (i.e.  via DECT base GUI or
             pushing a button), the parameter MUST report the
             correct status ({{true}}, while the window is
             opened).";
        }
        leaf CipheringEnable {
          type boolean;
          description
            "Enable or disable ciphering for the calls on the DECT
             domain.";
        }
        leaf EncryptionType {
          type enumeration {
            enum "DSC";
            enum "DSC2";
            enum "CCM";
          }
          config false;
          description
            "Algorithm used in the encryption process defined in
             {{bibref|ETSI_EN_300_175-7}}.";
        }
        leaf RFPowerControl {
          type enumeration {
            enum "Normal";
            enum "Reduced";
          }
          description
            "This parameter is used to control the sending RF power
             as per the required range within the customer
             premises.
          
             When set to 'Reduced', the CPE SHALL undertake
             measures to reduce the transmission RF power.";
        }
        leaf FirmwareVersion {
          type string {
            length "0..20";
          }
          config false;
          description
            "Firmware version of the base as defined in
             {{bibref|ETSI_TS_102_527-3}}";
        }
        leaf EepromVersion {
          type string {
            length "0..20";
          }
          config false;
          description
            "EEPROM version of the base as defined in
             {{bibref|ETSI_TS_102_527-3}}";
        }
        leaf HardwareVersion {
          type string {
            length "0..20";
          }
          config false;
          description
            "Hardware version of the base as defined in
             {{bibref|ETSI_TS_102_527-3}}";
        }

        container Stats {
          config false;
          description
            "This object is associated with statistics collected
             from the DECT domain of the CPE.  The collected
             statistics are common for all call scenarios.
          
             The CPE MUST reset the DECT base's Stats parameters
             (unless otherwise stated in individual object or
             parameter descriptions) either when the base becomes
             operationally down due to a previous administrative
             down (i.e.  the base's {{param|#.Status}} parameter
             transitions to a down state after the base is
             disabled) or when the base becomes administratively
             up (i.e.  the base's {{param|#.Enable}} parameter
             transitions from {{false}} to {{true}}).";
          leaf Handovers {
            type uint32;
            description
              "The count of all successful handovers.";
          }
          leaf HandoverFailures {
            type uint32;
            description
              "The count of all failed handovers.";
          }
          leaf ControlFieldErrors {
            type uint32;
            description
              "The count of all bad A-field packets.";
          }
          leaf PayloadFieldErrors {
            type uint32;
            description
              "The count of all bad B-field packets.";
          }
          leaf SyncFailures {
            type uint32;
            description
              "The count of all synchronization failures during all
               calls.";
          }
        }
      }

      list Portable {
        key "IPEI";
        description
          "DECT portable table.";
        leaf Enable {
          type boolean;
          description
            "Enables or disables this DECT portable.";
        }
        leaf Status {
          type enumeration {
            enum "Up";
            enum "Error";
            enum "Testing";
            enum "Disabled";
          }
          config false;
          description
            "Indicates the status of this DECT portable.";
        }
        leaf CodecList {
          type string;
          description
            "{{list}} {{reference}}
          
             The CPE SHOULD use the first enabled item in the
             list among those supported by the portable.";
        }
        leaf RegistrationStatus {
          type enumeration {
            enum "In reach";
            enum "Not in reach";
          }
          config false;
          description
            "The current registration status of the DECT portable.";
        }
        leaf IPUI {
          type yang:hex-string {
            length "0..13";
          }
          config false;
          description
            "The International Portable User Identity which uniquely
             identifies the current user of the portable.
          
             The IPUI is composed of the Portable User Type
             (PUT), of 4 bits, followed by the Portable User
             Number (PUN) whose size and format depend on PUT
             (see {{bibref|ETSI_EN_300_175-6|Section 6.2}}).
          
             The hexbinary string is encoded exactly as it is
             defined in {{bibref|ETSI_EN_300_175-5|section
             7.7.30}}) :
          
             * Bits from position 0 to 3 represent the PUT (as
             defined in {{bibref|ETSI_EN_300_175-6|section
             7.3}}).
          
             * Bits from position 4 to {{param|IPUILength}}-1
             represent the PUN.
          
             * Unused bits after position {{param|IPUILength}}-1
             are set to 0.
          
             Examples :
          
             : - Type N (PUT + IPEI) :
          
             :: - PUT = 0000 (4 bits) = 0 (hexadecimal)
          
             :: - IPEI = 0000 0000 0000 1100 0000 0000 0000 1000
             1001 (36 bits) = 00 0C 00 08 9 (hexadecimal)
          
             :: - IPUILength = 4 + 36 = 40 (bits)
          
             :: - IPUI = 00 00 C0 00 89 (40 bits; multiple of 8
             so no bits are ignored)
          
             : - Type O (PUT + binary-coded number) :
          
             :: - PUT = 0001 (4 bits) = 1 (hexadecimal)
          
             :: - Number (decimal) = 4546812123
          
             :: - Number (binary) = 1000 0111 1000 0001 0110 1100
             0110 1101 1 (33 bits)
          
             :: - Number (hexadecimal) = 87 81 6C 6D 8 (33 bits;
             last three bits are ignored)
          
             :: - IPUILength = 4 + 33 = 37 (bits)
          
             :: - IPUI = 18 78 16 C6 D8 (37 bits; last 3 bits are
             ignored)
          
             : - Type Q (PUT + BCD number) :
          
             :: - PUT = 0011 (4 bits) = 3 (hexadecimal)
          
             :: - Number (decimal) = 4546812123
          
             :: - Number (BCD) = 0100 0101 0100 0110 1000 0001
             0010 0001 0010 0011 (40 bits)
          
             :: - IPUILength = 4 + 40 = 44 (bits)
          
             :: - IPUI = 34 54 68 12 12 30 (40 bits; last 4 bits
             are ignored)";
        }
        leaf IPUILength {
          type uint32;
          config false;
          description
            "The length of {{param|IPUI}}, in {{units}}.";
        }
        leaf IPEI {
          type yang:hex-string {
            length "0..5";
          }
          config false;
          description
            "The International Portable Equipment Identity which is
             globally unique and identifies the portable.
          
             The IPEI is composed of the Equipment Manufacturer's
             Code (EMC), of 16 bits, followed by the Portable
             equipment Serial Number (PSN) of 20 bits (see
             {{bibref|ETSI_EN_300_175-6|Section 10}}).
          
             The hexbinary string is encoded as follows :
          
             * Bits from position 0 to 15 represent the EMC.
          
             * Bits from position 16 to 35 represent the PSN.
          
             * The last four bits are unused and are set to 0.";
        }
        leaf PARK {
          type yang:hex-string {
            length "0..5";
          }
          config false;
          description
            "The Portable Access Rights Key of this portable.
          
             The PARK is composed of the Access Rights Class
             (ARC) of 3 bits and the Access Rights Details (ARD)
             whose size and format depend on the ARC (see
             {{bibref|ETSI_EN_300_175-6|Sections 6.1.1 to
             6.1.5}}).
          
             The hexbinary string is encoded as follows :
          
             * Bits from position 0 to 2 represent the ARC (as
             defined in {{bibref|ETSI_EN_300_175-6|section
             7.2}}).
          
             * For class A :
          
             ** Bits from position 3 to 35 represent the ARD.
          
             ** The last four bits are unused and are set to 0.
          
             * For other classes :
          
             ** Bits from position 3 to 31 represent the ARD.";
        }
        leaf BaseAttachedTo {
          type string {
            length "0..256";
          }
          config false;
          description
            "Refers to the {{object|#.Base}} where this portable
             part is attached to.";
        }
        leaf PortableType {
          type enumeration {
            enum "GAP";
            enum "CAT-iq 1.0";
            enum "CAT-iq 2.0";
            enum "CAT-iq 2.1";
            enum "CAT-iq 3.0";
            enum "CAT-iq 4.0";
          }
          config false;
          description
            "{{list}} Protocols used for connection.";
        }
        leaf SubscriptionTime {
          type yang:date-and-time;
          config false;
          description
            "The date and time in which the DECT portable has been
             subscribed with the base.
          
             If NTP or equivalent is not available, this
             parameter, if present, SHOULD be set to the Unknown
             Time value.";
        }
        leaf Control {
          type enumeration {
            enum "Unregister";
            enum "Disable";
          }
          description
            "This parameter MAY be used by the ACS to control the
             registration status of the portable.";
        }
        leaf HardwareVersion {
          type string {
            length "0..20";
          }
          config false;
          description
            "Indicates the Hardware Version of a DECT portable.
             Corresponds to the portable HW Version identifier
             parameter, as defined in
             {{bibref|ETSI_TS_102_527-4}}.";
        }
        leaf SoftwareVersion {
          type string {
            length "0..20";
          }
          config false;
          description
            "Indicates the Software Version used by a DECT portable.
             Maps with the portable SW Version identifier
             parameter, as defined in
             {{bibref|ETSI_TS_102_527-4}}.";
        }
        leaf SoftwareUpgrade {
          type boolean;
          config false;
          description
            "This parameter indicates support for SUOTA (Software
             Update Over The Air).";
        }
        leaf LastUpdateDateTime {
          type yang:date-and-time;
          config false;
          description
            "Indicates the last successful SW update of the DECT
             portable.  This is based on the reception of a
             FACILITY message (being part of the HS version
             indication procedure) from the portable containing
             another value of SW version than the current value
             in this table.  This new SW version is then updated
             in this table.";
        }
        leaf OperatorName {
          type string {
            length "0..32";
          }
          description
            "The name of the operator that will be displayed on the
             portable, if it supports this feature.";
        }
      }
    }

    container SIP {
      description
        "This object is dedicated to SIP as defined in
         {{bibref|RFC3261}}.  It models SIP networks, clients,
         proxies and registrars.";

      list Client {
        key "Alias";
        description
          "SIP client table (a Client as described in
           {{bibref|TR-104i2|Section 4.2}}).  Each SIP client
           maintains its identity-to-location (i.e.,
           RegisterURI-to-ContactURI) binding for SIP signaling
           exchanged between the client and the network.
        
           For CPE use cases where {{object|.CallControl}} is
           used to map network-facing to user-facing objects, the
           relationship between the SIP client object and its
           associated {{object|.CallControl.Line}} object(s) is
           determined by the {{param|RegisterMode}} parameter, as
           follows:
        
           : - In case of RFC3261-style explicit registration of
           SIP AoRs, only a single line shall be associated with
           each SIP client.
        
           : - In case of RFC6140 or IMS/TISPAN-style
           registration, multiple lines can be associated with
           each SIP client.  The set of lines associated with a
           SIP client constitute an 'identity set'.  In this
           case, registering the single SIP client implicitly
           registers the identities of all associated lines.
        
           : - In the case where the client does not register
           with the network ({{param|RegisterMode}} is
           {{enum|STATIC|RegisterMode}}), multiple lines can be
           associated with each SIP client.";
        leaf Enable {
          type boolean;
          default "false";
          description
            "Enable or disable this client.";
        }
        leaf QuiescentMode {
          type boolean;
          description
            "If {{true}}, when {{param|Enable}} is set to {{false}}
             in-progress sessions remain intact, but no new
             sessions are allowed.  When all sessions are
             terminated, the {{object}} is disabled.";
        }
        leaf Status {
          type enumeration {
            enum "Up";
            enum "Initializing";
            enum "Registering";
            enum "Deregistering";
            enum "Error_Misconfigured";
            enum "Error_Network";
            enum "Error_Registration";
            enum "Quiescent";
            enum "Disabled";
          }
          config false;
          default "Disabled";
          description
            "Indicates the status of this client.  Unless noted
             otherwise, the status values apply to both
             registering and non-registering clients.";
        }
        leaf Origin {
          type enumeration {
            enum "AutoConfigured";
            enum "Static";
          }
          config false;
          default "Static";
          description
            "Mechanism via which this instance was assigned.
             {{enum}}";
        }
        leaf RegisterMode {
          type enumeration {
            enum "RFC3261";
            enum "STATIC";
            enum "RFC6140";
            enum "TISPAN";
          }
          description
            "The registration procedures to apply.  For {{param}}
             values other than {{enum|STATIC}}, the SIP
             {{object|#}} conveys its RegisterURI-to-ContactURI
             binding to the network using the SIP registration
             procedure.  For the {{param}} value of
             {{enum|STATIC}}, the SIP client
             RegisterURI-to-ContactURI binding is conveyed to the
             network via some out-of-band mechanism not defined
             by this data model.
          
             This parameter can only be modified if
             {{param|Origin}} is {{enum|Static|Origin}}.";
        }
        leaf AuthUserName {
          type string {
            length "0..128";
          }
          default "";
          description
            "Username used to authenticate the connection to the
             server.
          
             This parameter can only be modified if
             {{param|Origin}} is {{enum|Static|Origin}}.";
        }
        leaf AuthPassword {
          type string {
            length "0..128";
          }
          default "";
          description
            "Password used to authenticate the connection to the
             server.
          
             This parameter can only be modified if
             {{param|Origin}} is {{enum|Static|Origin}}.";
        }
        leaf Network {
          type string {
            length "0..256";
          }
          description
            "SIP network with which this SIP client is associated.
          
             {{reference}}
          
             This parameter can only be modified if
             {{param|Origin}} is {{enum|Static|Origin}}.";
        }
        leaf MaxSessions {
          type uint32;
          default "0";
          description
            "Limit on the number of simultaneous voice sessions
             across this client.  This MUST be less than or equal
             to {{param|.Capabilities.MaxSessionCount}}.
          
             A value of zero indicates no explicit limit on the
             number of sessions.";
        }
        leaf RegisterURI {
          type string {
            length "0..389";
          }
          default "";
          description
            "The SIP URI that represents the identity of this SIP
             client.  For {{param|RegisterMode}} values where the
             SIP client registers with the network, this SIP URI
             is placed in the From and To headers in the REGISTER
             request.
          
             This parameter can only be modified if
             {{param|Origin}} is {{enum|Static|Origin}}.";
        }
        leaf E164Format {
          type boolean;
          default "true";
          description
            "When {{true}} and using a {{object|.Trunk}}, the SIP
             URIs built from the directory numbers in
             {{param|.Trunk.{i}.DDIRange}} SHOULD use E.164
             format, using the \"user=phone\" URI parameter,
             according to {{bibref|RFC3261|section 19.1.6}}.";
        }
        leaf T38Enable {
          type boolean;
          description
            "Enable or disable the use of T.38.";
        }

        list Contact {
          key "Alias";
          description
            "Active registrations for this SIP account.";
          leaf Enable {
            type boolean;
            default "false";
            description
              "Enable or disable this {{object}}.";
          }
          leaf Status {
            type enumeration {
              enum "Up";
              enum "Error";
              enum "Disabled";
            }
            config false;
            default "Disabled";
            description
              "Indicates the status of this {{object}}.";
          }
          leaf Origin {
            type enumeration {
              enum "AutoConfigured";
              enum "Static";
            }
            config false;
            default "Static";
            description
              "Mechanism via which this {{object}} was assigned.
               {{enum}}";
          }
          leaf IPAddress {
            type types:IPAddress;
            description
              "This is the IP address where the {{object|#}} is
               listening for SIP requests from the service
               provider network.  This IP address value is
               populated in the host portion of the
               {{param|ContactURI}} parameter.
            
               This parameter can only be modified if
               {{param|Origin}} is {{enum|Static|Origin}}.";
          }
          leaf Port {
            type uint32 {
              range "0..65535";
            }
            description
              "This is the port where the {{object|#}} is listening
               for SIP requests from the service provider
               network.  This IP port value is populated in the
               port portion of the {{param|ContactURI}}
               parameter.
            
               This parameter can only be modified if
               {{param|Origin}} is {{enum|Static|Origin}}.";
          }
          leaf ContactURI {
            type string {
              length "0..256";
            }
            default "";
            description
              "The current Contact URI of the {{object|#}}.
            
               If SIP registration procedures are being used, as
               determined by the {{param|#.RegisterMode}}
               parameter, then this parameter is populated in the
               Contact header field of the REGISTER request.
            
               This parameter can only be modified if
               {{param|Origin}} is {{enum|Static|Origin}}.";
          }
          leaf ExpireTime {
            type yang:date-and-time;
            config false;
            description
              "Time when this registration will expire.  This
               parameter is valid only when SIP registration
               procedures are being used, as determined by the
               {{param|#.RegisterMode}} parameter.
            
               If this registration never expires, this parameter
               SHOULD be set to the Unknown Time value.";
          }
          leaf PingInterval {
            type uint32 {
              range "0..65535";
            }
            description
              "The interval in {{units}} between sending a periodic
               ping request toward the network (i.e.  a SIP
               OPTIONS ping).  The CPE performs the periodic ping
               request to verify connectivity with the network
               when SIP registration procedures are not used
               (i.e.  when the SIP client
               {{param|#.RegisterMode}} is
               {{enum|STATIC|#.RegisterMode}}).  A value of '0'
               indicates that the CPE should not perform the
               periodic ping request.";
          }
          leaf UserAgent {
            type string {
              length "0..256";
            }
            config false;
            description
              "This is the User-Agent field reported in the SIP
               header of the REGISTER message.";
          }
        }

        list EventSubscribe {
          key "Event";
          description
            "Table of SIP events automatically populated by the CPE
             with each of the SIP event subscriptions in
             {{object|.SIP.Network.{i}.EventSubscribe.{i}.}}.
             This table allows specification of the
             authentication credentials needed for each event
             subscription.";
          leaf Enable {
            type boolean;
            default "false";
            description
              "Enables or disables this entry.";
          }
          leaf Event {
            type string {
              length "0..32";
            }
            config false;
            description
              "SIP event name corresponding to the value given in
               {{object|.SIP.Network.{i}.EventSubscribe.{i}.}}.";
          }
          leaf AuthUserName {
            type string {
              length "0..128";
            }
            default "";
            description
              "Username used to authenticate the connection to the
               event notify server.";
          }
          leaf AuthPassword {
            type string {
              length "0..128";
            }
            default "";
            description
              "Password used to authenticate the connection to the
               event notify server.";
          }
        }
      }

      list Network {
        key "Alias";
        description
          "This object models a SIP network (a network as described
           in {{bibref|TR-104i2|Section 4.2}}).  SIP networks are
           used by SIP {{object|#.Client}} objects so that common
           parameters do not have to be provisioned multiple
           times.";
        leaf Enable {
          type boolean;
          default "false";
          description
            "Enable or disable this {{object}}.  Starts the DNS
             resolving when enabled.";
        }
        leaf QuiescentMode {
          type boolean;
          description
            "If {{true}}, when {{param|Enable}} is set to {{false}}
             in-progress sessions remain intact, but no new
             sessions are allowed.  When all sessions are
             terminated, the {{object}} is disabled.";
        }
        leaf Status {
          type enumeration {
            enum "Up";
            enum "Resolving";
            enum "Error_DNS";
            enum "Error_Other";
            enum "Disabled";
          }
          config false;
          default "Disabled";
          description
            "Indicates the status of this network.";
        }
        leaf ProxyServer {
          type string {
            length "0..256";
          }
          default "";
          description
            "Host name or IP address of the SIP proxy server.
          
             If not {{empty}}, all SIP signaling traffic MUST be
             sent to the host indicated by this parameter and the
             port indicated by {{param|ProxyServerPort}} unless
             {{param|OutboundProxy}} is not {{empty}} or a
             different route was discovered during normal SIP
             routing operations.
          
             Regardless of which host the traffic gets sent to
             ({{param}} or {{param|OutboundProxy}}), the value of
             this parameter (unless {{empty}}) MUST be used to
             derive the URI placed into the SIP Route header
             field of all requests originated by this end-point,
             unless a different proxy host was discovered
             dynamically during normal SIP routing operations.";
        }
        leaf ProxyServerPort {
          type uint32 {
            range "0..65535";
          }
          default "5060";
          description
            "Destination port to be used in connecting to the SIP
             proxy server.";
        }
        leaf ProxyServerTransport {
          type enumeration {
            enum "UDP";
            enum "TCP";
            enum "TLS";
            enum "SCTP";
          }
          default "UDP";
          description
            "Transport protocol to be used in connecting to the SIP
             proxy server.";
        }
        leaf RegistrarServer {
          type string {
            length "0..256";
          }
          default "";
          description
            "Host name or IP address of the SIP registrar server.
          
             If this parameter is {{empty}}, the CPE MUST obtain
             all of the registrar server configuration
             information, including host name or IP address,
             port, and transport protocol, from the values in
             {{param|ProxyServer}}, {{param|ProxyServerPort}},
             and {{param|ProxyServerTransport}}.";
        }
        leaf RegistrarServerPort {
          type uint32 {
            range "0..65535";
          }
          default "5060";
          description
            "Destination port to be used in connecting to the SIP
             registrar server.
          
             If {{param|RegistrarServer}} is empty the CPE MUST
             obtain all of the registrar server configuration
             information, including host name or IP address,
             port, and transport protocol, from the values in
             {{param|ProxyServer}}, {{param|ProxyServerPort}},
             and {{param|ProxyServerTransport}}.";
        }
        leaf RegistrarServerTransport {
          type enumeration {
            enum "UDP";
            enum "TCP";
            enum "TLS";
            enum "SCTP";
          }
          default "UDP";
          description
            "Transport protocol to be used in connecting to the
             registrar server.  {{enum}}
          
             If {{param|RegistrarServer}} is empty the CPE MUST
             obtain all of the registrar server configuration
             information, including host name or IP address,
             port, and transport protocol, from the values in
             {{param|ProxyServer}}, {{param|ProxyServerPort}},
             and {{param|ProxyServerTransport}}.";
        }
        leaf ServerDomain {
          type string {
            length "0..256";
          }
          default "";
          description
            "If non-empty this {{param}} is used by the devices in a
             DNS SRV request to provide FQDNs
             {{object|FQDNServer.{i}.}} for SIP Server
             connections.
          
             {{bibref|RFC2782}} ''Clients ask for a specific
             service/protocol for a specific domain (the word
             domain is used here in the strict RFC 1034 sense),
             and get back the names of any available servers.''";
        }
        leaf ChosenDomain {
          type string {
            length "0..256";
          }
          config false;
          default "";
          description
            "Domain used by {{object|#.Client}} objects that
             reference this {{object}} instance.";
        }
        leaf ChosenIPAddress {
          type types:IPAddress;
          config false;
          description
            "IP address used to reach the {{param|ChosenDomain}}.";
        }
        leaf ChosenPort {
          type uint32 {
            range "0..65535";
          }
          config false;
          description
            "Port used to reach the {{param|ChosenDomain}}.";
        }
        leaf UserAgentDomain {
          type string {
            length "0..256";
          }
          default "";
          description
            "CPE domain string.  If {{empty}}, the CPE SHOULD use
             its IP address as the domain.";
        }
        leaf UserAgentPort {
          type uint32 {
            range "0..65535";
          }
          default "0";
          description
            "Port used for incoming call control signaling.";
        }
        leaf UserAgentTransport {
          type enumeration {
            enum "UDP";
            enum "TCP";
            enum "TLS";
            enum "SCTP";
          }
          default "UDP";
          description
            "Transport protocol to be used for incoming call control
             signaling.";
        }
        leaf OutboundProxy {
          type string {
            length "0..256";
          }
          default "";
          description
            "The Fully Qualified Domain Name (FQDN) or IP Address of
             the outbound proxy.  If the value is not {{empty}},
             the SIP endpoint MUST send all SIP traffic (requests
             and responses) to the host indicated by this
             parameter and the port indicated by
             {{param|OutboundProxyPort}}.  This MUST be done
             regardless of the routes discovered using normal SIP
             operations, including use of Route headers
             initialized from Service-Route and Record-Route
             headers previously received.  {{param}} is NOT used
             to generate the URI placed into the Route header of
             any requests.
          
             When {{param}} is assigned, the name is looked up
             (resolved) and the corresponding address is set in
             {{param|OutboundProxyResolvedAddress}}.";
        }
        leaf OutboundProxyResolvedAddress {
          type types:IPAddress;
          config false;
          description
            "The IP address of the outbound proxy.
          
             This parameter can be assigned statically (e.g.
             present in the factory default configuration or set
             by the ACS via {{param|OutboundProxy}}) or assigned
             dynamically (via DHCP).
          
             When {{param|OutboundProxy}} is assigned, the name
             is looked up (resolved) and the corresponding
             address is set in {{param}}.";
        }
        leaf OutboundProxyPrecedence {
          type enumeration {
            enum "Static";
            enum "DHCP";
          }
          config false;
          description
            "Indicates whether it is the static configuration or the
             DHCP configuration that is actually used for
             {{param|OutboundProxyResolvedAddress}}.";
        }
        leaf OutboundProxyPort {
          type uint32 {
            range "0..65535";
          }
          default "5060";
          description
            "Destination port to be used in connecting to the
             outbound proxy.  This parameter MUST be ignored
             unless the value of {{param|OutboundProxy}} is
             non-empty.";
        }
        leaf STUNEnable {
          type boolean;
          default "false";
          description
            "Enable or disable use of STUN to allow operation
             through NAT.  Note: enabling STUN is to be
             interpreted as enabling the use of STUN for
             discovery, not use as a keep-alive mechanism.";
        }
        leaf STUNServer {
          type string {
            length "0..256";
          }
          default "";
          description
            "Domain name or IP address of the STUN server.";
        }
        leaf NonVoiceBandwidthReservedUpstream {
          type uint32;
          default "0";
          description
            "For bandwidth-based admission control, a session can
             proceed only if there is {{param}} {{units}} of
             upstream bandwidth left available for non-voice
             traffic.  This parameter is appropriate only in
             implementations in which the actual bandwidth can be
             known, such as a VoIP device embedded in a DSL B-NT.";
        }
        leaf NonVoiceBandwidthReservedDownstream {
          type uint32;
          default "0";
          description
            "For bandwidth-based admission control, a session can
             proceed only if there is {{param}} {{units}} of
             downstream bandwidth left available for non-voice
             traffic.  This parameter is appropriate only in
             implementations in which the actual bandwidth can be
             known, such as a VoIP device embedded in a DSL B-NT.";
        }
        leaf Organization {
          type string {
            length "0..256";
          }
          default "";
          description
            "Text string to be used in the Organization header.";
        }
        leaf RegistrationPeriod {
          type uint32 {
            range "1..max";
          }
          description
            "Duration, in {{units}}, after which the user agent
             needs to register again.";
        }
        leaf Realm {
          type string;
          description
            "Realm for authentication with the specified values of
             {{param|#.Client.{i}.AuthUserName}} and
             {{param|#.Client.{i}.AuthPassword}}.";
        }
        leaf TimerT1 {
          type uint32 {
            range "1..max";
          }
          description
            "Value of SIP timer T1, in {{units}}, as defined in
             {{bibref|RFC3261}}.";
        }
        leaf TimerT2 {
          type uint32 {
            range "1..max";
          }
          description
            "Value of SIP timer T2, in {{units}}, as defined in
             {{bibref|RFC3261}}.";
        }
        leaf TimerT4 {
          type uint32 {
            range "1..max";
          }
          description
            "Value of SIP timer T4, in {{units}}, as defined in
             {{bibref|RFC3261}}.";
        }
        leaf TimerA {
          type uint32 {
            range "1..max";
          }
          description
            "Value of SIP timer A, in {{units}}, as defined in
             {{bibref|RFC3261}}.";
        }
        leaf TimerB {
          type uint32 {
            range "1..max";
          }
          description
            "Value of SIP timer B, in {{units}}, as defined in
             {{bibref|RFC3261}}.";
        }
        leaf TimerC {
          type uint32 {
            range "1..max";
          }
          description
            "Value of SIP timer C, in {{units}}, as defined in
             {{bibref|RFC3261}}.";
        }
        leaf TimerD {
          type uint32 {
            range "1..max";
          }
          description
            "Value of SIP timer D, in {{units}}, as defined in
             {{bibref|RFC3261}}.";
        }
        leaf TimerE {
          type uint32 {
            range "1..max";
          }
          description
            "Value of SIP timer E, in {{units}}, as defined in
             {{bibref|RFC3261}}.";
        }
        leaf TimerF {
          type uint32 {
            range "1..max";
          }
          description
            "Value of SIP timer F, in {{units}}, as defined in
             {{bibref|RFC3261}}.";
        }
        leaf TimerG {
          type uint32 {
            range "1..max";
          }
          description
            "Value of SIP timer G, in {{units}}, as defined in
             {{bibref|RFC3261}}.";
        }
        leaf TimerH {
          type uint32 {
            range "1..max";
          }
          description
            "Value of SIP timer H, in {{units}}, as defined in
             {{bibref|RFC3261}}.";
        }
        leaf TimerI {
          type uint32 {
            range "1..max";
          }
          description
            "Value of SIP timer I, in {{units}}, as defined in
             {{bibref|RFC3261}}.";
        }
        leaf TimerJ {
          type uint32 {
            range "1..max";
          }
          description
            "Value of SIP timer J, in {{units}}, as defined in
             {{bibref|RFC3261}}.";
        }
        leaf TimerK {
          type uint32 {
            range "1..max";
          }
          description
            "Value of SIP timer K, in {{units}}, as defined in
             {{bibref|RFC3261}}.";
        }
        leaf InviteExpires {
          type uint32 {
            range "1..max";
          }
          description
            "Invite request Expires header value, in {{units}}.";
        }
        leaf ReInviteExpires {
          type uint32 {
            range "1..max";
          }
          description
            "Re-invite request Expires header value, in {{units}}.";
        }
        leaf RegisterExpires {
          type uint32 {
            range "1..max";
          }
          description
            "Register request Expires header value, in {{units}}.";
        }
        leaf RegisterRetryInterval {
          type uint32 {
            range "1..max";
          }
          description
            "Register retry interval, in {{units}}.";
        }
        leaf InboundAuth {
          type enumeration {
            enum "None";
            enum "Digest";
            enum "SourceFilter";
          }
          default "None";
          description
            "Applicable inbound authentication method, if any.";
        }
        leaf InboundAuthUsername {
          type string {
            length "0..256";
          }
          default "";
          description
            "If inbound authentication is used, the username
             credentials.";
        }
        leaf InboundAuthPassword {
          type string {
            length "0..256";
          }
          default "";
          description
            "If inbound authentication is used, the password
             credentials.";
        }
        leaf UseCodecPriorityInSDPResponse {
          type boolean;
          default "false";
          description
            "When {{true}}, in the SDP included in an OK response to
             an Invite, the first listed codec MUST be the
             highest priority codec among those offered in the
             Invite, based on the priorities specified in
             {{param|CodecList}}.  The list of codecs in the SDP
             MAY also include other lower priority codecs.
          
             When {{false}}, there is no specific requirement for
             choosing the codecs listed in the SDP included in an
             OK response.";
        }
        leaf DSCPMark {
          type uint32 {
            range "0..63";
          }
          default "0";
          description
            "Diffserv code point to be used for outgoing SIP
             signaling packets.";
        }
        leaf VLANIDMark {
          type int32 {
            range "-1..max";
          }
          default "-1";
          description
            "VLAN ID (as defined in {{bibref|802.1Q-2005}}) to be
             used for outgoing SIP signaling packets for this
             network.  A value of -1 indicates the default value
             is to be used.
          
             If either {{param}} or
             {{param|EthernetPriorityMark}} are greater than
             zero, then the outgoing frames MUST be tagged.
             Otherwise, the outgoing frames MAY be tagged or
             untagged.";
        }
        leaf EthernetPriorityMark {
          type int32 {
            range "-1..max";
          }
          default "-1";
          description
            "Ethernet priority code (as defined in
             {{bibref|802.1Q-2005}}) to be used for outgoing SIP
             signaling packets for this network.  A value of -1
             indicates the default value is to be used.
          
             If either {{param|VLANIDMark}} or {{param}} are
             greater than zero, then the outgoing frames MUST be
             tagged.  Otherwise, the outgoing frames MAY be
             tagged or untagged.";
        }
        leaf ConferenceCallDomainURI {
          type string {
            length "0..256";
          }
          description
            "URI of the network conference bridge for the multiway
             conference call service.";
        }
        leaf TimerLoginRejected {
          type uint32;
          description
            "In case of a 401 (Unauthorized) or a 407 (Proxy
             Authentication Required) response to a REGISTER
             request, the CPE shall send REGISTER using
             credentials.  If the second response is a new 401
             (Unauthorized) or a 407 (Proxy Authentication
             Required) with stale=false or no stale value, the
             CPE shall re-init registration cycle after
             expiration of this timer (in {{units}}).  If
             stale=true, the CPE shall send REGISTER using
             credentials.";
        }
        leaf NoLoginRetry {
          type boolean;
          description
            "If {{true}}, no retry after a 401 (Unauthorized) or a
             407 (Proxy Authentication Required) response to a
             REGISTER until power cycle or credentials have been
             changed.";
        }
        leaf TimerRegistrationFailed {
          type uint32;
          description
            "In case of no response to a REGISTER request, the CPE
             shall retry according to retransmission algorithm
             defined in {{bibref|RFC3261}}, then wait for
             expiration of this timer (in {{units}}).
          
             In case of other response, the CPE shall wait for
             expiration of this timer before sending a new
             REGISTER request.";
        }
        leaf TimerSubscriptionFailed {
          type uint32;
          description
            "When starting a MWI subscription, on response of a
             SUBSCRIBE request : in case of no response or other
             response than 200 or 423, the CPE shall retry
             according to retransmission algorithm defined in
             {{bibref|RFC3261}}, then wait for expiration of this
             timer (in {{units}}) before sending a new SUBSCRIBE
             request.";
        }
        leaf UnansweredRegistrationAttempts {
          type uint32;
          config false;
          description
            "The number of registration timeouts when trying to
             register the server.";
        }
        leaf VoIPProfile {
          type string {
            length "0..256";
          }
          description
            "VoIP profile to use with this {{object}}.
          
             {{reference}}";
        }
        leaf CodecList {
          type string;
          description
            "{{list}} {{reference}}
          
             The CPE SHOULD use the first enabled item in the
             list among those supported by the remote endpoint
             and consistent with the available bandwidth.";
        }
        leaf MaxSessions {
          type uint32;
          default "0";
          description
            "Limit on the number of simultaneous voice sessions
             across all {{object|.SIP.Client}} referencing this
             {{object}}.  This MUST be less than or equal to
             {{param|.Capabilities.MaxSessionCount}}.
          
             A value of zero indicates no explicit limit on the
             number of sessions.";
        }

        list FQDNServer {
          key "Domain";
          description
            "Table of Fully Qualified Domain Names for this
             {{object|#}} instance in order to connect to the SIP
             server as described in {{bibref|RFC2782}}.";
          leaf Enable {
            type boolean;
            default "false";
            description
              "Enables or disables this FQDN server.";
          }
          leaf Origin {
            type enumeration {
              enum "AutoConfigured";
              enum "Static";
            }
            config false;
            default "Static";
            description
              "Mechanism via which the FQDN server was assigned.";
          }
          leaf Domain {
            type string {
              length "0..256";
            }
            description
              "The domain name of the target host.  This parameter
               can only be modified if {{param|Origin}} is
               {{enum|Static|Origin}}.";
          }
          leaf Weight {
            type uint32 {
              range "0..65535";
            }
            default "0";
            description
              "A server selection mechanism.  The weight field
               specifies a relative weight for entries with the
               same priority.
            
               Larger weights SHOULD be given a proportionately
               higher probability of being selected.  This
               parameter can only be modified if {{param|Origin}}
               is {{enum|Static|Origin}}.";
          }
          leaf Priority {
            type uint32 {
              range "0..65535";
            }
            default "0";
            description
              "The priority of this target host.  A client MUST
               attempt to contact the target host with the
               lowest-numbered priority it can reach;
            
               target hosts with the same priority SHOULD be
               tried in an order defined by the weight field.
               This parameter can only be modified if
               {{param|Origin}} is {{enum|Static|Origin}}.";
          }
          leaf Port {
            type uint32 {
              range "0..65535";
            }
            description
              "The port on this target host of this service.";
          }
          leaf IPAddresses {
            type types:IPAddress;
            description
              "{{list|the IP Addresses that the FQDN resolves to}}
            
               The order in which the addresses appear in the
               list MAY imply priority.  This parameter MAY be
               modified by the ACS only if {{param|Origin}} is
               {{enum|Static|Origin}}.";
          }
        }

        list EventSubscribe {
          key "Event";
          description
            "Table to specify the SIP events to which the CPE MUST
             subscribe.";
          leaf Enable {
            type boolean;
            default "false";
            description
              "Enables or disables this entry.";
          }
          leaf Event {
            type string {
              length "0..32";
            }
            default "";
            description
              "SIP event name to appear in the EVENT header of the
               SIP SUBSCRIBE request.";
          }
          leaf Notifier {
            type string {
              length "0..256";
            }
            default "";
            description
              "Host name or IP address of the event notify server.";
          }
          leaf NotifierPort {
            type uint32 {
              range "0..65535";
            }
            default "0";
            description
              "Destination port to be used in connecting to the
               event notifier.";
          }
          leaf NotifierTransport {
            type enumeration {
              enum "UDP";
              enum "TCP";
              enum "TLS";
              enum "SCTP";
            }
            default "UDP";
            description
              "Transport protocol to be used in connecting to the
               event notifier.";
          }
          leaf ExpireTime {
            type uint32;
            description
              "Subscription refresh timer, in {{units}}.";
          }
        }

        list ResponseMap {
          key "SIPResponseNumber";
          description
            "Each entry in this table specifies the tone and message
             to be provided to the user for a particular SIP
             response received (normally 4xx and 5xx).";
          leaf SIPResponseNumber {
            type uint32 {
              range "101..999";
            }
            description
              "The SIP response code number.";
          }
          leaf Enable {
            type boolean;
            default "false";
            description
              "Enables or disables this entry.";
          }
          leaf TextMessage {
            type string {
              length "0..64";
            }
            default "";
            description
              "The message to be provided on the screen or display
               of the VoIP device when the SIP response is
               received.
            
               If this parameter is not {{empty}}, display of
               this text preempts the value of
               {{param|.Tone.Description.{i}.ToneText}}
               associated with {{param|Tone}}.  If this parameter
               is {{empty}}, the value of
               {{param|.Tone.Description.{i}.ToneText}}
               associated with {{param|Tone}}, if any, is
               displayed instead.
            
               This parameter is applicable only for VoIP devices
               capable of text display.";
          }
          leaf Tone {
            type string {
              length "0..256";
            }
            description
              "The tone to be played to the user when the SIP
               response is received.
            
               {{reference}}
            
               {{empty}} indicates no tone is to be played for
               this event.";
          }
        }
      }

      list Proxy {
        key "ProxyIPAddress ProxyPort";
        description
          "Global SIP parameters used by the CPE when acting as
           proxy for SIP user agents.";
        leaf Enable {
          type boolean;
          default "false";
          description
            "Enable or disable the proxy.";
        }
        leaf Status {
          type enumeration {
            enum "Up";
            enum "Error";
            enum "Disabled";
          }
          config false;
          default "Disabled";
          description
            "Indicates the status of this proxy.";
        }
        leaf Origin {
          type enumeration {
            enum "AutoConfigured";
            enum "Static";
          }
          config false;
          default "Static";
          description
            "Mechanism via which the IP address was assigned.
             {{enum}}";
        }
        leaf ProxyIPAddress {
          type types:IPAddress;
          description
            "The IP address the proxy listens on.
          
             This parameter can only be modified if
             {{param|Origin}} is {{enum|Static|Origin}}.";
        }
        leaf ProxyPort {
          type uint32 {
            range "0..65535";
          }
          description
            "The port the proxy listens on.";
        }
        leaf ContactURI {
          type string {
            length "0..256";
          }
          config false;
          description
            "Built by the CPE using {{param|ProxyIPAddress}} and
             {{param|ProxyPort}}.";
        }
        leaf VoIPProfile {
          type string {
            length "0..256";
          }
          description
            "VoIP profile to use with this proxy.
          
             {{reference}}";
        }
      }

      list Registrar {
        key "RegistrarPort RegistrarIPAddress";
        description
          "Global SIP parameters used by the CPE when acting as
           registrar server for externally connected SIP user
           agents.  This object also contains the global SIP
           parameters used by the CPE when it acts as static
           identity-to-location binding database for externally
           connected SIP user agents that don't register (i.e.
           static-mode SIP-PBX).";
        leaf Enable {
          type boolean;
          default "false";
          description
            "Enable or disable the registrar.";
        }
        leaf QuiescentMode {
          type boolean;
          description
            "If {{true}}, when {{param|Enable}} is set to {{false}}
             in-progress sessions remain intact, but no new
             sessions are allowed.  When all sessions are
             terminated, the {{object}} is disabled.";
        }
        leaf Status {
          type enumeration {
            enum "Up";
            enum "Error";
            enum "Disabled";
          }
          config false;
          default "Disabled";
          description
            "Indicates the status of this registrar.";
        }
        leaf Origin {
          type enumeration {
            enum "AutoConfigured";
            enum "Static";
          }
          config false;
          default "Static";
          description
            "Mechanism via which the IP address was assigned.
             {{enum}}";
        }
        leaf RegistrarIPAddress {
          type types:IPAddress;
          description
            "The IP address the registrar listens on for incoming
             SIP requests from an externally connected SIP user
             agent.
          
             This parameter can only be modified if
             {{param|Origin}} is {{enum|Static|Origin}}.";
        }
        leaf RegistrarPort {
          type uint32 {
            range "0..65535";
          }
          description
            "The port the registrar listens on.";
        }
        leaf RegisterExpires {
          type uint32;
          description
            "The minimum register expire time in {{units}}.  This
             parameter is valid only for SIP user agents that
             support registration.";
        }
        leaf PingInterval {
          type uint32 {
            range "0..65535";
          }
          description
            "The interval in {{units}} between sending a periodic
             ping request (e.g., a SIP OPTIONS ping) to
             externally connected SIP user agents.  The CPE
             performs the periodic ping request to verify
             connectivity with externally connected devices that
             do not support SIP registration procedures (i.e.  a
             static-mode SIP-PBX).  A value of 0 indicates that
             the CPE should not perform the periodic ping
             request.";
        }
        leaf Organization {
          type string {
            length "0..256";
          }
          default "";
          description
            "Text string to be used in the Organization header.";
        }
        leaf Realm {
          type string;
          description
            "Realm for authentication with the specified values of
             {{param|Account.{i}.AuthUserName}} and
             {{param|Account.{i}.AuthPassword}}.";
        }
        leaf VoIPProfile {
          type string {
            length "0..256";
          }
          description
            "VoIP profile to use with this registrar.
          
             {{reference}}";
        }
        leaf ContactURI {
          type string {
            length "0..256";
          }
          config false;
          description
            "Built by the CPE using {{param|RegistrarIPAddress}} and
             {{param|RegistrarPort}}.";
        }

        list Account {
          key "URI";
          description
            "SIP account table.";
          leaf Enable {
            type enumeration {
              enum "Enable";
              enum "Quiescent";
              enum "Disable";
            }
            default "Disable";
            description
              "Enables or disables this account, or places it into a
               quiescent state.  {{enum}}
            
               In the {{enum|Quiescent}} state, in-progress
               sessions remain intact, but no new sessions are
               allowed.  If this parameter is set to
               {{enum|Quiescent}} in a CPE that does not support
               the {{enum|Quiescent}} state, it MUST treat it the
               same as the {{enum|Disable}} state (and indicate
               {{enum|Disabled|Status}} in {{param|Status}}).";
          }
          leaf QuiescentMode {
            type boolean;
            description
              "If {{true}}, when {{param|Enable}} is set to
               {{false}} in-progress sessions remain intact, but
               no new sessions are allowed.  When all sessions
               are terminated, the {{object}} is disabled.";
          }
          leaf Status {
            type enumeration {
              enum "Up";
              enum "Initializing";
              enum "Registering";
              enum "Deregistering";
              enum "ErrorMisconfigured";
              enum "ErrorNetwork";
              enum "ErrorRegistration";
              enum "Quiescent";
              enum "Disabled";
            }
            config false;
            default "Disabled";
            description
              "Indicates the status of this account.  Unless noted
               otherwise, the {{param}} values apply to both
               registering and non-registering external SIP user
               agents.";
          }
          leaf Origin {
            type enumeration {
              enum "AutoConfigured";
              enum "Static";
            }
            config false;
            default "Static";
            description
              "Mechanism via which the {{object}} was created.
               {{enum}}";
          }
          leaf CallStatus {
            type enumeration {
              enum "Idle";
              enum "Dialing";
              enum "Delivered";
              enum "Connected";
              enum "Alerting";
              enum "Disconnected";
            }
            config false;
            description
              "Indicates the call status for this account.";
          }
          leaf AuthUserName {
            type string {
              length "0..128";
            }
            default "";
            description
              "Username used to authenticate the connection to the
               registrar server.
            
               This parameter can only be modified if
               {{param|Origin}} is Static.";
          }
          leaf AuthPassword {
            type string {
              length "0..128";
            }
            default "";
            description
              "Password used to authenticate the connection to the
               registrar server.
            
               This parameter can only be modified if
               {{param|Origin}} is Static.";
          }
          leaf RegistrationStatus {
            type enumeration {
              enum "Registered";
              enum "Unregistered";
            }
            config false;
            description
              "The current registration status of the externally
               connected SIP user agent.  This parameter is valid
               only for SIP user agents that support
               registration.";
          }
          leaf URI {
            type string {
              length "0..389";
            }
            description
              "The URI (AoR) of the externally connected SIP user
               agent.  For SIP user agents that register, this is
               the URI that is contained in the To header field
               of the incoming REGISTER request.
            
               This parameter can only be modified if
               {{param|Origin}} is {{enum|Static|Origin}}.";
          }
          leaf Domain {
            type string {
              length "0..256";
            }
            description
              "The domain name used when the SIP user agent has
               registered itself.
            
               This parameter can only be modified if
               {{param|Origin}} is {{enum|Static|Origin}}.";
          }
          leaf CodecList {
            type string;
            description
              "{{list}} {{reference}}
            
               The CPE SHOULD use the first enabled item in the
               list among those supported by the remote endpoint
               and consistent with the available bandwidth.";
          }
          leaf VoIPProfile {
            type string {
              length "0..256";
            }
            description
              "Voice profile to use with this {{object}}.
            
               {{reference}}";
          }

          list Contact {
            key "Alias";
            description
              "Active registrations for this SIP account.";
            leaf Enable {
              type boolean;
              default "false";
              description
                "Enable or disable this entry.";
            }
            leaf Status {
              type enumeration {
                enum "Up";
                enum "Error";
                enum "Disabled";
              }
              config false;
              default "Disabled";
              description
                "Indicates the status of this entry.";
            }
            leaf Origin {
              type enumeration {
                enum "AutoConfigured";
                enum "Static";
              }
              config false;
              default "Static";
              description
                "Mechanism via which the {{object}} was assigned.
                 {{enum}}";
            }
            leaf IPAddress {
              type types:IPAddress;
              description
                "IP Address of the externally connected SIP user
                 agent.  This is the IP address contained in the
                 {{param|ContactURI}} parameter.
              
                 This parameter can only be modified if
                 {{param|Origin}} is {{enum|Static|Origin}}.";
            }
            leaf Port {
              type uint32 {
                range "0..65535";
              }
              description
                "The port of the externally connected SIP user
                 agent.  This is the port contained in the
                 {{param|ContactURI}} parameter.
              
                 This parameter can only be modified if
                 {{param|Origin}} is {{enum|Static|Origin}}.";
            }
            leaf ContactURI {
              type string {
                length "0..256";
              }
              description
                "This is the SIP signaling address of the externally
                 connected SIP user agent.  If the SIP user agent
                 registers, then {{param}} is the Contact URI
                 contained in the Contact header field of the
                 REGISTER request received from the SIP user
                 agent.  If the SIP user agent does not register,
                 then the {{param}} is provisioned by the ACS.
              
                 This parameter can only be modified if
                 {{param|Origin}} is {{enum|Static|Origin}}.";
            }
            leaf ExpireTime {
              type yang:date-and-time;
              config false;
              description
                "Time when this registration will expire.  This
                 parameter is valid only for external SIP user
                 agents that register.
              
                 If this registration never expires, this
                 parameter SHOULD be set to the Unknown Time
                 value.";
            }
            leaf UserAgent {
              type string {
                length "0..64";
              }
              description
                "This parameter defines the User-Agent header that
                 will be used by the SIP messages send by this
                 user agent.  Implementers SHOULD make the
                 User-Agent header field a configurable option.";
            }
          }
        }
      }
    }

    container MGCP {
      description
        "This object is dedicated to MGCP as defined in
         {{bibref|RFC3435}}.  It models MGCP clients and
         networks.";

      list Client {
        key "Alias";
        description
          "MGCP client table (a client as described in
           {{bibref|TR-104i2|Section 4.2}}).  Each MGCP client
           maintains a registration for the MGCP identities of
           the associated line with the {{object|#.Network}}.";
        leaf Enable {
          type boolean;
          default "false";
          description
            "Enable or disable this client.";
        }
        leaf QuiescentMode {
          type boolean;
          description
            "If {{true}}, when {{param|Enable}} is set to {{false}}
             in-progress sessions remain intact, but no new
             sessions are allowed.  When all sessions are
             terminated, the {{object}} is disabled.";
        }
        leaf Status {
          type enumeration {
            enum "Up";
            enum "Initializing";
            enum "Registering";
            enum "Deregistering";
            enum "Error_Misconfigured";
            enum "Error_Network";
            enum "Error_Registration";
            enum "Quiescent";
            enum "Disabled";
          }
          config false;
          default "Disabled";
          description
            "Indicates the status of this client.";
        }
        leaf RegisterMode {
          type enumeration {
            enum "Wildcard";
            enum "Individual";
          }
          default "Wildcard";
          description
            "Register mode.";
        }
        leaf LocalPort {
          type uint32 {
            range "0..65535";
          }
          default "0";
          description
            "Port listening for incoming call control signaling.";
        }
        leaf Domain {
          type string {
            length "0..256";
          }
          default "";
          description
            "CPE domain string.  If {{empty}}, the CPE SHOULD use
             its IP address.";
        }
        leaf User {
          type string {
            length "0..64";
          }
          default "";
          description
            "User string used in accessing the call agent.";
        }
        leaf Network {
          type string {
            length "0..256";
          }
          description
            "MGCP network with which this MGCP client is associated.
          
             {{reference}}";
        }
        leaf MaxSessions {
          type uint32;
          default "0";
          description
            "Limit on the number of simultaneous voice sessions
             across this {{object}}.  This MUST be less than or
             equal to {{param|.Capabilities.MaxSessionCount}}.
          
             A value of zero indicates no explicit limit on the
             number of sessions.";
        }
      }

      list Network {
        key "Alias";
        description
          "This object models a MGCP network (a network as described
           in {{bibref|TR-104i2|Section 4.2}}).";
        leaf Enable {
          type boolean;
          default "false";
          description
            "Enable or disable the {{object}}.  Starts the DNS
             resolving when enabled.";
        }
        leaf QuiescentMode {
          type boolean;
          description
            "If {{true}}, when {{param|Enable}} is set to {{false}}
             in-progress sessions remain intact, but no new
             sessions are allowed.  When all sessions are
             terminated, the {{object}} is disabled.";
        }
        leaf Status {
          type enumeration {
            enum "Up";
            enum "Resolving";
            enum "Error_DNS";
            enum "Error_Other";
            enum "Disabled";
          }
          config false;
          default "Disabled";
          description
            "Indicates the status of this {{object}}.";
        }
        leaf CallAgent1 {
          type string {
            length "0..256";
          }
          default "";
          description
            "Host name or IP address of the main MGCP call agent.";
        }
        leaf CallAgentPort1 {
          type uint32 {
            range "0..65535";
          }
          default "0";
          description
            "Destination port to be used in connecting with the main
             MGCP call agent.";
        }
        leaf CallAgent2 {
          type string {
            length "0..256";
          }
          default "";
          description
            "Host name or IP address of the backup MGCP call agent.";
        }
        leaf CallAgentPort2 {
          type uint32 {
            range "0..65535";
          }
          default "0";
          description
            "Destination port to be used in connecting with the
             backup MGCP call agent.";
        }
        leaf RetranIntervalTimer {
          type uint32 {
            range "0..65535";
          }
          default "1";
          description
            "Message retransfer interval, in {{units}}.";
        }
        leaf MaxRetranCount {
          type uint32 {
            range "0..65535";
          }
          default "10";
          description
            "Max number of message retransfers.";
        }
        leaf DSCPMark {
          type uint32 {
            range "0..63";
          }
          description
            "Diffserv code point to be used for outgoing MGCP
             signaling packets.";
        }
        leaf VLANIDMark {
          type int32 {
            range "-1..max";
          }
          default "-1";
          description
            "VLAN ID (as defined in {{bibref|802.1Q-2005}}) to be
             used for outgoing MGCP signaling packets for this
             network.  A value of -1 indicates the default value
             is to be used.
          
             If either {{param}} or
             {{param|EthernetPriorityMark}} are greater than
             zero, then the outgoing frames MUST be tagged.
             Otherwise, the outgoing frames MAY be tagged or
             untagged.";
        }
        leaf EthernetPriorityMark {
          type int32 {
            range "-1..max";
          }
          default "-1";
          description
            "Ethernet priority code (as defined in
             {{bibref|802.1D-2004}}) to be used for outgoing MGCP
             signaling packets for this network.  A value of -1
             indicates the default value is to be used.
          
             If either {{param|VLANIDMark}} or {{param}} are
             greater than zero, then the outgoing frames MUST be
             tagged.  Otherwise, the outgoing frames MAY be
             tagged or untagged.";
        }
        leaf AllowPiggybackEvents {
          type boolean;
          description
            "Indicates whether or not piggyback events are allowed
             to the MGCP call agent.";
        }
        leaf SendRSIPImmediately {
          type boolean;
          description
            "Indicates whether or not to send RSIP immediately on
             restart.";
        }
        leaf STUNEnable {
          type boolean;
          default "false";
          description
            "Enable or disable use of STUN to allow operation
             through NAT.  Note: enabling STUN is to be
             interpreted as enabling the use of STUN for
             discovery, not use as a keep-alive mechanism.";
        }
        leaf STUNServer {
          type string {
            length "0..256";
          }
          default "";
          description
            "Domain name or IP address of the STUN server.";
        }
        leaf NonVoiceBandwidthReservedUpstream {
          type uint32;
          default "0";
          description
            "For bandwidth-based admission control, a session can
             proceed only if there is {{param}} {{units}} of
             upstream bandwidth left available for non-voice
             traffic.  This parameter is appropriate only in
             implementations in which the actual bandwidth can be
             known, such as a VoIP device embedded in a DSL B-NT.";
        }
        leaf NonVoiceBandwidthReservedDownstream {
          type uint32;
          default "0";
          description
            "For bandwidth-based admission control, a session can
             proceed only if there is {{param}} {{units}} of
             downstream bandwidth left available for non-voice
             traffic.  This parameter is appropriate only in
             implementations in which the actual bandwidth can be
             known, such as a VoIP device embedded in a DSL B-NT.";
        }
        leaf MaxSessions {
          type uint32;
          default "0";
          description
            "Limit on the number of simultaneous voice sessions
             across all {{object|.MGCP.Client.}} referencing this
             {{object}}.  This MUST be less than or equal to
             {{param|.Capabilities.MaxSessionCount}}.
          
             A value of zero indicates no explicit limit on the
             number of sessions.";
        }
        leaf VoIPProfile {
          type string {
            length "0..256";
          }
          description
            "VoIP profile to use with this network.
          
             {{reference}}";
        }
        leaf CodecList {
          type string;
          description
            "{{list}} {{reference}}
          
             The CPE SHOULD use the first enabled item in the
             list among those supported by the remote endpoint
             and consistent with the available bandwidth.";
        }
      }
    }

    container H323 {
      description
        "This object is dedicated to H.323 as defined in
         {{bibref|H.323}}.  It models H.323 clients and networks.";

      list Client {
        key "Alias";
        description
          "H.323 client table (a client as described in
           {{bibref|TR-104i2|Section 4.2}}).  Each H.323 client
           maintains a registration for the H.323 identities of
           the associated line with the {{object|#.Network}}.";
        leaf Enable {
          type boolean;
          default "false";
          description
            "Enable or disable this client.";
        }
        leaf QuiescentMode {
          type boolean;
          description
            "If {{true}}, when {{param|Enable}} is set to {{false}}
             in-progress sessions remain intact, but no new
             sessions are allowed.  When all sessions are
             terminated, the {{object}} is disabled.";
        }
        leaf Status {
          type enumeration {
            enum "Up";
            enum "Initializing";
            enum "Registering";
            enum "Deregistering";
            enum "Error_Misconfigured";
            enum "Error_Network";
            enum "Error_Registration";
            enum "Quiescent";
            enum "Disabled";
          }
          config false;
          default "Disabled";
          description
            "Indicates the status of this client.";
        }
        leaf H235Authentication {
          type boolean;
          default "false";
          description
            "Enables or disables usage of H.235 security baseline
             security profile as defined in {{bibref|H.235.1}}.";
        }
        leaf AuthPassword {
          type string;
          default "";
          description
            "Password to be used when H.235 is enabled.";
        }
        leaf SendersID {
          type string;
          default "";
          description
            "In ITU-T based H.235 authentication, the sendersID is
             the ID of the gateway as received from the
             Gatekeeper.  As long as the endpointID is not
             received from the Gatekeeper, the sendersID will be
             applied as configured here.  The generalID is the
             GatekeeperID.";
        }
        leaf Network {
          type string {
            length "0..256";
          }
          description
            "H.323 network with which this H.323 client is
             associated.
          
             {{reference}}";
        }
        leaf H323ID {
          type string {
            length "0..32";
          }
          default "";
          description
            "The H.323 ID assigned to the client.";
        }
        leaf MaxSessions {
          type uint32;
          default "0";
          description
            "Limit on the number of simultaneous voice sessions
             across this {{object}}.  This MUST be less than or
             equal to {{param|.Capabilities.MaxSessionCount}}.
          
             A value of zero indicates no explicit limit on the
             number of sessions.";
        }
      }

      list Network {
        key "Alias";
        description
          "This object models a H.323 network (a network as
           described in {{bibref|TR-104i2|Section 4.2}}).";
        leaf Enable {
          type boolean;
          default "false";
          description
            "Enable or disable this {{object}}.  Starts the DNS
             resolving when enabled.";
        }
        leaf QuiescentMode {
          type boolean;
          description
            "If {{true}}, when {{param|Enable}} is set to {{false}}
             in-progress sessions remain intact, but no new
             sessions are allowed.  When all sessions are
             terminated, the {{object}} is disabled.";
        }
        leaf Status {
          type enumeration {
            enum "Up";
            enum "Resolving";
            enum "Error_DNS";
            enum "Error_Other";
            enum "Disabled";
          }
          config false;
          default "Disabled";
          description
            "Indicates the status of this network.";
        }
        leaf Gatekeeper {
          type string;
          default "";
          description
            "Host name or IP address of H.323 Gatekeeper.";
        }
        leaf GatekeeperPort {
          type uint32;
          default "1719";
          description
            "Destination port to be used in connecting to the H.323
             Gatekeeper.";
        }
        leaf GatekeeperID {
          type string;
          default "";
          description
            "Gatekeeper ID.";
        }
        leaf TimeToLive {
          type uint32;
          default "86400";
          description
            "Defines the TimeToLive specification in the
             registration with the Gatekeeper in {{units}}.";
        }
        leaf DSCPMark {
          type uint32 {
            range "0..63";
          }
          default "0";
          description
            "Diffserv code point to be used for outgoing H.323
             signaling packets.";
        }
        leaf VLANIDMark {
          type int32 {
            range "-1..max";
          }
          default "-1";
          description
            "VLAN ID (as defined in {{bibref|802.1Q-2005}}) to be
             used for outgoing H.323 signaling packets for this
             network.  A value of -1 indicates the default value
             is to be used.
          
             If either {{param}} or
             {{param|EthernetPriorityMark}} is greater than zero,
             then the outgoing frames MUST be tagged.  Otherwise,
             the outgoing frames MAY be tagged or untagged.";
        }
        leaf EthernetPriorityMark {
          type int32 {
            range "-1..max";
          }
          default "-1";
          description
            "Ethernet priority code (as defined in
             {{bibref|802.1D-2004}}) to be used for outgoing
             H.323 signaling packets for this network.  A value
             of -1 indicates the default value is to be used.
          
             If either {{param|VLANIDMark}} or {{param}} is
             greater than zero, then the outgoing frames MUST be
             tagged.  Otherwise, the outgoing frames MAY be
             tagged or untagged.";
        }
        leaf STUNEnable {
          type boolean;
          default "false";
          description
            "Enable or disable use of STUN to allow operation
             through NAT.  Note: enabling STUN is to be
             interpreted as enabling the use of STUN for
             discovery, not use as a keep-alive mechanism.";
        }
        leaf STUNServer {
          type string {
            length "0..256";
          }
          default "";
          description
            "Domain name or IP address of the STUN server.";
        }
        leaf NonVoiceBandwidthReservedUpstream {
          type uint32;
          default "0";
          description
            "For bandwidth-based admission control, a session can
             proceed only if there is {{param}} {{units}} of
             upstream bandwidth left available for non-voice
             traffic.  This parameter is appropriate only in
             implementations in which the actual bandwidth can be
             known, such as a VoIP device embedded in a DSL B-NT.";
        }
        leaf NonVoiceBandwidthReservedDownstream {
          type uint32;
          default "0";
          description
            "For bandwidth-based admission control, a session can
             proceed only if there is {{param}} {{units}} of
             downstream bandwidth left available for non-voice
             traffic.  This parameter is appropriate only in
             implementations in which the actual bandwidth can be
             known, such as a VoIP device embedded in a DSL B-NT.";
        }
        leaf MaxSessions {
          type uint32;
          default "0";
          description
            "Limit on the number of simultaneous voice sessions
             across all {{object|.H323.Client.}} referencing this
             {{object}}.  This MUST be less than or equal to
             {{param|.Capabilities.MaxSessionCount}}.
          
             A value of zero indicates no explicit limit on the
             number of sessions.";
        }
        leaf VoIPProfile {
          type string {
            length "0..256";
          }
          description
            "VoIP profile to use with this network.
          
             {{reference}}";
        }
        leaf CodecList {
          type string;
          description
            "{{list}} {{reference}}
          
             The CPE SHOULD use the first enabled item in the
             list among those supported by the remote endpoint
             and consistent with the available bandwidth.";
        }
      }
    }

    list Trunk {
      key "Alias";
      description
        "Trunk table.
      
         The {{object}} holds all parameters a CPE needs to set
         up a trunk connection with an NGN, as defined in
         {{bibref|ETSI_TS_181_019}}.";
      leaf Enable {
        type boolean;
        default "false";
        description
          "Enables or disables this trunk.";
      }
      leaf QuiescentMode {
        type boolean;
        description
          "If {{true}}, when {{param|Enable}} is set to {{false}}
           in-progress sessions remain intact, but no new
           sessions are allowed.  When all sessions are
           terminated, the {{object}} is disabled.";
      }
      leaf Status {
        type enumeration {
          enum "Up";
          enum "Initializing";
          enum "Registering";
          enum "Unregistering";
          enum "Error";
          enum "Testing";
          enum "Disabled";
        }
        config false;
        default "Disabled";
        description
          "Indicates the status of this trunk.";
      }
      leaf Origin {
        type enumeration {
          enum "AutoConfigured";
          enum "Static";
        }
        config false;
        default "Static";
        description
          "Mechanism via which the {{object}} was assigned.
           {{enum}}";
      }
      leaf Name {
        type string {
          length "0..16";
        }
        description
          "Name of the trunk.";
      }
      leaf DDIRange {
        type string;
        description
          "{{list}} Each range consists of a ''Start'' part
           consisting of 1 to n digits (string representation)
           followed by an OPTIONAL ''End'' part consisting of 1
           to n digits prefixed by a \"-\" symbol.
        
           Examples:
        
           :0123456789
        
           :0123456700-0123456720
        
           Each time this value is changed, the table of Lines
           managed by the {{object|.Trunk}} is automatically
           adapted and each value of the {{param}} MUST be
           represented in corresponding
           {{param|.CallControl.Line.{i}.DirectoryNumber}}
           parameter.
        
           If this trunk has a {{object|.SIP.Client.}} provider
           and {{param|.SIP.Client.{i}.E164Format}} is set to
           {{true}}, full E.164 numbers with country code (but
           without \"+\" prefix) MUST be used.
        
           This parameter can only be modified if
           {{param|Origin}} is {{enum|Static|Origin}}.";
      }
      leaf LineObjectCreation {
        type boolean;
        description
          "When {{true}}, a {{object|.CallControl.Line.{i}.}}
           instance SHOULD be created automatically for each
           identity within the ranges specified by
           {{param|DDIRange}}.";
      }
      leaf MaxChannels {
        type uint32;
        description
          "Defines the maximum number of simultaneous communication
           channels handled by this trunk.  A channel is used to
           convey an information signal, for example a digital
           bit stream, from one or several senders to one or
           several receivers.";
      }
      leaf MaxOutboundChannelCount {
        type int32 {
          range "-1..max";
        }
        default "-1";
        description
          "Maximal number of simultaneous communication channels in
           outbound direction supported across this trunk.  The
           maximum number cannot exceed {{param|MaxChannels}} -
           {{param|MaxInboundChannelCount}}.  A value n>0 means,
           that there are no more than n channels allowed, which
           are used by outbound calls.  A value of -1 means that
           there are no restrictions in this direction.";
      }
      leaf MaxInboundChannelCount {
        type int32 {
          range "-1..max";
        }
        default "-1";
        description
          "Maximal number of simultaneous communication channels in
           inbound direction supported across this trunk.  The
           maximum number cannot exceed {{param|MaxChannels}} -
           {{param|MaxOutboundChannelCount}}.  A value n>0 means,
           that there are no more than n channels allowed, which
           are used by inbound calls.  A value of -1 means that
           there are no restrictions in this direction.";
      }
      leaf CodecPriority {
        type enumeration {
          enum "Local";
          enum "Remote";
        }
        description
          "The {{param}} option controls which end of an inbound
           call leg will have priority over the negotiation of
           codecs.";
      }
      leaf Provider {
        type string {
          length "0..256";
        }
        description
          "SIP client or ISDN interface associated with the
           identities represented by this trunk.
        
           {{reference}}
        
           This parameter can only be modified if
           {{param|Origin}} is {{enum|Static|Origin}}.";
      }
    }

    container CallControl {
      description
        "Call control and call routing parameters.  This object is a
         control plane application for the VoiceService that
         provides numbers or names based routing, local PBX
         functionalities and advanced telephony features.
      
         It is mutually exclusive with the {{object|.Interwork}}
         table which is used in case of switching capabilities.";
      leaf MaxNumberOfLines {
        type uint32;
        description
          "Maximum number of {{object|Line.{i}.}} in {{object}}.
        
           This value cannot be greater than
           {{param|.Capabilities.MaxLineCount}}.";
      }
      leaf MaxNumberOfExtensions {
        type uint32;
        description
          "Maximum number of {{object|Extension.{i}.}} in
           {{object}}.
        
           This value cannot be greater than
           {{param|.Capabilities.MaxExtensionCount}}.";
      }

      list Line {
        key "DirectoryNumber";
        description
          "Voice line table.
        
           Support for adding and removing lines is conditional
           on whether the CPE supports more than one line in
           total as indicated by
           {{param|.Capabilities.MaxLineCount}}.";
        leaf Enable {
          type boolean;
          default "false";
          description
            "Enable or disable this line.";
        }
        leaf QuiescentMode {
          type boolean;
          description
            "If {{true}}, when {{param|Enable}} is set to {{false}}
             in-progress sessions remain intact, but no new
             sessions are allowed.  When all sessions are
             terminated, the {{object}} is disabled.";
        }
        leaf Status {
          type enumeration {
            enum "Up";
            enum "Error";
            enum "Testing";
            enum "Quiescent";
            enum "Disabled";
          }
          config false;
          default "Disabled";
          description
            "Indicates the status of this line.";
        }
        leaf CallStatus {
          type enumeration {
            enum "Idle";
            enum "Dialing";
            enum "Delivered";
            enum "Connected";
            enum "Alerting";
            enum "Disconnected";
          }
          config false;
          description
            "Indicates the call status for this line.";
        }
        leaf Origin {
          type enumeration {
            enum "Static";
            enum "DDIRange";
          }
          config false;
          description
            "Mechanism via which the {{object}} instance was
             created.";
        }
        leaf DirectoryNumber {
          type string {
            length "0..32";
          }
          default "";
          description
            "Directory number associated with this line.";
        }
        leaf Provider {
          type string {
            length "0..256";
          }
          description
            "Provider for the line.  The value MUST be the path name
             of a row in one of the following tables:
          
             {{reference}}";
        }
        leaf CallingFeatures {
          type string {
            length "0..256";
          }
          description
            "Set of calling features to apply to this line.
          
             {{reference}}";
        }

        container Stats {
          config false;
          description
            "Statistics for this {{object|#}} instance.
          
             The CPE MUST reset the line's Stats parameters
             (unless otherwise stated in individual object or
             parameter descriptions) either when the line becomes
             operationally down due to a previous administrative
             down (i.e.  the line's {{param|#.Status}} parameter
             transitions to a down state after the line is
             disabled) or when the line becomes administratively
             up (i.e.  the line's {{param|#.Enable}} parameter
             transitions from {{false}} to {{true}}).";

          container IncomingCalls {
            description
              "Statistics for incoming calls.";
            leaf CallsReceived {
              type uint32;
              description
                "Total number of received calls to the line.";
            }
            leaf CallsConnected {
              type uint32;
              description
                "Total number of calls that successfully completed
                 call setup signaling.";
            }
            leaf CallsFailed {
              type uint32;
              description
                "Total number of calls that failed to successfully
                 complete call setup signaling.";
            }
            leaf CallsDropped {
              type uint32;
              description
                "Total calls that were successfully connected, but
                 dropped unexpectedly while in progress without
                 explicit user termination.";
            }
            leaf TotalCallTime {
              type uint32;
              description
                "Cumulative call duration in {{units}}.";
            }
          }

          container OutgoingCalls {
            description
              "Statistics for outgoing calls.";
            leaf CallsAttempted {
              type uint32;
              description
                "Total number of outgoing calls attempted from the
                 line.";
            }
            leaf CallsConnected {
              type uint32;
              description
                "Total number of calls that successfully completed
                 call setup signaling.";
            }
            leaf CallsFailed {
              type uint32;
              description
                "Total number of calls that failed to successfully
                 complete call setup signaling.";
            }
            leaf CallsDropped {
              type uint32;
              description
                "Total calls that were successfully connected, but
                 dropped unexpectedly while in progress without
                 explicit user termination.";
            }
            leaf TotalCallTime {
              type uint32;
              description
                "Cumulative call duration in {{units}}.";
            }
          }

          container RTP {
            description
              "RTP statistic parameters.";
            leaf PacketsReceived {
              type uint32;
              description
                "Total number of RTP packets received.";
            }
            leaf PacketsSent {
              type uint32;
              description
                "Total number of RTP packets sent.";
            }
            leaf PacketsLost {
              type uint32;
              description
                "Total number of RTP packets that have been lost.";
            }
            leaf BytesSent {
              type uint32;
              description
                "Total number of bytes sent.";
            }
            leaf BytesReceived {
              type uint32;
              description
                "Total number of bytes received.";
            }
          }

          container DSP {
            description
              "DSP statistic parameters.";
            leaf Overruns {
              type uint32;
              description
                "Total number of times the receive jitter buffer has
                 overrun.";
            }
            leaf Underruns {
              type uint32;
              description
                "Total number of times the receive jitter buffer has
                 underrun.";
            }
          }
        }
      }

      list Extension {
        key "ExtensionNumber";
        description
          "Extension table containing the local numbers and names.
        
           Support for adding and removing extensions is
           conditional on whether the CPE supports more than one
           line in total as indicated by
           {{param|.Capabilities.MaxExtensionCount}}.";
        leaf Enable {
          type boolean;
          default "false";
          description
            "Enable or disable this extension.";
        }
        leaf QuiescentMode {
          type boolean;
          description
            "If {{true}}, when {{param|Enable}} is set to {{false}}
             in-progress sessions remain intact, but no new
             sessions are allowed.  When all sessions are
             terminated, the {{object}} is disabled.";
        }
        leaf Status {
          type enumeration {
            enum "Up";
            enum "Initializing";
            enum "Error";
            enum "Testing";
            enum "Quiescent";
            enum "Disabled";
          }
          config false;
          default "Disabled";
          description
            "Indicates the status of this extension.";
        }
        leaf CallStatus {
          type enumeration {
            enum "Idle";
            enum "Dialing";
            enum "Delivered";
            enum "Connected";
            enum "Alerting";
            enum "Disconnected";
          }
          config false;
          description
            "Indicates the call status for this extension.";
        }
        leaf Origin {
          type enumeration {
            enum "AutoConfigured";
            enum "Static";
          }
          config false;
          default "Static";
          description
            "Mechanism via which the {{object}} object was assigned.
             {{enum}}";
        }
        leaf Name {
          type string {
            length "0..256";
          }
          description
            "The name of this extension.
          
             This name will also be used for CallerIdName
             functionality and for displaying on screen of
             handset, etc...";
        }
        leaf ExtensionNumber {
          type string {
            length "0..32";
          }
          default "";
          description
            "The number assigned to this extension for internal
             calls.";
        }
        leaf Provider {
          type string {
            length "0..256";
          }
          description
            "Provider for the extension.  The value MUST be the path
             name of a row in one of the following tables:
          
             {{reference}}";
        }
        leaf NumberingPlan {
          type string {
            length "0..256";
          }
          description
            "Numbering plan to be used for outgoing calls.
          
             {{reference}}";
        }
        leaf CallingFeatures {
          type string {
            length "0..256";
          }
          description
            "Set of calling features to apply to this extension.
          
             {{reference}}";
        }
        leaf CallWaitingStatus {
          type enumeration {
            enum "Disabled";
            enum "Idle";
            enum "SecondaryRinging";
            enum "SecondaryConnecting";
            enum "SecondaryConnected";
          }
          config false;
          description
            "Status of endpoint managed call waiting, if supported.
             {{enum}}
          
             This parameter SHOULD NOT be present if the CPE does
             not support endpoint managed call waiting.";
        }
        leaf ConferenceCallingStatus {
          type enumeration {
            enum "Disabled";
            enum "Idle";
            enum "SecondaryCalling";
            enum "SecondaryConnecting";
            enum "SecondaryConnected";
            enum "InConferenceCall";
          }
          config false;
          description
            "Status of endpoint managed conference calling, if
             supported.  {{enum}}
          
             This parameter SHOULD NOT be present if the CPE does
             not support endpoint managed conference calling.";
        }
        leaf ConferenceCallingSessionCount {
          type uint32;
          config false;
          description
            "Number of active sessions on this extension.
          
             : 0 indicates no call is in progress.
          
             : 1 indicates a single call is in progress.
          
             : Higher values indicate a conference call is in
             progress.
          
             This parameter SHOULD NOT be present if the CPE does
             not support endpoint managed conference calling.";
        }
        leaf VoiceMail {
          type string {
            length "0..256";
          }
          description
            "Voice mail to use when the {{object}} is not
             responding.
          
             {{reference}}";
        }

        container Stats {
          config false;
          description
            "Statistics for this extension.
          
             The CPE MUST reset the extension's Stats parameters
             (unless otherwise stated in individual object or
             parameter descriptions) either when the extension
             becomes operationally down due to a previous
             administrative down (i.e.  the extension's
             {{param|#.Status}} parameter transitions to a down
             state after the extension is disabled) or when the
             extension becomes administratively up (i.e.  the
             extension's {{param|#.Enable}} parameter transitions
             from {{false}} to {{true}}).";

          container IncomingCalls {
            description
              "Statistics for incoming calls.";
            leaf CallsReceived {
              type uint32;
              description
                "Total number of received calls to the extension.";
            }
            leaf CallsConnected {
              type uint32;
              description
                "Total number of calls that successfully completed
                 call setup signaling.";
            }
            leaf CallsFailed {
              type uint32;
              description
                "Total number of calls that failed to successfully
                 complete call setup signaling.";
            }
            leaf CallsDropped {
              type uint32;
              description
                "Total calls that were successfully connected, but
                 dropped unexpectedly while in progress without
                 explicit user termination.";
            }
            leaf TotalCallTime {
              type uint32;
              description
                "Cumulative call duration in {{units}}.";
            }
          }

          container OutgoingCalls {
            description
              "Statistics for outgoing calls.";
            leaf CallsAttempted {
              type uint32;
              description
                "Total number of outgoing calls attempted from the
                 extension.";
            }
            leaf CallsConnected {
              type uint32;
              description
                "Total number of calls that successfully completed
                 call setup signaling.";
            }
            leaf CallsFailed {
              type uint32;
              description
                "Total number of calls that failed to successfully
                 complete call setup signaling.";
            }
            leaf CallsDropped {
              type uint32;
              description
                "Total calls that were successfully connected, but
                 dropped unexpectedly while in progress without
                 explicit user termination.";
            }
            leaf TotalCallTime {
              type uint32;
              description
                "Cumulative call duration in {{units}}.";
            }
          }

          container RTP {
            description
              "RTP statistic parameters.";
            leaf PacketsReceived {
              type uint32;
              description
                "Total number of RTP packets received.";
            }
            leaf PacketsSent {
              type uint32;
              description
                "Total number of RTP packets sent.";
            }
            leaf PacketsLost {
              type uint32;
              description
                "Total number of RTP packets that have been lost.";
            }
            leaf BytesSent {
              type uint32;
              description
                "Total number of bytes sent.";
            }
            leaf BytesReceived {
              type uint32;
              description
                "Total number of bytes received.";
            }
          }

          container DSP {
            description
              "DSP statistic parameters.";
            leaf Overruns {
              type uint32;
              description
                "Total number of times the receive jitter buffer has
                 overrun.";
            }
            leaf Underruns {
              type uint32;
              description
                "Total number of times the receive jitter buffer has
                 underrun.";
            }
          }
        }
      }

      list Group {
        key "Alias";
        description
          "This object models an extension as a group of extensions.";
        leaf Extensions {
          type string;
          description
            "{{list}} If this parameter is null the group is treated
             as a group that contains all extensions.
          
             {{reference}}";
        }
        leaf RingType {
          type enumeration {
            enum "Simultaneous";
            enum "Hierarchical";
            enum "Cyclic";
          }
          description
            "Defines the way of ringing for the extensions in this
             group.  {{enum}}";
        }
        leaf RingTimeout {
          type uint32;
          description
            "The time (in {{units}}) to wait for extension reply
             before trying the next extension.
          
             Only applicable if {{param|RingType}} =
             {{enum|Hierarchical|RingType}} or
             {{enum|Cyclic|RingType}}.";
        }
      }

      list Mailbox {
        key "Alias";
        description
          "Voice mail configuration related to a particular
           extension.";
        leaf Enable {
          type boolean;
          default "false";
          description
            "Enables or disables this entry.";
        }
        leaf MaxMsg {
          type uint32;
          description
            "This limits the number of messages in a voicemail
             folder.";
        }
        leaf MaxMessageTime {
          type uint32;
          description
            "Defines the maximum amount of time in {{units}} of an
             incoming message.  Use this when there are many
             users and disk space is limited.  A value of 0 means
             there will be no maximum time limit enforced.";
        }
        leaf MinSize {
          type uint32;
          description
            "Minimal size in {{units}} of the voicemail box.";
        }
        leaf SMTPServerAddress {
          type string {
            length "0..256";
          }
          description
            "SMTP server FQDN or IP Address used for voicemail
             notifications.";
        }
        leaf SMTPServerPort {
          type uint32 {
            range "0..65535";
          }
          default "25";
          description
            "SMTP server port for voicemail notifications.";
        }
        leaf SMTPUser {
          type string {
            length "0..256";
          }
          description
            "SMTP user name.";
        }
        leaf SMTPPassword {
          type string {
            length "0..256";
          }
          description
            "SMTP password.";
        }
        leaf SMTPAuthenticationType {
          type enumeration {
            enum "None";
            enum "SSL";
            enum "TLS";
            enum "Auto";
          }
          default "None";
          description
            "Type of authentication used to connect to the SMTP
             server.";
        }
        leaf SMTPFrom {
          type string {
            length "0..256";
          }
          description
            "Sender's email address.";
        }
      }

      list IncomingMap {
        key "Line Extension";
        description
          "The {{object}} is a table that is used to control which
           extensions ring when an incoming call is received.
        
           The map approach separates the call routing aspects
           from the configuration of the lines and extensions.
           It support PBX concepts such as DDI (one extension per
           line) and groups (parallel dialing if extensions have
           same priority and hunting when extensions have
           different priority).";
        leaf Enable {
          type boolean;
          default "false";
          description
            "Enables or disables this entry.";
        }
        leaf Line {
          type string {
            length "0..256";
          }
          description
            "{{object|#.Line}} used by the call.
          
             {{reference}}";
        }
        leaf Extension {
          type string {
            length "0..256";
          }
          description
            "{{object|#.Extension}} that rings on incoming call.
          
             {{reference}}";
        }
        leaf Order {
          type uint32 {
            range "1..max";
          }
          default "1";
          description
            "Indicates the order in which extensions ring.
          
             First all extensions with the lowest order value
             will ring.
          
             When all these extensions have rejected the call or
             did not reply, the next order value will be
             attempted.";
        }
        leaf Timeout {
          type uint32;
          description
            "The time in {{units}} the extension will ring before it
             is considered that there was no reply.";
        }
      }

      list OutgoingMap {
        key "Extension Line";
        description
          "The {{object}} is a table that is used to control which
           line is used when an extension makes a call.";
        leaf Enable {
          type boolean;
          default "false";
          description
            "Enables or disables this entry.";
        }
        leaf CLIPNoScreeningNumber {
          type string {
            length "0..32";
          }
          description
            "Public number to be presented outgoing calls, instead
             of the effective extension number.";
        }
        leaf Extension {
          type string {
            length "0..256";
          }
          description
            "{{object|#.Extension}} which makes the outgoing call.
          
             {{reference}}";
        }
        leaf Line {
          type string {
            length "0..256";
          }
          description
            "Identifies the {{object|#.Line}} to be used for
             outgoing calls.
          
             When applicable in the signaling protocol the
             DirectoryNumber will be used as source number for
             this call.
          
             Note: The Line to be used for an outgoing call can
             be overridden by the {{object|#.NumberingPlan}}.
          
             {{reference}}";
        }
        leaf Order {
          type uint32 {
            range "1..max";
          }
          default "1";
          description
            "The order in which using the lines is attempted.  This
             is used to implement a backup mechanism.
          
             If the first line is not available, using the next
             one will be attempted.";
        }
      }

      list NumberingPlan {
        key "Alias";
        description
          "Information related the numbering plan.
        
           {{object}} is applicable only if the device supports a
           dialing mechanism for which a number plan is needed
           (for example, some devices with an explicit Dial
           button do not need to be aware of the dialing plan)
           and if the device does not already support a numbering
           plan mechanism for this call control (e.g., in-band
           via MGCP).";
        leaf MinimumNumberOfDigits {
          type uint32 {
            range "1..32";
          }
          default "1";
          description
            "This is the minimum number of digits to be collected
             before an outgoing request (e.g., a SIP INVITE) can
             be initiated.
          
             If ''End of Dialing'' (as defined in
             {{param|InterDigitTimerStd}}) occurs before the
             minimum number of digits has been reached then the
             number will be considered incomplete and no request
             will be initiated.
          
             In practice, searching
             {{object|.CallControl.NumberingPlan.{i}.PrefixInfo.{i}.}}
             commences only once {{param}} digits has been
             received.";
        }
        leaf MaximumNumberOfDigits {
          type uint32 {
            range "1..32";
          }
          default "15";
          description
            "When this number of digits has been collected, an
             outgoing request (e.g., a SIP INVITE) MUST be
             initiated.  Any additional dialed digits will be
             ignored.  This parameter is only used in the case
             that no match in
             {{object|.CallControl.NumberingPlan.{i}.PrefixInfo.{i}.}}
             has been found.";
        }
        leaf InterDigitTimerStd {
          type uint32 {
            range "1..50000";
          }
          default "15000";
          description
            "This timer is the maximum allowable time (expressed in
             {{units}}) between the dialing of digits.  This
             timer is restarted every time a digit is dialed.
             Expiration of this timer indicates ''End of
             Dialing''.";
        }
        leaf InterDigitTimerOpen {
          type uint32 {
            range "1..50000";
          }
          default "3000";
          description
            "This timer is the maximum allowable time (expressed in
             {{units}}) between the dialing of digits once the
             minimum number of digits defined on a prefix based
             has been reached.
          
             This timer is only applicable to \"open numbering\",
             where the exact number of digits for a prefix is not
             known.";
        }
        leaf TerminationDigit {
          type string {
            length "0..1";
          }
          default "#";
          description
            "Digit that can be used by the subscriber to indicate
             that dialing has completed.";
        }
        leaf InvalidNumberTone {
          type string {
            length "0..256";
          }
          description
            "The tone that tells the user when the number dialed is
             determined to be invalid.
          
             {{reference}}";
        }
        leaf PrefixInfoMaxEntries {
          type uint32;
          config false;
          description
            "This is the maximum number of instances of
             {{object|.CallControl.NumberingPlan.{i}.PrefixInfo.{i}.}}
             that can be supported.";
        }

        list PrefixInfo {
          key "Alias";
          description
            "Each entry in this table contains information related
             to an individual prefix in the NumberingPlan.
          
             It is anticipated that once the minimum number of
             digits has been received, the VoIP device will
             search this prefix list every time a new digit is
             received.  If no new entry is found, then the object
             that was previously found will be used instead.
          
             If supported,
             {{param|.CallControl.NumberingPlan.{i}.PrefixInfoMaxEntries}}
             and
             {{param|.CallControl.NumberingPlan.{i}.PrefixInfoNumberOfEntries}}
             MUST be present.
          
             The defaults given for this object apply only to
             explicit creation of an instance of this object and
             not to automatic creation of instances of this
             object due to creation of a parent object.";
          leaf Enable {
            type boolean;
            default "false";
            description
              "Enables or disables this entry.";
          }
          leaf PrefixRange {
            type string {
              length "0..42";
            }
            default "";
            description
              "This is a string representation of a range of
               prefixes.  Each prefix consists of a ''From'' part
               consisting of 1 to n digits (string
               representation) followed by an OPTIONAL ''To''
               part consisting of exactly one digit prefixed by a
               \"-\" symbol.
            
               All characters in the \"From\" and \"To\" parts of
               the prefix range MUST be \"0-9\", \"*\" or \"#\".
            
               A further constraint is that the \"To\" digit MUST
               always be numerically greater than the last digit
               of the \"From\" part.
            
               Examples:
            
               : 02
            
               : 031-5
            
               : 032
            
               : 0325
            
               : *#34
            
               : #22";
          }
          leaf PrefixMinNumberOfDigits {
            type uint32 {
              range "1..40";
            }
            default "1";
            description
              "This is the minimum number of allowable digits for
               the prefix range.  Once the minimum number of
               digits has been reached,
               {{param|#.InterDigitTimerOpen}} will be used
               instead of {{param|#.InterDigitTimerStd}}.
            
               If the minimum number of digits has been reached
               and the inter-digit timer expires, an outgoing
               request is initiated.";
          }
          leaf PrefixMaxNumberOfDigits {
            type uint32 {
              range "1..40";
            }
            default "1";
            description
              "This is the maximum number of allowable digits for
               the prefix range.  Once the number of digits
               received reaches this value an outgoing request is
               initiated.";
          }
          leaf NumberOfDigitsToRemove {
            type uint32 {
              range "0..40";
            }
            default "0";
            description
              "If this parameter has a non-zero value, the specified
               number of digits will be removed from the internal
               digit buffer (which contains the dialed digits)
               from the position specified by
               {{param|PosOfDigitsToRemove}}.
            
               Subsequently a search of {{object}} for a matching
               prefix using the modified number is performed.
               Note that this parameter does not have any impact
               on the number sent in the outgoing request: it is
               used only for searching within the Numbering Plan.
            
               This parameter has no effect if it is set to 0.
            
               This parameter is provided to handle Carrier
               override and other codes used as prefix to
               standard numbers and to ensure that the correct
               ''End of Dialing'' can be specified without
               significant data duplication.";
          }
          leaf PosOfDigitsToRemove {
            type uint32 {
              range "0..40";
            }
            default "0";
            description
              "This parameter is used in conjunction with
               {{param|NumberOfDigitsToRemove}}.  It specifies
               the position within the internal digit buffer from
               which the digits are to be removed.";
          }
          leaf DialTone {
            type string {
              length "0..256";
            }
            description
              "The tone to be played by the VoIP device when the
               user has dialed exactly the same digits as defined
               in the prefix.  The VoIP device will cease playing
               the tone once an additional digit has been dialed.
            
               {{reference}}";
          }
          leaf FacilityAction {
            type string {
              length "0..64";
            }
            default "";
            description
              "This is a string representing a Facility Action
               implemented by the VoIP device.
            
               The parameter MAY instead indicate a
               vendor-specific Facility Action, which MUST use
               the format defined in {{bibref|TR-106}}.
            
               When {{empty}} or the value is an unrecognized
               string (i.e.  a Facility Action not supported by
               the CPE) normal outgoing requests are made.";
          }
          leaf FacilityActionArgument {
            type string {
              length "0..256";
            }
            default "";
            description
              "Optional argument associated with
               {{param|FacilityAction}}.  The interpretation of
               the argument is dependent on a specific value of
               {{param|FacilityAction}}.  {{reference}}";
          }
        }
      }

      container CallingFeatures {
        description
          "This object models the calling features that can be apply
           on {{object|.CallControl.Line}} or
           {{object|.CallControl.Extension}}.";

        list Set {
          key "Alias";
          description
            "This object models a set of calling features that can
             be applied in {{object|.CallControl.Line.}} or
             {{object|.CallControl.Extension.}} objects.";
          leaf CallerIDEnable {
            type boolean;
            description
              "Enable or disable the transmission of caller ID
               information on incoming calls (CLIP).";
          }
          leaf CallerIDNameEnable {
            type boolean;
            description
              "Enable or disable the transmission of caller ID name
               information on incoming calls (CNIP).";
          }
          leaf CallWaitingEnable {
            type boolean;
            description
              "Enables or disables call waiting in the Endpoint.
            
               This parameter SHOULD NOT be present if the CPE
               does not support Endpoint managed call waiting.";
          }
          leaf CallForwardUnconditionalEnable {
            type boolean;
            description
              "Enables or disables unconditional call forwarding by
               the endpoint.
            
               This parameter SHOULD NOT be present if the CPE
               does not support Endpoint based call forwarding.";
          }
          leaf CallForwardUnconditionalNumber {
            type string {
              length "0..32";
            }
            description
              "Directory number to which all incoming calls to this
               line are forwarded when
               {{param|CallForwardUnconditionalEnable}} is
               {{true}}.
            
               This parameter SHOULD NOT be present if the CPE
               does not support Endpoint based call forwarding";
          }
          leaf CallForwardOnBusyEnable {
            type boolean;
            description
              "Enables or disables call forwarding-on-busy by the
               Endpoint.
            
               This parameter SHOULD NOT be present if the CPE
               does not support Endpoint based call forwarding.";
          }
          leaf CallForwardOnBusyNumber {
            type string {
              length "0..32";
            }
            description
              "Directory number to which all incoming calls to this
               line are forwarded when
               {{param|CallForwardOnBusyEnable}} is {{true}} and
               the line is busy.
            
               This parameter SHOULD NOT be present if the CPE
               does not support Endpoint based call forwarding.";
          }
          leaf CallForwardOnBusyRingTimeout {
            type uint32;
            description
              "Delay in {{units}} before considering there is no
               answer for call forwarding-on-busy.
            
               This parameter SHOULD NOT be present if the CPE
               does not support Endpoint based call forwarding.";
          }
          leaf CallForwardOnNoAnswerEnable {
            type boolean;
            description
              "Enables or disables call forwarding-on-no-answer by
               the Endpoint.
            
               This parameter SHOULD NOT be present if the CPE
               does not support Endpoint based call forwarding.";
          }
          leaf CallForwardOnNoAnswerNumber {
            type string {
              length "0..32";
            }
            description
              "Directory number to which all incoming calls to this
               line are forwarded when
               {{param|CallForwardOnNoAnswerEnable}} is {{true}}
               and there is no local answer.
            
               This parameter SHOULD NOT be present if the CPE
               does not support Endpoint based call forwarding.";
          }
          leaf CallForwardOnNoAnswerRingTimeout {
            type uint32;
            description
              "Delay in {{units}} before considering there is no
               answer for call forwarding-on-no-answer.
            
               This parameter SHOULD NOT be present if the CPE
               does not support Endpoint based call forwarding.";
          }
          leaf CallTransferEnable {
            type boolean;
            description
              "Enables or disables call transfer by the Endpoint.
            
               This parameter SHOULD NOT be present if the CPE
               does not support Endpoint based call transfer.";
          }
          leaf MWIEnable {
            type boolean;
            description
              "Enables or disables Message Waiting Indication by the
               Endpoint.
            
               This parameter SHOULD NOT be present if the CPE
               does not support MWI.";
          }
          leaf VMWIEnable {
            type boolean;
            description
              "Enables or disables Visual Message Waiting
               Indication.";
          }
          leaf LineMessagesWaiting {
            type uint32;
            config false;
            description
              "Indicates the number of messages which are currently
               waiting on this line as known by the CPE.
            
               This parameter SHOULD NOT be present if the CPE
               does not support MWI.";
          }
          leaf AnonymousCallRejectionEnable {
            type boolean;
            description
              "Enable or disable Anonymous Call Block capability in
               the endpoint (ACR).
            
               This parameter SHOULD NOT be present if the CPE
               does not support endpoint based Anonymous Call
               Block capability.";
          }
          leaf AnonymousCallEnable {
            type boolean;
            description
              "Enable or disable Anonymous Call capability in the
               endpoint (CLIR).
            
               This parameter SHOULD NOT be present if the CPE
               does not support endpoint based Anonymous Call
               capability.";
          }
          leaf DoNotDisturbEnable {
            type boolean;
            description
              "Enable or disable Do Not Disturb capability in the
               Endpoint.  When enabled, all calls are forwarded
               to voice mail.
            
               This parameter SHOULD NOT be present if the CPE
               does not support Endpoint based Do Not Disturb
               capability.";
          }
          leaf RepeatDialEnable {
            type boolean;
            description
              "Enable or disable Repeat Dial capability in the
               Endpoint.
            
               This parameter SHOULD NOT be present if the CPE
               does not support Endpoint based Repeat Dial
               capability.";
          }
          leaf VoiceMailEnable {
            type boolean;
            description
              "Enable or disable Voice Mail capability in the
               Endpoint.
            
               This parameter SHOULD NOT be present if the CPE
               does not support Endpoint based Voice Mail
               capability.";
          }
          leaf CallPickUpEnable {
            type boolean;
            description
              "Enable or disable Call Interception capability in the
               Endpoint.";
          }
          leaf CCBSEnable {
            type boolean;
            description
              "Enable or disable automatic recall on busy
               (Completion of Calls to Busy Subscriber)
               capability in the Endpoint.";
          }
          leaf IIFCEnable {
            type boolean;
            description
              "Enable or disable successive forwarding (Inhibition
               of Incoming Forwarded Calls) from the Endpoint.";
          }
          leaf BlockForwardEnable {
            type boolean;
            description
              "Allow or block any internal forward to the Endpoint.";
          }
          leaf SecretForwarderEnable {
            type boolean;
            description
              "Enable or disable secret identity of this Endpoint in
               case it initiates (on an external incoming call) a
               forward to another internal phone Endpoint.
            
               If enabled, only the remote ''caller party'' can
               be identified (if not anonymous), not this
               intermediate ''via'' phone extension.";
          }
          leaf FollowMeEnable {
            type boolean;
            description
              "Enable or disable FollowMe capability in the
               Endpoint.";
          }

          list CFT {
            key "Alias";
            description
              "This object defines a Call Forwarding Timed (CFT)
               that permit the user to forward calls to
               particular destinations depending on the time of
               day.
            
               Note: a bad configuration (e.g.  timeslots
               overlapping) could cause unexpected behavior.";
            leaf Enable {
              type boolean;
              description
                "Whether this schedule is currently enabled.";
            }
            leaf Day {
              type enumeration {
                enum "Monday";
                enum "Tuesday";
                enum "Wednesday";
                enum "Thursday";
                enum "Friday";
                enum "Saturday";
                enum "Sunday";
                enum "All";
              }
              description
                "Day where the schedule active.";
            }
            leaf StartTime {
              type string {
                length "0..5";
              }
              description
                "Start time of the schedule in the form : hh:mm.";
            }
            leaf EndTime {
              type string {
                length "0..5";
              }
              description
                "End time of the schedule in the form : hh:mm.";
            }
            leaf ForwardedToNumber {
              type string {
                length "0..32";
              }
              description
                "Number to forward the call to.";
            }
          }

          list SCF {
            key "CallingNumber";
            description
              "This object defines a Selective Call Forwarding (SCF)
               that permit the user to forward calls to different
               destinations depending on the calling number.";
            leaf Enable {
              type boolean;
              default "false";
              description
                "Enables or disables this Selective Call Forward.";
            }
            leaf CallingNumber {
              type string {
                length "0..32";
              }
              description
                "Calling number concerned by the forward.
              
                 The CPE SHOULD perform an exact match with this
                 string without any attempts at number
                 normalization.";
            }
            leaf ForwardedToNumber {
              type string {
                length "0..32";
              }
              description
                "Number to forward the call to.";
            }
          }

          list SCREJ {
            key "CallingNumber";
            description
              "This object defines a Selective Call Rejection
               (SCREJ) that permit the user to selectively reject
               calls depending on the calling number.";
            leaf Enable {
              type boolean;
              default "false";
              description
                "Enables or disables this Selective Call Rejection.";
            }
            leaf CallingNumber {
              type string {
                length "0..32";
              }
              description
                "Calling number concerned by the reject.
              
                 The CPE SHOULD perform an exact match with this
                 string without any attempts at number
                 normalization.";
            }
          }

          list FollowMe {
            key "Number Order";
            description
              "This object defines the FollowMe destinations mapping
               definition, in the provided sequence order.";
            leaf Enable {
              type boolean;
              default "false";
              description
                "Enables or disables this FollowMe sequence item.";
            }
            leaf Delay {
              type uint32;
              description
                "Delay in {{units}} before next FollowMe sequence
                 item applies.";
            }
            leaf Number {
              type string {
                length "0..32";
              }
              description
                "Directory number to which all incoming calls to
                 this line are forwarded to after
                 {{param|Delay}}, when {{param|#.FollowMeEnable}}
                 is {{true}}.  In this case,
                 {{param|#.CallForwardOnNoAnswerNumber}} is not
                 used.";
            }
            leaf Order {
              type uint32;
              description
                "For a given {{param|Number}}, defines the order of
                 this item in the FollowMe sequence.";
            }
          }

          container Voice2Mail {
            description
              "Voice to mail specific attributes.  Applies only if
               {{param|#.VoiceMailEnable}} is set to {{true}}.";
            leaf Enable {
              type boolean;
              description
                "Enable or disable voice mail notification.";
            }
            leaf MaxMessageLength {
              type uint32;
              description
                "Defines the maximum amount of time in {{units}} of
                 an incoming message.  Use this when there are
                 many users and disk space is limited.  A value
                 of 0 means there will be no maximum time limit
                 enforced.";
            }
            leaf Attach {
              type boolean;
              description
                "Indicates if the message is sent as an attachment
                 in voice mail notification.";
            }
            leaf KeepLocal {
              type boolean;
              description
                "Whether the voice to mail message is kept on the
                 CPE after sending the mail.  Applicable only if
                 {{param|Attach}} is {{true}}.";
            }
            leaf EMailAddress {
              type string;
              description
                "E-mail for voice to mail notification messages.";
            }
          }
        }
      }
    }

    list Interwork {
      key "Alias";
      description
        "Each entry in this table configures Inter-Working Function
         switching features.
      
         It is mutually exclusive with the
         {{object|.CallControl}} object which is used in case of
         PBX or Endpoint capabilities.";
      leaf Enable {
        type boolean;
        default "false";
        description
          "Enable or disable this {{object}} instance.";
      }
      leaf QuiescentMode {
        type boolean;
        description
          "If {{true}}, when {{param|Enable}} is set to {{false}}
           in-progress sessions remain intact, but no new
           sessions are allowed.  When all sessions are
           terminated, the {{object}} is disabled.";
      }
      leaf Status {
        type enumeration {
          enum "Up";
          enum "Error";
          enum "Quiescent";
          enum "Disabled";
        }
        config false;
        default "Disabled";
        description
          "Indicates the status of this {{object}} instance.";
      }
      leaf OperationalStatus {
        type enumeration {
          enum "InService";
          enum "OutOfService";
          enum "NetworkServersOffline";
        }
        config false;
        default "OutOfService";
        description
          "Indicates the operational status of the {{object}}
           connections when {{param|Status}} is
           {{enum|Up|Status}}.  {{enum}}";
      }
      leaf OperationalStatusReason {
        type string {
          length "0..256";
        }
        config false;
        description
          "Human-readable string identifying the reason or
           explanation for the current
           {{param|OperationalStatus}}.";
      }
      leaf NetworkConnectionMode {
        type enumeration {
          enum "Static";
          enum "RegisterDynamic";
          enum "RegisterLearn";
          enum "RegisterStatic";
        }
        description
          "This parameter indicates whether or not the CPE supports
           a registration procedure that conveys its signaling IP
           address:port to the network.  This parameter also
           indicates whether the network-facing Client object and
           its parameters are statically provisioned by the ACS
           or dynamically created by the CPE.  {{enum}}";
      }
      leaf UserConnectionMode {
        type enumeration {
          enum "Static";
          enum "RegisterDynamic";
          enum "RegisterLearn";
        }
        description
          "This parameter indicates whether or not an externally
           connected user device supports a registration
           procedure to convey its signaling address to the CPE.
           This parameter also indicates whether the user-facing
           objects and parameters that contain the external user
           device signaling address are statically provisioned by
           the ACS or dynamically learned by the CPE.  {{enum}}";
      }
      leaf E164Mode {
        type boolean;
        description
          "This attribute indicates whether or not the CPE performs
           E.164 routing of incoming requests received from the
           service provider network when the target Endpoint is a
           PBX.";
      }
      leaf NetworkAuthenticationChallengeMode {
        type enumeration {
          enum "PassThru";
          enum "RespondLocal";
          enum "Hop-by-Hop";
        }
        description
          "This parameter indicates how the CPE treats
           authentication challenges received from the service
           provider network.  This parameter only has meaning
           when the CPE supports an externally connected user
           device (e.g., the CPE is acting as a gateway between
           the user device and the network).  {{enum}}";
      }
      leaf NetworkIPAddress {
        type types:IPAddress;
        config false;
        description
          "The network IP Address of the CPE.  The CPE MUST resolve
           this when the {{object|.Interwork.{i}.}} object is
           created.
        
           Note: In case of multiple network IP addresses, the
           choice is left to the CPE.";
      }
      leaf InterworkingRuleSetURI {
        type string {
          length "0..256";
        }
        description
          "URI of the Interworking Rule Set for this {{object}}
           instance.";
      }
      leaf InterworkingRuleSetInterval {
        type uint32;
        description
          "The duration in {{units}} of the interval for which the
           CPE SHOULD send request to refresh the Interworking
           Rule Set.
        
           A value of '0' indicates that this feature is
           disabled.";
      }
      leaf InterworkingRuleSetTime {
        type yang:date-and-time;
        description
          "An absolute time reference in UTC to determine when the
           CPE will send a request to refresh the Interworking
           Rule Set.  Each refresh request MUST occur at this
           reference time plus or minus an integer multiple of
           the {{param|InterworkingRuleSetInterval}}.
        
           {{param}} is used only to set the ''phase'' of refresh
           requests.  The actual value of {{param}} can be
           arbitrarily far into the past or future.
        
           For example, if {{param|InterworkingRuleSetInterval}}
           is 86400 (a day) and if {{param}} is set to UTC
           midnight on some day (in the past, present, or future)
           then the refresh requests will occur every day at UTC
           midnight.  These MUST begin on the very next midnight,
           even if {{param}} refers to a day in the future.
        
           The Unknown Time value defined in
           {{bibref|TR-106a2|section 3.2}} indicates that no
           particular time reference is specified.  That is, the
           CPE MAY locally choose the time reference, and needs
           only to adhere to the specified
           {{param|InterworkingRuleSetInterval}}.
        
           If absolute time is not available to the CPE, its
           behavior MUST be the same as if the {{param}}
           parameter was set to the Unknown Time value.";
      }
      leaf FirewallRuleSetURI {
        type string {
          length "0..256";
        }
        description
          "URI of the Firewall Rule Set for this {{object}}
           instance.";
      }
      leaf FirewallRuleSetInterval {
        type uint32;
        description
          "The duration in {{units}} of the interval for which the
           CPE SHOULD send request to refresh the Firewall Rule
           Set.
        
           A value of '0' indicates that this feature is
           disabled.";
      }
      leaf FirewallRuleSetTime {
        type yang:date-and-time;
        description
          "An absolute time reference in UTC to determine when the
           CPE will send a request to refresh the Firewall Rule
           Set.  Each refresh request MUST occur at this
           reference time plus or minus an integer multiple of
           the {{param|FirewallRuleSetInterval}}.
        
           {{param}} is used only to set the ''phase'' of refresh
           requests.  The actual value of {{param}} can be
           arbitrarily far into the past or future.
        
           For example, if {{param|FirewallRuleSetInterval}} is
           86400 (a day) and if {{param}} is set to UTC midnight
           on some day (in the past, present, or future) then the
           refresh requests will occur every day at UTC midnight.
           These MUST begin on the very next midnight, even if
           {{param}} refers to a day in the future.
        
           The Unknown Time value defined in
           {{bibref|TR-106a2|section 3.2}} indicates that no
           particular time reference is specified.  That is, the
           CPE MAY locally choose the time reference, and needs
           only to adhere to the specified
           {{param|FirewallRuleSetInterval}}.
        
           If absolute time is not available to the CPE, its
           behavior MUST be the same as if the {{param}}
           parameter was set to the Unknown Time value.";
      }
      leaf InterworkName {
        type string {
          length "0..256";
        }
        description
          "Human-readable string identifying the name or explanation
           for this {{object}}.";
      }
      leaf ProxyServer {
        type string {
          length "0..256";
        }
        description
          "Reference to the {{object|.SIP.Proxy}} associated with
           this {{object}}.  {{reference}}";
      }
      leaf Networks {
        type string;
        description
          "{{list}} {{reference}}
        
           List of available Networks for routing calls.";
      }
      leaf E164Client {
        type string {
          length "0..256";
        }
        description
          "This parameter is MUST contain the {{object|.SIP.Client}}
           for all {{object|.Trunk}} objects referenced in the
           {{object|Map}} table when {{param|E164Mode}} =
           {{true}}.";
      }

      list UserInterface {
        key "Registrar";
        description
          "Each table entry references a row in the
           {{object|.SIP.Registrar}} table to identify the User
           IP address and listening port for the Device and the
           Network to route calls to.";
        leaf Enable {
          type boolean;
          default "false";
          description
            "Enable ({{true}}) or disable ({{false}}) {{object}}.";
        }
        leaf Registrar {
          type string {
            length "0..256";
          }
          description
            "The {{object|.SIP.Registrar}} to use with this
             {{object|#}}.  The value of {{param}} MUST be unique
             over all {{object|.Interwork.{i}.}}.
          
             {{reference}}";
        }
        leaf Network {
          type string {
            length "0..256";
          }
          description
            "If not null this provides the appropriate
             {{object|.SIP.Network}} to route calls from this
             User server to.
          
             {{reference}}";
        }
      }

      list Map {
        key "Alias";
        description
          "For interworking use cases such as SIP-ISDN PBX plug and
           ESBC : mapping instance between a Network interface
           and a User extension.";
        leaf Enable {
          type boolean;
          default "false";
          description
            "Enable ({{true}}) or disable ({{false}}) this
             connection mapping.";
        }
        leaf Status {
          type enumeration {
            enum "Active";
            enum "InActive";
          }
          config false;
          default "InActive";
          description
            "Indicates the status of this connection mapping.
             {{enum}}";
        }
        leaf StatusDescription {
          type string {
            length "0..256";
          }
          config false;
          description
            "Human-readable string identifying the reason or
             explanation of the current mapping {{param|Status}}.";
        }
        leaf LastTime {
          type yang:date-and-time;
          config false;
          description
            "The last time the Status was updated.";
        }
        leaf Origin {
          type enumeration {
            enum "AutoConfigured";
            enum "Static";
          }
          config false;
          default "Static";
          description
            "Mechanism via which this connection mapping was
             assigned.  {{enum}}";
        }
        leaf NetworkConnection {
          type string {
            length "0..256";
          }
          description
            "{{reference}}.  This parameter can only be modified if
             {{param|Origin}} is {{enum|Static|Origin}}.";
        }
        leaf UserConnection {
          type string {
            length "0..256";
          }
          description
            "{{reference}}.  This parameter can only be modified if
             {{param|Origin}} is {{enum|Static|Origin}}.";
        }
        leaf DigitMap {
          type string {
            length "0..256";
          }
          default "";
          description
            "Digit map controlling digit collection on a User
             interface.  The string defines the criteria to be
             met as digits are collected before an outgoing
             request (e.g., a SIP INVITE) can be initiated.
          
             The syntax of this parameter is exactly the syntax
             used by MGCP as defined in {{bibref|RFC3435|Section
             2.1.5}}.
          
             This parameter is applicable only if the User
             interface supports per digit dialing and the Network
             interface supports en-bloc dialing only.";
        }
        leaf DigitMapEnable {
          type boolean;
          default "true";
          description
            "Enables use of {{param|DigitMap}}.";
        }
        leaf Priority {
          type uint32 {
            range "1..max";
          }
          description
            "Indicates the priority for this combination of
             Network-to-User mapping, where 1 is the highest
             priority.  Where the priority differs between
             entries in this table, the CPE SHOULD use the
             highest priority (lowest numbered) entry.  Where the
             priorities are equal among multiple entries, the CPE
             MAY apply a local criterion for choosing among them.";
        }
      }
    }

    list CallLog {
      key "Alias";
      config false;
      description
        "This table contains a list of calls.  An entry is similar
         to a CDR (Call Detail Record) as used in PBX or on
         mobile phones.
      
         An entry is created each time a call is terminated.  If
         the number of {{object|.CallLog}} exceeds
         {{param|.Capabilities.MaxCallLogCount}}, the CPE SHOULD
         remove the oldest {{object|.CallLog}} object on basis of
         {{param|Start}} parameter.";
      leaf CallingPartyNumber {
        type string {
          length "0..256";
        }
        description
          "Number of the party originating the call.";
      }
      leaf CalledPartyNumber {
        type string {
          length "0..256";
        }
        description
          "Number of destination party of the call.";
      }
      leaf Source {
        type string {
          length "0..256";
        }
        description
          "Party originating the call.
        
           {{reference}}
        
           {{object|.Trunk}},
           {{object|.SIP.Registrar.{i}.Account}} and
           {{object|.SIP.Client}} objects SHOULD be referenced
           only when {{object|.Interwork}} is in use.";
      }
      leaf Destination {
        type string {
          length "0..256";
        }
        description
          "Destination party of the call.
        
           {{reference}}
        
           {{object|.Trunk}},
           {{object|.SIP.Registrar.{i}.Account}} and
           {{object|.SIP.Client}} objects SHOULD be only
           referenced only when {{object|.Interwork}} is in use.";
      }
      leaf RemoteParty {
        type string {
          length "0..32";
        }
        description
          "The phone number of the remote party after the dial plan
           has been processed.";
      }
      leaf UsedLine {
        type string {
          length "0..256";
        }
        description
          "The {{object|.CallControl.Line}} used to process the
           call.
        
           {{reference}}
        
           When {{object|.Interwork}} is in use, this parameter
           is {{empty}}.";
      }
      leaf UsedExtensions {
        type string;
        description
          "{{list}} {{reference}}
        
           For an incoming call multiple
           {{object|.CallControl.Extension}} objects can be
           involved till one user answers the call.
        
           When {{object|.Interwork}} is in use, this parameter
           is {{empty}}.";
      }
      leaf Direction {
        type enumeration {
          enum "Incoming";
          enum "Outgoing";
        }
        description
          "Direction of the call.";
      }
      leaf Start {
        type yang:date-and-time;
        description
          "Start of the call.";
      }
      leaf Duration {
        type uint32;
        description
          "Length of the call in {{units}}.";
      }
      leaf CallTerminationCause {
        type enumeration {
          enum "NoExtensionsMapped";
          enum "NoExtensionsAvailable";
          enum "AnonymousCallRejection";
          enum "CallWaitingRejected";
          enum "CallForwardingUnconditional";
          enum "CallForwardingBusy";
          enum "CallForwardingNoReply";
          enum "LocalDisconnect";
          enum "LocalForbidden";
          enum "LocalTimeout";
          enum "LocalMediaError.";
          enum "LocalPriority.";
          enum "LocalReject";
          enum "LocalTransfer";
          enum "LocalInternalError";
          enum "RemoteDisconnect";
          enum "RemoteBadRequest";
          enum "RemoteForbidden";
          enum "RemoteNotFound";
          enum "RemoteReject";
          enum "RemoteNotAllowed";
          enum "RemoteNotAcceptable";
          enum "RemoteTimeout";
          enum "RemoteUnavailable";
          enum "RemoteBusy";
          enum "RemoteNotSupported";
          enum "RemoteNetworkFailure";
        }
        description
          "The call termination cause.
        
           The parameter MAY instead indicate a vendor-specific
           cause, which MUST use the format defined in
           {{bibref|TR-106}}.";
      }

      list SignalingPerformance {
        key "Protocol";
        min-elements 1;
        description
          "This table contains signaling performance statistics for
           each protocol involved in the call.";
        leaf Protocol {
          type enumeration {
            enum "H.323";
            enum "SIP";
          }
          description
            "Protocol for which this signaling performance
             statistics are available.";
        }
        leaf CallSetupDelay {
          type uint32;
          description
            "The time between the instant a system receives a call
             attempt and the instant of invitation of ringing at
             the call receiver end instrument in {{units}}.";
        }
        leaf OutgoingMediaEstablishDelay {
          type int32;
          description
            "The time in {{units}} between :
          
             :- the instant a system has received information
             that the called party is connected
          
             :- the instant the first media packet goes out the
             CPE
          
             The value could be negative if a media packet is
             sent before the connection establishment.";
        }
        leaf IncomingMediaEstablishDelay {
          type int32;
          description
            "The time in {{units}} between :
          
             :- the instant a system has received information
             that the called party is connected
          
             :- the instant the first media packet goes into the
             CPE
          
             The value could be negative if a media packet
             arrives before the connection establishment.";
        }
      }

      list Session {
        key "SessionID";
        description
          "Session information within one call.";
        leaf StreamType {
          type enumeration {
            enum "Audio";
            enum "Video";
            enum "Fax";
            enum "Modem";
          }
          description
            "The type of media stream used in this session.";
        }
        leaf Start {
          type yang:date-and-time;
          description
            "The time that the session started, in UTC.";
        }
        leaf Duration {
          type uint32;
          description
            "Length of the session in {{units}}.";
        }
        leaf SessionID {
          type string {
            length "0..16";
          }
          description
            "Session identifier.";
        }

        container Source {
          description
            "The source of the session information within one call.";

          container RTP {
            description
              "The RTP part of the source session information.";
            leaf FarEndIPAddress {
              type types:IPAddress;
              description
                "The IP address of far end VoIP device.";
            }
            leaf FarEndUDPPort {
              type uint32 {
                range "0..65535";
              }
              description
                "The UDP port used for current session in the far
                 end device.";
            }
            leaf LocalUDPPort {
              type uint32 {
                range "0..65535";
              }
              description
                "The local UDP port used for current session.";
            }
            leaf MinJitter {
              type int32 {
                range "-1..max";
              }
              description
                "The minimum relative transit time in {{units}}
                 between two packets as defined in
                 {{bibref|RFC3611}}.
              
                 A value of -1 indicates no reliable value is
                 available.";
            }
            leaf MaxJitter {
              type int32 {
                range "-1..max";
              }
              description
                "The maximum relative transit time in {{units}}
                 between two packets as defined in
                 {{bibref|RFC3611}}.
              
                 A value of -1 indicates no reliable value is
                 available.";
            }
            leaf MeanJitter {
              type int32 {
                range "-1..max";
              }
              description
                "The mean relative transit time in {{units}} between
                 each two packet series as defined in
                 {{bibref|RFC3611}}.
              
                 A value of -1 indicates no reliable value is
                 available.";
            }
            leaf PacketDelayVariation {
              type int32 {
                range "-1..max";
              }
              description
                "1-Point Packet Delay Variation according to
                 {{bibref|Y.1540}} in {{units}}.
              
                 A value of -1 indicates no reliable value is
                 available.";
            }
            leaf BufferDelay {
              type int32 {
                range "-1..max";
              }
              description
                "Average delay in {{units}} added by buffer
                 processing.
              
                 A value of -1 indicates no reliable value is
                 available.";
            }
            leaf BurstCount {
              type types:StatsCounter32;
              description
                "The number of bursts (as defined in
                 {{bibref|RFC3611}}) that occur during this
                 session (during one burst several packets MAY be
                 lost).
              
                 The burst's threshold is configured with the
                 parameter {{param|.VoIPProfile.{i}.RTP.Gmin}}.";
            }
            leaf PacketsReceived {
              type types:StatsCounter64;
              description
                "Total number of RTP packets received for this
                 session.";
            }
            leaf PacketsSent {
              type types:StatsCounter64;
              description
                "Total number of RTP packets sent for this session.";
            }
            leaf PacketsLost {
              type types:StatsCounter32;
              description
                "Total number of RTP packets that have been lost for
                 this session (see {{bibref|RFC3611}}).";
            }
            leaf PacketsDiscarded {
              type types:StatsCounter32;
              description
                "Total number of RTP packets that have been
                 discarded for this session (see
                 {{bibref|RFC3611}}).";
            }
            leaf BytesReceived {
              type types:StatsCounter64;
              description
                "Total number of bytes received for this session.";
            }
            leaf BytesSent {
              type types:StatsCounter64;
              description
                "Total number of bytes sent for this session.";
            }
            leaf ReceivePacketLossRate {
              type uint32 {
                range "0..100";
              }
              description
                "Current receive packet loss rate in percent,
                 calculated as defined in
                 {{bibref|RFC3550|Section 6.4}}.";
            }
            leaf FarEndPacketLossRate {
              type uint32 {
                range "0..100";
              }
              description
                "Current far end receive packet lost rate in
                 percent, calculated as defined in
                 {{bibref|RFC3550|Section 6.4}}.";
            }
            leaf ReceiveInterarrivalJitter {
              type int32 {
                range "-1..max";
              }
              description
                "Current receive interarrival jitter in timestamp
                 units.  Calculated from J(i) as defined in
                 {{bibref|RFC3550|Section 6.4}}.
              
                 A value of -1 indicates no reliable value is
                 available.";
            }
            leaf FarEndInterarrivalJitter {
              type int32 {
                range "-1..max";
              }
              description
                "Current Interarrival jitter in timestamp units as
                 reported from the far-end device via RTCP.
                 Calculated from J(i) as defined in
                 {{bibref|RFC3550|Section 6.4}}.
              
                 A value of -1 indicates no reliable value is
                 available.";
            }
            leaf AverageReceiveInterarrivalJitter {
              type int32 {
                range "-1..max";
              }
              description
                "Average receive interarrival jitter in timestamp
                 units since the beginning of the current call.
                 Calculated as the average of the interarrival
                 jitter values reported by the far-end.
              
                 A value of -1 indicates no reliable value is
                 available.";
            }
            leaf AverageFarEndInterarrivalJitter {
              type int32 {
                range "-1..max";
              }
              description
                "Average far-end interarrival jitter in timestamp
                 units since the beginning of the current call.
                 Calculated as the average of the interarrival
                 jitter values reported by the far-end.
              
                 A value of -1 indicates no reliable value is
                 available.";
            }
            leaf RoundTripDelay {
              type int32 {
                range "-1..max";
              }
              description
                "Current round trip delay in {{units}} calculated as
                 defined in {{bibref|RFC3550|Section 6.4}}.
              
                 A value of -1 indicates no reliable value is
                 available.";
            }
            leaf AverageRoundTripDelay {
              type int32 {
                range "-1..max";
              }
              description
                "Average round trip delay in {{units}} since the
                 beginning of the current session.
              
                 A value of -1 indicates no reliable value is
                 available.";
            }
            leaf SamplingFrequency {
              type uint32;
              description
                "Sample frequency in {{units}} used by the codec for
                 this session.";
            }
          }

          container DSP {
            description
              "The DSP part of the line session information.";

            container ReceiveCodec {
              description
                "The receive codec used in this session.";
              leaf Codec {
                type string {
                  length "0..256";
                }
                description
                  "The codec in use for the incoming voice stream.
                
                   {{reference}}";
              }
              leaf SilenceSuppression {
                type boolean;
                description
                  "Whether or not silence suppression is in use for
                   the incoming voice stream.";
              }
              leaf Overruns {
                type uint32;
                description
                  "Total number of times the receive jitter buffer
                   has overrun for this session.";
              }
              leaf Underruns {
                type uint32;
                description
                  "Total number of times the receive jitter buffer
                   has underrun for this session.";
              }
            }

            container TransmitCodec {
              description
                "The transmit codec used in this session.";
              leaf Codec {
                type string {
                  length "0..256";
                }
                description
                  "The codec in use for the outgoing voice stream.
                
                   {{reference}}";
              }
              leaf SilenceSuppression {
                type boolean;
                description
                  "Whether or not silence suppression is in use for
                   the outgoing voice stream.";
              }
              leaf PacketizationPeriod {
                type uint32;
                description
                  "Current outgoing packetization period in
                   {{units}}.";
              }
              leaf Overruns {
                type uint32;
                description
                  "Total number of times the transmit jitter buffer
                   has overrun for this session.";
              }
              leaf Underruns {
                type uint32;
                description
                  "Total number of times the transmit jitter buffer
                   has underrun for this session.";
              }
            }
          }

          container VoiceQuality {
            description
              "VoIP Statistics for current session instance.";
            leaf VoIPQualityIndicator {
              type uint32 {
                range "min..65535";
              }
              description
                "{{list|representing the VoIP quality calculated for
                 consecutive intervals of the session}} The
                 interval is specified by
                 {{param|.VoIPProfile.{i}.QICalculationInterval}}
                 and the quality model used is specified by
                 {{param|.VoIPProfile.{i}.QIModelUsed}}.
              
                 The statistics values in this list MUST be in
                 time order, with the oldest one first and the
                 most recent one last.
              
                 For long sessions the number of values might
                 exceed the limit given by
                 {{param|.Capabilities.QualityIndicator.MaxQIValues}}.
                 In that case, the CPE MUST remove the oldest
                 values to keep the number of reported values
                 within the limit.
              
                 The interpretation of the QI values are
                 algorithm-specific, the only constraints being
                 the range and the fact that lower values
                 indicate worse quality than do higher values.
              
                 For instance, if {{param}} is reported as
                 \"78,57,88,79,34,56\", and
                 {{param|.VoIPProfile.{i}.QICalculationInterval}}
                 is 10 seconds, the quality during the first ten
                 seconds was 78, the next ten seconds 57, and so
                 on.  The last reported value (here 56) might
                 cover a shorter time period than
                 {{param|.VoIPProfile.{i}.QICalculationInterval}},
                 but the length can be deduced using
                 {{param|##.Duration}}.";
            }
            leaf WorstVoIPQualityIndicatorsValues {
              type uint32 {
                range "min..65535";
              }
              description
                "{{list|representing the worst VoIP quality
                 indicators calculated during the whole session}}
              
                 Only the N worst values are stored, where N is
                 the limit stored in the
                 {{param|.VoIPProfile.{i}.NumberOfWorstQIValues}}
                 attribute.
              
                 The values are given in the same
                 algorithm-specific representation as
                 {{param|VoIPQualityIndicator}}, and MUST be in
                 quality-order with the lowest value first.
              
                 Example: \"34,56,57\" are the 3 worst values
                 calculated during the call.";
            }
            leaf WorstVoIPQualityIndicatorTimestamps {
              type uint32 {
                range "min..65535";
              }
              description
                "{{list}} Each value represents the timestamp index,
                 given in units of
                 {{param|.VoIPProfile.{i}.QICalculationInterval}},
                 when the corresponding value in
                 {{param|WorstVoIPQualityIndicatorsValues}} was
                 calculated.
              
                 The first index is number 1.
              
                 Only the N worst values are stored, where N is
                 the limit stored in
                 {{param|.VoIPProfile.{i}.NumberOfWorstQIValues}}.
              
                 Example: if
                 {{param|.VoIPProfile.{i}.QICalculationInterval}}
                 is equal to 10 (seconds), the value \"6,2,5\"
                 designates the time intervals 50-60 s, 10-20 s,
                 and 40-50 s when the 3 worst values were
                 calculated.";
            }
          }
        }

        container Destination {
          description
            "The destination part of session information within one
             call.";

          container RTP {
            description
              "The RTP part of the destination session information.";
            leaf FarEndIPAddress {
              type types:IPAddress;
              description
                "The IP address of far end VoIP device.";
            }
            leaf FarEndUDPPort {
              type uint32 {
                range "0..65535";
              }
              description
                "The UDP port used for current session in the far
                 end device.";
            }
            leaf LocalUDPPort {
              type uint32 {
                range "0..65535";
              }
              description
                "The local UDP port used for current session.";
            }
            leaf MinJitter {
              type int32 {
                range "-1..max";
              }
              description
                "The minimum relative transit time in {{units}}
                 between two packets as defined in
                 {{bibref|RFC3611}}.
              
                 A value of -1 indicates no reliable value is
                 available.";
            }
            leaf MaxJitter {
              type int32 {
                range "-1..max";
              }
              description
                "The maximum relative transit time in {{units}}
                 between two packets as defined in
                 {{bibref|RFC3611}}.
              
                 A value of -1 indicates no reliable value is
                 available.";
            }
            leaf MeanJitter {
              type int32 {
                range "-1..max";
              }
              description
                "The mean relative transit time in {{units}} between
                 each two packet series as defined in
                 {{bibref|RFC3611}}.
              
                 A value of -1 indicates no reliable value is
                 available.";
            }
            leaf PacketDelayVariation {
              type int32 {
                range "-1..max";
              }
              description
                "1-Point Packet Delay Variation according to
                 {{bibref|Y.1540}} in {{units}}.
              
                 A value of -1 indicates no reliable value is
                 available.";
            }
            leaf BufferDelay {
              type int32 {
                range "-1..max";
              }
              description
                "Average delay in {{units}} added by buffer
                 processing.
              
                 A value of -1 indicates no reliable value is
                 available.";
            }
            leaf BurstCount {
              type types:StatsCounter32;
              description
                "The number of bursts (as defined in
                 {{bibref|RFC3611}}) that occur during this
                 session (during one burst several packets MAY be
                 lost).
              
                 The burst's threshold is configured with the
                 parameter {{param|.VoIPProfile.{i}.RTP.Gmin}}.";
            }
            leaf PacketsReceived {
              type types:StatsCounter64;
              description
                "Total number of RTP packets received for this
                 session.";
            }
            leaf PacketsSent {
              type types:StatsCounter64;
              description
                "Total number of RTP packets sent for this session.";
            }
            leaf PacketsLost {
              type types:StatsCounter32;
              description
                "Total number of RTP packets that have been lost for
                 this session (see {{bibref|RFC3611}}).";
            }
            leaf PacketsDiscarded {
              type types:StatsCounter32;
              description
                "Total number of RTP packets that have been
                 discarded for this session (see
                 {{bibref|RFC3611}}).";
            }
            leaf BytesReceived {
              type types:StatsCounter64;
              description
                "Total number of bytes received for this session.";
            }
            leaf BytesSent {
              type types:StatsCounter64;
              description
                "Total number of bytes sent for this session.";
            }
            leaf ReceivePacketLossRate {
              type uint32 {
                range "0..100";
              }
              description
                "Current receive packet loss rate in percent,
                 calculated as defined in
                 {{bibref|RFC3550|Section 6.4}}.";
            }
            leaf FarEndPacketLossRate {
              type uint32 {
                range "0..100";
              }
              description
                "Current far end receive packet lost rate in
                 percent, calculated as defined in
                 {{bibref|RFC3550|Section 6.4}}.";
            }
            leaf ReceiveInterarrivalJitter {
              type int32 {
                range "-1..max";
              }
              description
                "Current receive interarrival jitter in timestamp
                 units.  Calculated from J(i) as defined in
                 {{bibref|RFC3550|Section 6.4}}.
              
                 A value of -1 indicates no reliable value is
                 available.";
            }
            leaf FarEndInterarrivalJitter {
              type int32 {
                range "-1..max";
              }
              description
                "Current Interarrival jitter in timestamp units as
                 reported from the far-end device via RTCP.
                 Calculated from J(i) as defined in
                 {{bibref|RFC3550|Section 6.4}}.
              
                 A value of -1 indicates no reliable value is
                 available.";
            }
            leaf AverageReceiveInterarrivalJitter {
              type int32 {
                range "-1..max";
              }
              description
                "Average receive interarrival jitter in timestamp
                 units since the beginning of the current call.
                 Calculated as the average of the interarrival
                 jitter values reported by the far-end.
              
                 A value of -1 indicates no reliable value is
                 available.";
            }
            leaf AverageFarEndInterarrivalJitter {
              type int32 {
                range "-1..max";
              }
              description
                "Average far-end interarrival jitter in timestamp
                 units since the beginning of the current call.
                 Calculated as the average of the interarrival
                 jitter values reported by the far-end.
              
                 A value of -1 indicates no reliable value is
                 available.";
            }
            leaf RoundTripDelay {
              type int32 {
                range "-1..max";
              }
              description
                "Current round trip delay in {{units}} calculated as
                 defined in {{bibref|RFC3550|Section 6.4}}.
              
                 A value of -1 indicates no reliable value is
                 available.";
            }
            leaf AverageRoundTripDelay {
              type int32 {
                range "-1..max";
              }
              description
                "Average round trip delay in {{units}} since the
                 beginning of the current session.
              
                 A value of -1 indicates no reliable value is
                 available.";
            }
            leaf SamplingFrequency {
              type uint32;
              description
                "Sample frequency in {{units}} used by the codec for
                 this session.";
            }
          }

          container DSP {
            description
              "The DSP part of the destination session information.";

            container ReceiveCodec {
              description
                "The receive codec used in this session.";
              leaf Codec {
                type string {
                  length "0..256";
                }
                description
                  "The codec in use for the incoming voice stream.
                
                   {{reference}}";
              }
              leaf SilenceSuppression {
                type boolean;
                description
                  "Whether or not silence suppression is in use for
                   the incoming voice stream.";
              }
              leaf Overruns {
                type uint32;
                description
                  "Total number of times the receive jitter buffer
                   has overrun for this session.";
              }
              leaf Underruns {
                type uint32;
                description
                  "Total number of times the receive jitter buffer
                   has underrun for this session.";
              }
            }

            container TransmitCodec {
              description
                "The transmit codec used in this session.";
              leaf Codec {
                type string {
                  length "0..256";
                }
                description
                  "The codec in use for the outgoing voice stream.
                
                   {{reference}}";
              }
              leaf SilenceSuppression {
                type boolean;
                description
                  "Whether or not silence suppression is in use for
                   the outgoing voice stream.";
              }
              leaf PacketizationPeriod {
                type uint32;
                description
                  "Current outgoing packetization period in
                   {{units}}.";
              }
              leaf Overruns {
                type uint32;
                description
                  "Total number of times the transmit jitter buffer
                   has overrun for this session.";
              }
              leaf Underruns {
                type uint32;
                description
                  "Total number of times the transmit jitter buffer
                   has underrun for this session.";
              }
            }
          }

          container VoiceQuality {
            description
              "VoIP Statistics for current session instance.";
            leaf VoIPQualityIndicator {
              type uint32 {
                range "min..65535";
              }
              description
                "{{list|representing the VoIP quality calculated for
                 consecutive intervals of the session}} The
                 interval is specified by
                 {{param|.VoIPProfile.{i}.QICalculationInterval}}
                 and the quality model used is specified by
                 {{param|.VoIPProfile.{i}.QIModelUsed}}.
              
                 The statistics values in this list MUST be in
                 time order, with the oldest one first and the
                 most recent one last.
              
                 For long sessions the number of values might
                 exceed the limit given by
                 {{param|.Capabilities.QualityIndicator.MaxQIValues}}.
                 In that case, the CPE MUST remove the oldest
                 values to keep the number of reported values
                 within the limit.
              
                 The interpretation of the QI values are
                 algorithm-specific, the only constraints being
                 the numeric range and the fact that lower values
                 indicate worse quality than do higher values.
              
                 For instance, if {{param}} is reported as
                 \"78,57,88,79,34,56\", and
                 {{param|.VoIPProfile.{i}.QICalculationInterval}}
                 is 10 seconds, the quality during the first ten
                 seconds was 78, the next ten seconds 57, and so
                 on.  The last reported value (here 56) might
                 cover a shorter time period than
                 {{param|.VoIPProfile.{i}.QICalculationInterval}},
                 but the length can be deduced using
                 {{param|##.Duration}}.";
            }
            leaf WorstVoIPQualityIndicatorsValues {
              type uint32 {
                range "min..65535";
              }
              description
                "{{list|representing the worst VoIP quality
                 indicators calculated during the whole session}}
              
                 Only the N worst values are stored, where N is
                 the limit stored in the
                 {{param|.VoIPProfile.{i}.NumberOfWorstQIValues}}
                 attribute.
              
                 The values are given in the same
                 algorithm-specific representation as
                 {{param|VoIPQualityIndicator}}, and MUST be in
                 quality-order with the lowest value first.
              
                 Example: \"34,56,57\" are the 3 worst values
                 calculated during the call.";
            }
            leaf WorstVoIPQualityIndicatorTimestamps {
              type uint32 {
                range "min..65535";
              }
              description
                "{{list}} Each value represents the timestamp index,
                 given in units of
                 {{param|.VoIPProfile.{i}.QICalculationInterval}},
                 when the corresponding value in
                 {{param|WorstVoIPQualityIndicatorsValues}} was
                 calculated.
              
                 The first index is number 1.
              
                 Only the N worst values are stored, where N is
                 the limit stored in
                 {{param|.VoIPProfile.{i}.NumberOfWorstQIValues}}.
              
                 Example: if
                 {{param|.VoIPProfile.{i}.QICalculationInterval}}
                 is equal to 10 (seconds), the value \"6,2,5\"
                 designates the time intervals 50-60 s, 10-20 s,
                 and 40-50 s when the 3 worst values were
                 calculated.";
            }
          }
        }
      }
    }

    list VoIPProfile {
      key "Alias";
      description
        "Configuration profile that can be shared by VoIP
         components.
      
         A VoIP Profile contains media transport configuration
         parameters that are common to different VoIP protocols.
      
         VoIP Profiles could be used by {{object|.SIP.Network.}},
         {{object|.SIP.Proxy.}}, {{object|.SIP.Network.}},
         {{object|.H323.Network.}} and {{object|.MGCP.Network.}}.";
      leaf Enable {
        type boolean;
        default "false";
        description
          "Enables or disables this VoIP profile.  If the value is
           set to {{false}}, all components using the profile are
           disabled, whatever their status is.";
      }
      leaf QuiescentMode {
        type boolean;
        description
          "If {{true}}, when {{param|Enable}} is set to {{false}}
           in-progress sessions remain intact, but no new
           sessions are allowed.  When all sessions are
           terminated, the {{object}} is disabled.";
      }
      leaf Name {
        type string {
          length "0..64";
        }
        default "";
        description
          "Human-readable string to identify the profile instance.";
      }
      leaf DTMFMethod {
        type enumeration {
          enum "InBand";
          enum "RFC4733";
          enum "SIPInfo";
        }
        default "InBand";
        description
          "{{list}} Method by which DTMF digits MUST be passed.
           {{enum}}
        
           If {{param|DTMFMethodG711}} is non-empty, then this
           parameter applies only when the current codec is not
           G.711.";
      }
      leaf DTMFMethodG711 {
        type enumeration {
          enum "InBand";
          enum "RFC4733";
          enum "SIPInfo";
          enum "";
        }
        default "";
        description
          "Method by which DTMF digits MUST be passed if the the
           current codec is G.711.  {{enum}}
        
           If {{empty}} indicates that the value of
           {{param|DTMFMethod}} is to apply whether or not the
           the the current codec is G.711.";
      }
      leaf QIModelUsed {
        type string {
          length "0..128";
        }
        description
          "Quality model which the CPE shall use to calculate the
           parameters
           {{param|.CallLog.{i}.Session.{i}.Source.VoiceQuality.VoIPQualityIndicator}}
           and
           {{param|.CallLog.{i}.Session.{i}.Destination.VoiceQuality.VoIPQualityIndicator}}.
           The value MUST be a member of the list reported by the
           {{param|.Capabilities.QualityIndicator.QIModelsSupported}}
           parameter.";
      }
      leaf QICalculationInterval {
        type uint32;
        description
          "The interval between successive calculations of
           {{param|.CallLog.{i}.Session.{i}.Source.VoiceQuality.VoIPQualityIndicator}}
           and
           {{param|.CallLog.{i}.Session.{i}.Destination.VoiceQuality.VoIPQualityIndicator}}
           values (in {{units}}).  If {{param}} is not set then
           only one final quality value covering the complete
           session is reported in
           {{param|.CallLog.{i}.Session.{i}.Source.VoiceQuality.VoIPQualityIndicator}}
           and
           {{param|.CallLog.{i}.Session.{i}.Destination.VoiceQuality.VoIPQualityIndicator}}.";
      }
      leaf NumberOfWorstQIValues {
        type uint32;
        description
          "The maximum number of worst quality indicators to store
           for each call.
        
           The CPE MUST permit {{param}} to be set to any value
           in the range from 0 to
           {{param|.Capabilities.QualityIndicator.MaxWorstQIValues}}.";
      }

      container RTP {
        description
          "VoIP profile parameters related to the voice stream sent
           via RTP.";
        leaf LocalPortMin {
          type uint32 {
            range "1..65535";
          }
          default "1024";
          description
            "Base of port range to be used for incoming RTP streams
             for this profile.";
        }
        leaf LocalPortMax {
          type uint32 {
            range "1..65535";
          }
          default "1024";
          description
            "Top of port range to be used for incoming RTP streams
             for this profile.";
        }
        leaf Gmin {
          type uint32 {
            range "1..255";
          }
          default "16";
          description
            "Minimum number of consecutive received packets after
             the end of an RTP Loss Event.  A Loss Event is
             defined as as a sequence of lost or discarded
             packets, possibly including islands of received
             packets.  Each island consists of up to ({{param}} -
             1) received packets (a sequence of {{param}}
             received packets terminates the Loss Event, and so
             is not an island).";
        }
        leaf DSCPMark {
          type uint32 {
            range "0..63";
          }
          description
            "Diffserv code point to be used for outgoing RTP and
             RTCP packets for this profile.  It is RECOMMENDED
             that by default the DSCP for RTP traffic be set to
             the value to indicate EF traffic.";
        }
        leaf VLANIDMark {
          type int32 {
            range "-1..max";
          }
          default "-1";
          description
            "VLAN ID (as defined in {{bibref|802.1Q-2005}}) to be
             used for outgoing RTP packets for this profile.  A
             value of -1 indicates the default value is to be
             used.
          
             If either {{param}} or
             {{param|EthernetPriorityMark}} is greater than zero,
             then the outgoing frames MUST be tagged.  Otherwise,
             the outgoing frames MAY be tagged or untagged.";
        }
        leaf EthernetPriorityMark {
          type int32 {
            range "-1..max";
          }
          default "-1";
          description
            "Ethernet priority code (as defined in
             {{bibref|802.1D-2004}}) to be used for outgoing RTP
             packets for this profile.  A value of -1 indicates
             the default value is to be used.
          
             If either {{param|VLANIDMark}} or {{param}} is
             greater than zero, then the outgoing frames MUST be
             tagged.  Otherwise, the outgoing frames MAY be
             tagged or untagged.";
        }
        leaf TelephoneEventPayloadType {
          type uint32 {
            range "0..128";
          }
          description
            "Payload type to be used for RTP telephone events.
          
             This parameter indicates the payload type to be used
             for DTMF events if transmission of DTMF information
             is in use according to {{bibref|RFC4733}}.";
        }
        leaf JitterBufferType {
          type enumeration {
            enum "Static";
            enum "Dynamic";
          }
          description
            "The indicates if the jitte buffer is static or dynamic.";
        }
        leaf JitterBufferMaxSize {
          type uint32;
          description
            "Maximal (or static) jitter buffer size in {{units}}.";
        }
        leaf JitterBufferMinSize {
          type uint32;
          description
            "Minimal jitter buffer size in {{units}}, not used if
             static buffer is used.";
        }
        leaf JitterBufferActualSize {
          type uint32;
          description
            "Actual jitter buffer size in {{units}}, if static
             buffer ist used equal to
             {{param|JitterBufferMaxSize}}.";
        }

        container RTCP {
          description
            "VoIP profile parameters related to RTCP.";
          leaf Enable {
            type boolean;
            description
              "Enable or disable RTCP.";
          }
          leaf TxRepeatInterval {
            type uint32 {
              range "1..max";
            }
            description
              "Transmission repeat interval, in {{units}}.";
          }
          leaf LocalCName {
            type string {
              length "0..64";
            }
            description
              "Local Cname (canonical name).";
          }
        }

        container SRTP {
          description
            "VoIP profile parameters for secure voice transmission
             via SRTP.";
          leaf Enable {
            type boolean;
            description
              "Enable or disable the use of SRTP.
            
               If RTCP is enabled, a {{true}} value of this
               parameter also implies the use of SRTCP.";
          }
          leaf KeyingMethods {
            type enumeration {
              enum "Null";
              enum "Static";
              enum "SDP";
              enum "IKE";
            }
            description
              "{{list|available keying methods}} {{enum}}";
          }
          leaf EncryptionKeySizes {
            type uint32;
            description
              "{{list|available encryption key sizes}}";
          }
        }

        container Redundancy {
          description
            "VoIP profile parameters for RTP payload redundancy as
             defined by {{bibref|RFC2198}}.";
          leaf Enable {
            type boolean;
            default "false";
            description
              "Enable or disable the use of RTP payload redundancy
               as defined by {{bibref|RFC2198}}.";
          }
          leaf PayloadType {
            type uint32 {
              range "0..127";
            }
            default "0";
            description
              "The Payload Type of RTP packet as defined in
               {{bibref|RFC2198}}.  Values SHOULD be within the
               range of dynamic Payload Types (96-127).";
          }
          leaf BlockPayloadType {
            type uint32 {
              range "0..127";
            }
            config false;
            default "0";
            description
              "Block Payload Type of redundancy packet.";
          }
          leaf FaxAndModemRedundancy {
            type int32 {
              range "-1..5";
            }
            default "-1";
            description
              "Specifies the redundancy number for fax and modem
               pass-through data transmissions.
            
               A non-negative value indicates that
               {{bibref|RFC2198}} is to be used for fax and modem
               pass-through data.  The value indicates the number
               of redundant copies to be transmitted (the total
               number transmitted is one plus this value).
            
               A value of -1 indicates {{bibref|RFC2198}} is not
               to be used for fax and modem pass-through data.
            
               If {{param|ModemRedundancy}} is present, then
               {{param}} applies only to fax transmissions, but
               not to modem transmissions.";
          }
          leaf ModemRedundancy {
            type int32 {
              range "-1..5";
            }
            default "-1";
            description
              "Specifies the redundancy number for modem
               pass-through data transmissions.
            
               A non-negative value indicates that
               {{bibref|RFC2198}} is to be used for modem
               pass-through data.  The value indicates the number
               of redundant copies to be transmitted (the total
               number transmitted is one plus this value).
            
               A value of -1 indicates {{bibref|RFC2198}} is not
               to be used for modem pass-through data.";
          }
          leaf DTMFRedundancy {
            type int32 {
              range "-1..5";
            }
            default "-1";
            description
              "Specifies the redundancy number for DTMF
               transmissions.
            
               A non-negative value indicates that
               {{bibref|RFC2198}} is to be used for DTMF.  The
               value indicates the number of redundant copies to
               be transmitted (the total number transmitted is
               one plus this value).
            
               A value of -1 indicates {{bibref|RFC2198}} is not
               to be used for DTMF.";
          }
          leaf VoiceRedundancy {
            type int32 {
              range "-1..5";
            }
            default "-1";
            description
              "Specifies the redundancy number for general voice
               transmissions.
            
               A non-negative value indicates that
               {{bibref|RFC2198}} is to be used for voice.  The
               value indicates the number of redundant copies to
               be transmitted (the total number transmitted is
               one plus this value).
            
               A value of -1 indicates {{bibref|RFC2198}} is not
               to be used for voice.";
          }
          leaf MaxSessionsUsingRedundancy {
            type uint32;
            default "0";
            description
              "The maximum number of sessions using
               {{bibref|RFC2198}} payload redundancy
               simultaneously in this profile.
            
               A value of zero indicates no explicit limit on the
               number of sessions using redundancy.";
          }
        }
      }

      container FaxT38 {
        description
          "T.38 Fax information for devices that support T.38 relay.";
        leaf MaxBitRate {
          type uint32 {
            range "0..65535";
          }
          default "14400";
          description
            "Maximum data rate in {{units}} for fax as defined in
             {{bibref|T.38}}.";
        }
        leaf HighSpeedRedundancy {
          type uint32 {
            range "0..3";
          }
          description
            "Specifies the packet-level redundancy for high-speed
             data transmissions (i.e., T.4 image data).";
        }
        leaf LowSpeedRedundancy {
          type uint32 {
            range "0..5";
          }
          description
            "Specifies the packet-level redundancy for low-speed
             data transmissions (i.e., T.30 handshaking
             information).";
        }
        leaf TCFMethod {
          type enumeration {
            enum "Local";
            enum "Network";
          }
          description
            "The method with which data is handled over the network.";
        }
      }
    }

    list CodecProfile {
      key "Alias";
      description
        "Table of codec profiles.  This table MUST be populated with
         the set of supported codecs matching
         {{object|.Capabilities.Codec.}}.  Additional entries can
         be added to use different configurations of codec or to
         use the same codec configuration in different CodecList
         parameters.";
      leaf Enable {
        type boolean;
        description
          "Enable or disable the use of this combination of codec
           parameters.";
      }
      leaf Codec {
        type string {
          length "0..256";
        }
        config false;
        description
          "{{reference}}";
      }
      leaf PacketizationPeriod {
        type string {
          length "0..64";
        }
        description
          "{{list}} Each item is a supported packetization period,
           in milliseconds, or continuous ranges of packetization
           periods as defined in
           {{param|.Capabilities.Codec.{i}.PacketizationPeriod}}.
        
           The ACS MAY restrict the set of packetization periods
           by modifying the value of this parameter to a more
           restricted set of values than is listed in
           {{param|.Capabilities.Codec.{i}.PacketizationPeriod}}.
           The CPE MUST ignore any values or portions of ranges
           outside of those specified in
           {{param|.Capabilities.Codec.{i}.PacketizationPeriod}}.";
      }
      leaf SilenceSuppression {
        type boolean;
        description
          "Indicates support for silence suppression for this codec.
           If silence suppression is supported, it can be
           disabled for this codec/bit-rate by setting this
           parameter to {{false}}.";
      }
    }

    container Tone {
      description
        "This object defines the contents of the tones and
         announcements generated locally by the VoIP device.";
      leaf DefautEventProfile {
        type string {
          length "0..256";
        }
        description
          "Reference to the default tone event profile.";
      }

      list Description {
        key "Alias";
        description
          "Each entry in this table defines the contents of an
           individual tone.
        
           The defaults given for this object apply only to
           explicit creation of an instance of this object and
           not to automatic creation of instances of this object
           due to creation of a parent object.";
        leaf ToneEnable {
          type boolean;
          default "false";
          description
            "Enables or disables the tone entry.  If a disabled tone
             entry is referenced, the result is that no tone is
             played.";
        }
        leaf ToneName {
          type string {
            length "0..64";
          }
          default "";
          description
            "Name of the tone.";
        }
        leaf TonePattern {
          type string {
            length "0..256";
          }
          description
            "This is the {{object|#.Pattern.{i}.}} object that
             begins this tone.  If the tone is specified by a
             tone file instead of a tone pattern, this parameter
             MUST be set to {{empty}}.
          
             {{reference}}";
        }
        leaf ToneFile {
          type string {
            length "0..256";
          }
          default "";
          description
            "The file name of a tone file locally present on the
             CPE.
          
             An ACS MUST use the Download method with
             FileType=\"4 Tone File\" as defined in
             {{bibref|TR-069a4|Annex A.3.2.8}} to download a tone
             file.
          
             If the tone is specified by a tone pattern instead
             of a tone file, this parameter MUST be {{empty}}.";
        }
        leaf ToneRepetitions {
          type uint32 {
            range "0..255";
          }
          default "0";
          description
            "The default number of times the data in
             {{param|ToneFile}} is repeated.  If the value is 0
             (zero) then {{param|ToneFile}} is played
             indefinitely.";
        }
        leaf ToneText {
          type string {
            length "0..64";
          }
          default "";
          description
            "The text to be displayed by on the screen of the VoIP
             device when the tone is played and no specific error
             message has been provided.
          
             This parameter is applicable only for VoIP devices
             capable text display.";
        }
      }

      list Pattern {
        key "Alias";
        description
          "Each entry in the table defines a single phase in an
           overall tone pattern.  Each phase identifies the entry
           that corresponds to the next phase.
        
           Each entry in the table refers to the entry that
           corresponds to the next phase of the pattern.  The
           table MAY be set up such that entries form loops, or
           MAY end after a finite sequence.
        
           The defaults given for this object apply only to
           explicit creation of an instance of this object and
           not to automatic creation of instances of this object
           due to creation of a parent object.";
        leaf Enable {
          type boolean;
          default "false";
          description
            "Enables or disables this entry.";
        }
        leaf ToneOn {
          type boolean;
          default "false";
          description
            "Whether or not a tone is on during this phase of the
             pattern.  If the value is {{false}}, the frequency
             and power parameters in this entry MUST be ignored.";
        }
        leaf Frequency1 {
          type uint32 {
            range "0..4095";
          }
          default "0";
          description
            "First tone frequency in {{units}}.
          
             A value of zero indicates this tone component is not
             used.";
        }
        leaf Power1 {
          type int32;
          default "0";
          description
            "First tone power level in units of 0.1 {{units}}.";
        }
        leaf Frequency2 {
          type uint32 {
            range "0..4095";
          }
          default "0";
          description
            "Second tone frequency in {{units}}.
          
             A value of zero indicates this tone component is not
             used.";
        }
        leaf Power2 {
          type int32;
          default "0";
          description
            "Second tone power level in units of 0.1 {{units}}.";
        }
        leaf Frequency3 {
          type uint32 {
            range "0..4095";
          }
          default "0";
          description
            "Third tone frequency in {{units}}.
          
             A value of zero indicates this tone component is not
             used.";
        }
        leaf Power3 {
          type int32;
          default "0";
          description
            "Third tone power level in units of 0.1 {{units}}.";
        }
        leaf Frequency4 {
          type uint32 {
            range "0..4095";
          }
          default "0";
          description
            "Fourth tone frequency in {{units}}.
          
             A value of zero indicates this tone component is not
             used.";
        }
        leaf Power4 {
          type int32;
          default "0";
          description
            "Fourth tone power level in units of 0.1 {{units}}.";
        }
        leaf ModulationFrequency {
          type uint32 {
            range "0..4095";
          }
          default "0";
          description
            "Modulation frequency in {{units}}.
          
             A value of zero indicates this tone component is not
             used.";
        }
        leaf ModulationPower {
          type int32;
          default "0";
          description
            "Modulation power level in units of 0.1 {{units}}.";
        }
        leaf Duration {
          type uint32;
          default "0";
          description
            "The duration of this phase of the tone pattern, in
             {{units}}.
          
             A value of zero indicates an unlimited duration.";
        }
        leaf NextPattern {
          type string {
            length "0..256";
          }
          description
            "The {{object}} for the next phase of the tone pattern,
             after the specified {{param|Duration}} of this phase
             has completed.
          
             {{reference}}
          
             {{empty}} indicates that the tone pattern is to
             terminate after the current phase is completed.";
        }
      }

      list EventProfile {
        key "Alias";
        description
          "Configuration profile for tone events.";

        list Event {
          key "Alias";
          description
            "Table of events for which a tone is defined.  The table
             is pre-populated with the list of events for which
             the CPE supports definition of tones.";
          leaf Function {
            type enumeration {
              enum "Busy";
              enum "Confirmation";
              enum "Dial";
              enum "LineMessagesWaiting";
              enum "OffHookWarning";
              enum "RingBack";
              enum "ReOrder";
              enum "Stutterdial";
              enum "CallWaiting1";
              enum "CallWaiting2";
              enum "CallWaiting3";
              enum "CallWaiting4";
              enum "AlertingSignal";
              enum "SpecialDial";
              enum "SpecialInfo";
              enum "Release";
              enum "Congestion";
              enum "UserDefined1";
              enum "UserDefined2";
              enum "UserDefined3";
              enum "UserDefined4";
            }
            description
              "The event for which the tone is to apply.  {{enum}}
            
               The parameter MAY instead indicate a
               vendor-specific event name, which MUST use the
               format defined in {{bibref|TR-106}}.";
          }
          leaf Tone {
            type string {
              length "0..256";
            }
            description
              "The description for the tone to be associated with
               the given event.
            
               {{reference}}
            
               {{empty}} indicates no tone is to be played for
               this event.";
          }
        }
      }
    }

    list Terminal {
      key "Alias";
      min-elements 1;
      description
        "This object models a telephony terminal, each object in the
         table represents an end-user interface.
      
         This object has to be used when the CPE is a voice
         endpoint itself.";
      leaf Enable {
        type boolean;
        description
          "Enables or disables this terminal.";
      }
      leaf QuiescentMode {
        type boolean;
        description
          "If {{true}}, when {{param|Enable}} is set to {{false}}
           in-progress sessions remain intact, but no new
           sessions are allowed.  When all sessions are
           terminated, the {{object}} is disabled.";
      }
      leaf Status {
        type enumeration {
          enum "Up";
          enum "Initializing";
          enum "Registering";
          enum "Unregistering";
          enum "Error";
          enum "Testing";
          enum "Quiescent";
          enum "Disabled";
        }
        config false;
        description
          "Indicates the status of this terminal.";
      }
      leaf ToneEventProfile {
        type string {
          length "0..256";
        }
        description
          "Reference to the {{object|.Tone.EventProfile}} to use
           with this terminal.  If this parameter is {{empty}},
           the value of {{param|.Tone.DefautEventProfile}} is
           used instead.";
      }

      list Audio {
        key "Alias";
        min-elements 1;
        description
          "This object models the audio outputs of a telephony
           terminal.(ex.  Handset, handsfree, ...)";
        leaf Name {
          type string {
            length "0..256";
          }
          description
            "The internal name of this audio.";
        }

        container VoiceProcessing {
          description
            "Parameters related to voice processing capabilities.";
          leaf TransmitGain {
            type int32;
            description
              "Gain in {{units}} to apply to the transmitted voice
               signal prior to encoding.  This gain is a modifier
               of the default transmit-gain, which is
               unspecified.";
          }
          leaf ReceiveGain {
            type int32;
            description
              "Gain in {{units}} to apply to the received voice
               signal after decoding.  This gain is a modifier of
               the default receive-gain, which is unspecified.";
          }
          leaf EchoCancellationEnable {
            type boolean;
            description
              "Enable or disable echo cancellation for this line.";
          }
          leaf EchoCancellationInUse {
            type boolean;
            config false;
            description
              "Indication of whether or not echo cancellation is
               currently in use for this line.";
          }
          leaf EchoCancellationTail {
            type uint32;
            config false;
            description
              "Tail length in {{units}} of the echo canceller
               associated with this line (whether or not it is
               currently in use).";
          }
        }
      }

      container ButtonMap {
        description
          "This object is provided to permit the purpose of the CPE
           buttons and function keys to be defined via the ACS.
        
           Support of this object is appropriate only for a
           device that has programmable buttons in its user
           interface.";

        list Button {
          key "Alias";
          min-elements 1;
          description
            "Each entry in this table specifies the purpose of each
             programmable CPE button / function key and whether
             the user has permission to reprogram the button.";
          leaf ButtonName {
            type string {
              length "0..16";
            }
            config false;
            description
              "Name of the button.";
          }
          leaf FacilityAction {
            type string {
              length "0..64";
            }
            description
              "The value MUST be a member of the list reported by
               {{param|.Capabilities.FacilityActions}}.  This is
               an OPTIONAL parameter that SHOULD NOT be specified
               for buttons not related to a particular Facility
               Action (e.g., invocation of ''Call Return'')
               implemented by the VoIP device.
            
               The parameter MAY instead indicate a
               vendor-specific Facility Action, which MUST use
               the format defined in {{bibref|TR-106}}.
            
               An empty or unrecognized string (i.e.  a Facility
               Action not supported by the CPE) means that there
               is no Facility Action to be taken.
            
               If this parameter is specified (not {{empty}})
               then {{param|QuickDialNumber}} SHOULD be
               {{empty}}.";
          }
          leaf FacilityActionArgument {
            type string {
              length "0..256";
            }
            description
              "Optional argument associated with the specified
               {{param|FacilityAction}}.  The interpretation of
               the argument is dependent on the specific
               FacilityAction.";
          }
          leaf QuickDialNumber {
            type string {
              length "0..40";
            }
            description
              "This is a string representing a quick dial
               destination number.  Only the characters '0-9',
               '*' and '#' can be used.
            
               If this parameter is specified (not {{empty}})
               then {{param|FacilityAction}} SHOULD be {{empty}}.";
          }
          leaf ButtonMessage {
            type string {
              length "0..64";
            }
            description
              "This string represents the message to be displayed on
               the screen when the button or function key is
               pressed.";
          }
          leaf UserAccess {
            type boolean;
            description
              "This parameter indicates whether the user has
               permission to program the button or function key.
               If this parameter is set to {{true}} then
               {{param|FacilityAction}},
               {{param|QuickDialNumber}} and
               {{param|ButtonMessage}} MUST all be {{empty}}.";
          }
        }
      }

      container Ringer {
        description
          "This object defines the ring sequences that may be
           generated by the terminal.";

        list Description {
          key "Alias";
          description
            "Each entry in this table defines the contents of an
             individual ring specification.
          
             The defaults given for this object apply only to
             explicit creation of an instance of this object and
             not to automatic creation of instances of this
             object due to creation of a parent object.";
          leaf RingEnable {
            type boolean;
            default "false";
            description
              "Enables or disables the ring description entry.  If a
               disabled ring description entry is referenced, the
               result is that no ring is played.";
          }
          leaf RingName {
            type string {
              length "0..64";
            }
            default "";
            description
              "Name of the ring.";
          }
          leaf RingPattern {
            type string {
              length "0..256";
            }
            description
              "This is the {{object|#.Pattern.{i}.}} object that
               begins this ring.  If the ring is specified by a
               ring file instead of a ring pattern, this
               parameter MUST be set to {{empty}}.
            
               {{reference}}";
          }
          leaf RingFile {
            type string {
              length "0..256";
            }
            default "";
            description
              "The file name of a ring file file locally present on
               the CPE.
            
               An ACS MUST use the Download method with
               FileType=\"5 Ringer File\" as defined in
               {{bibref|TR-069a4|Annex A.3.2.8}} to download a
               ring file.
            
               If the ring is specified by a ring pattern instead
               of a ring file, this parameter MUST be {{empty}}.";
          }
        }

        list Pattern {
          key "Alias";
          description
            "Each entry in the table defines a single phase in an
             overall ring pattern.  Each phase identifies the
             entry that corresponds to the next phase.
          
             Each entry in the table refers to the entry that
             corresponds to the next phase of the pattern.  The
             table MAY be set up such that entries form loops, or
             MAY end after a finite sequence.
          
             The defaults given for this object apply only to
             explicit creation of an instance of this object and
             not to automatic creation of instances of this
             object due to creation of a parent object.";
          leaf Enable {
            type boolean;
            default "false";
            description
              "Enables or disables this entry.";
          }
          leaf RingerOn {
            type boolean;
            default "false";
            description
              "Whether or not a ringer is on during this phase of
               the pattern.";
          }
          leaf Duration {
            type uint32;
            default "0";
            description
              "The duration of this phase of the ring pattern, in
               {{units}}.
            
               A value of zero indicates an unlimited duration.";
          }
          leaf NextPattern {
            type string {
              length "0..256";
            }
            description
              "The {{object}} for the next phase of the ring
               pattern, after the specified {{param|Duration}} of
               this phase has completed.
            
               {{reference}}
            
               {{empty}} indicates that the ring pattern is to
               terminate after the current phase is completed.";
          }
        }
      }

      container DiagTests {
        description
          "Terminal level tests.";
        leaf DiagnosticsState {
          type enumeration {
            enum "None";
            enum "Requested";
            enum "Complete";
            enum "Error_Internal";
            enum "Error_Other";
          }
          description
            "Indicates availability of diagnostic data.  {{enum}}
          
             If the ACS sets the value of this parameter to
             {{enum|Requested}}, the CPE MUST initiate the
             corresponding diagnostic test.  When writing, the
             only allowed value is {{enum|Requested}}.  To ensure
             the use of the proper test parameters (the writable
             parameters in this object), the test parameters MUST
             be set either prior to or at the same time as (in
             the same SetParameterValues) setting the
             DiagnosticsState to {{enum|Requested}}.
          
             When requested, the CPE SHOULD wait until after
             completion of the communication session with the ACS
             before starting the diagnostic.
          
             When the test is completed, the value of this
             parameter MUST be either {{enum|Complete}} (if the
             test completed successfully), or one of the Error
             values listed above.
          
             After the diagnostic is complete, the value of all
             result parameters (all read-only parameters in this
             object) MUST be retained by the CPE until either
             this diagnostic is run again, or the CPE reboots.
             After a reboot, if the CPE has not retained the
             result parameters from the most recent test, it MUST
             set the value of this parameter to {{enum|None}}.
          
             Modifying any of the writable parameters in this
             object except for this one MUST result in the value
             of this parameter being set to None.
          
             While the test is in progress, modifying any of the
             writable parameters in this object except for this
             one MUST result in the test being terminated and the
             value of this parameter being set to {{enum|None}}.
          
             While the test is in progress, setting this
             parameter to {{enum|Requested}} (and possibly
             modifying other writable parameters in this object)
             MUST result in the test being terminated and then
             restarted using the current values of the test
             parameters.";
        }
        leaf TestSelector {
          type enumeration {
            enum "RingingTest";
          }
          description
            "Indicates which test to perform.
          
             The parameter MAY instead indicate a vendor-specific
             test, which MUST use the format defined in
             {{bibref|TR-106}}.  For example:
          
             \"X_EXAMPLE-COM_MyTest\"";
        }
        leaf PhoneRinging {
          type boolean;
          config false;
          description
            "Indicates whether or not the phone associated with this
             port is ringing.  This parameter is applicable only
             if {{enum|RingingTest|TestSelector}} is supported.";
        }
      }
    }

    container ClockSynchronization {
      description
        "Clock source configuration for Time-Division multiplexing
         subsystem.";
      leaf CurrentSource {
        type string {
          length "0..256";
        }
        description
          "The currently selected external clock source.  If the
           current clock source is not selected from the
           {{object|ClockSource}} table, e.g.  an internal
           holdover clock, this parameter is set to {{empty}}.
        
           {{reference}}";
      }
      leaf Description {
        type string {
          length "0..64";
        }
        config false;
        description
          "Human readable description of the current clock
           synchronization status.";
      }
      leaf AutoRevert {
        type boolean;
        description
          "If set to {{true}} the CPE automatically reverts back to
           a higher priority external clock source when it
           becomes available once again.  If set to {{false}}, an
           automatic change between external clock sources only
           occurs when the current source becomes unavailable.";
      }

      list ClockSource {
        key "Order";
        description
          "List of eligible external clock sources.  The number of
           entries in this table depends on the maximum number of
           external clock sources supported by the CPE.";
        leaf Enable {
          type boolean;
          description
            "Enables or disables this entry.";
        }
        leaf Order {
          type uint32 {
            range "1..100";
          }
          description
            "Position of the {{object}} entry in the order of
             precedence.  A value of \"1\" indicates the first
             entry considered (highest precedence).";
        }
        leaf Interface {
          type string {
            length "0..256";
          }
          description
            "A reference to a physical interface from which a clock
             signal can be derived.  {{object|.ISDN.PRI.{i}.}} is
             eligible as a clock source when
             {{param|.ISDN.PRI.{i}.ClockMode}} is
             {{enum|Slave|.ISDN.PRI.{i}.ClockMode}}.
             {{object|.ISDN.BRI.{i}.}} is eligible as a clock
             source when
             {{param|.ISDN.BRI.{i}.ProtocolEmulation}} is
             {{enum|TE|.ISDN.BRI.{i}.ProtocolEmulation}}.
          
             {{reference}}";
        }
      }
    }
  }
}
