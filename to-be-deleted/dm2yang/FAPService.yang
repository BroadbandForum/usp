module FAPService {
  namespace "urn:tbd";
  prefix TBD;
  
  import ietf-yang-types {
    prefix yang;
  }
  
  import tr-106-types {
    prefix types;
  }
  
  organization
    "TBD";
  
  contact
    "TBD";
  
  description
    "";
  
  revision 1970-01-01 {
    description
      "TBD";
    reference
      "TBD";
  }

  list FAPService {
    key "Alias";
    description
      "The Femto Access Point (FAP) Service Object.";
    leaf DeviceType {
      type enumeration {
        enum "Standalone";
        enum "Integrated";
      }
      config false;
      description
        "The type of FAP device.";
    }
    leaf DNPrefix {
      type string {
        length "0..256";
      }
      description
        "The Distinguished Name prefix (DNPrefix) is an
         operator-configurable prefix string that is pre-pended
         to object distinguished names in the {{bibref|TR-157a5}}
         alarm object.  See {{bibref|3GPP-TS.32.300}} for the
         formal definition and examples of DNPrefix as applied to
         3GPP alarm objects";
    }

    container Capabilities {
      config false;
      description
        "This object contains parameters relating to the hardware
         capabilities of the FAP device.";
      leaf GPSEquipped {
        type boolean;
        description
          "Indicates whether the FAP is equipped with a GPS receiver
           or not.";
      }
      leaf MaxTxPower {
        type uint32;
        description
          "Indicates the maximum possible transmit power in
           {{units}} that the FAP hardware can support.";
      }
      leaf SupportedSystems {
        type enumeration {
          enum "UMTS";
          enum "LTE";
          enum "CDMA1x";
          enum "CDMAHRPD";
        }
        description
          "{{list}} Each entry is a type of system that the FAP
           supports.  {{enum}}";
      }
      leaf Beacon {
        type boolean;
        description
          "Indicates whether FAP can support beacon transmission.";
      }

      container UMTS {
        description
          "This object contains parameters relating to the system
           and RF aspect of the FAP device that supports the UMTS
           system.";
        leaf DuplexMode {
          type enumeration {
            enum "FDDMode";
          }
          description
            "Indicates the mode supported by the FAP.  {{enum}}";
        }
        leaf GSMRxSupported {
          type boolean;
          description
            "Indicates whether the FAP hardware supports the
             receiving function of GSM or not.";
        }
        leaf HSDPASupported {
          type boolean;
          description
            "Indicates whether the FAP hardware supports the HSDPA
             capability or not.";
        }
        leaf MaxHSDPADataRateSupported {
          type uint32;
          description
            "If the FAP hardware supports HSDPA
             ({{param|HSDPASupported}} is {{true}}), this
             parameter indicates the maximum HSDPA data rate in
             {{units}} that the device supports.";
        }
        leaf HSUPASupported {
          type boolean;
          description
            "Indicates whether the FAP hardware supports the HSUPA
             capability or not.";
        }
        leaf MaxHSUPADataRateSupported {
          type uint32;
          description
            "If the FAP hardware supports HSUPA
             ({{param|HSUPASupported}} is {{true}}), this
             parameter indicates the maximum HSUPA data rate in
             {{units}} that the device supports.";
        }
        leaf MaxHSPDSCHsSupported {
          type uint32 {
            range "min..15";
          }
          description
            "If the FAP hardware supports HSPA family (either
             {{param|HSDPASupported}} is {{true}} or
             {{param|HSUPASupported}} is {{true}}), this
             parameter indicates the available number of codes at
             the defined spreading factor (SF=16), within the
             complete code tree.  See
             {{bibref|3GPP-TS.32.642|Section 6.3.9}} for more
             details.";
        }
        leaf MaxHSSCCHsSupported {
          type uint32;
          description
            "If the FAP hardware supports HSPA family (either
             {{param|HSDPASupported}} is {{true}} or
             {{param|HSUPASupported}} is {{true}}), this
             parameter indicates the available number of HS-SCCHs
             for one cell.  See {{bibref|3GPP-TS.32.642|Section
             6.3.9}} for more details.";
        }
        leaf FDDBandsSupported {
          type string;
          description
            "{{list}} Indicates the UMTS bands that the FAP supports
             {{bibref|3GPP-TS.25.104}}, Release 8.  At least one
             band MUST be supported and multiple bands MAY be
             supported.
          
             {{bibref|3GPP-TS.25.104}} Version 8.3.0 defines 14
             UMTS bands (I through XIV).
          
             Each individual band is identified by its upper case
             Roman numeral.  The order of the band indicators in
             the string has no significance.
          
             In case a new band is defined in the 3GPP standard
             in a future release of {{bibref|3GPP-TS.25.104}},
             the corresponding new upper case Roman numeral will
             be included in the valid band indicators.
          
             The followings are examples of valid values:
          
             :\"I\" (specifies only band-I is supported)
          
             :\"I,II,V\" (specifies 3 bands are supported)
          
             :\"II,VII,I\" (specifies 3 bands are supported)";
        }
        leaf GSMRxBandsSupported {
          type enumeration {
            enum "T-GSM380";
            enum "T-GSM410";
            enum "GSM450";
            enum "GSM480";
            enum "GSM710";
            enum "GSM750";
            enum "T-GSM810";
            enum "GSM850";
            enum "P-GSM900";
            enum "E-GSM900";
            enum "R-GSM900";
            enum "T-GSM900";
            enum "DCS1800";
            enum "PCS1900";
          }
          description
            "{{list}} Indicates the GSM receive bands that the FAP
             supports {{bibref|3GPP-TS.45.005}}.  At least one
             band MUST be supported and multiple bands MAY be
             supported.
          
             {{bibref|3GPP-TS.45.005}} defines 14 GSM bands.
             {{enum}}
          
             The order of the band indicators in the string has
             no significance.
          
             The following is an example of a valid value.
          
             :\"GSM850,PCS1900\"";
        }

        container SelfConfig {
          description
            "This object contains parameters relating to the
             self-configuration capabilities of the FAP.
             Self-configuration is enabled in
             {{object|.FAPControl.UMTS.SelfConfig.}}";
          leaf UARFCNConfig {
            type boolean;
            description
              "Indicates whether the FAP supports the
               self-configuration capability to determine the
               UTRA Absolute Radio Frequency Channel Number
               (UARFCN).
            
               If {{true}} multiple values MAY be provided in
               {{param|.CellConfig.UMTS.RAN.RF.UARFCNDL}} for the
               FAP to select from.
            
               If {{false}} only a single value SHOULD be
               provided in
               {{param|.CellConfig.UMTS.RAN.RF.UARFCNDL}}.";
          }
          leaf PrimaryScramblingCodeConfig {
            type boolean;
            description
              "Indicates whether the FAP supports the
               self-configuration capability to determine the
               Primary Scrambling Code (PSC).
            
               If {{true}} multiple values or a range of values
               MAY be provided in
               {{param|.CellConfig.UMTS.RAN.RF.PrimaryScramblingCode}}
               for the FAP to select from.
            
               If {{false}} only a single value SHOULD be
               provided in
               {{param|.CellConfig.UMTS.RAN.RF.PrimaryScramblingCode}}.";
          }
          leaf MaxFAPTxPowerExpandedConfig {
            type boolean;
            description
              "Indicates whether the FAP supports the
               self-configuration capability to determine the
               Maximum FAP Transmit Power.
            
               If {{true}} a range of values MAY be provided in
               {{param|.CellConfig.UMTS.RAN.RF.MaxFAPTxPowerExpanded}}
               for the FAP to select from.
            
               If {{false}} only a single value SHOULD be
               provided in
               {{param|.CellConfig.UMTS.RAN.RF.MaxFAPTxPowerExpanded}}.";
          }
          leaf PCPICHPowerConfig {
            type boolean;
            description
              "Indicates whether the FAP supports the
               self-configuration capability to determine the
               P-CPICH power.
            
               If {{true}} a range of values MAY be provided in
               {{param|.CellConfig.UMTS.RAN.RF.PCPICHPower}} for
               the FAP to select from.
            
               If {{false}} only a single value SHOULD be
               provided in
               {{param|.CellConfig.UMTS.RAN.RF.PCPICHPower}} as
               an upper bound.";
          }
          leaf MaxULTxPowerConfig {
            type boolean;
            description
              "Indicates whether the FAP supports the
               self-configuration capability to determine the
               Maximum UL Transmit Power.
            
               If {{true}} a range of values MAY be provided in
               {{param|.CellConfig.UMTS.RAN.RF.MaxULTxPower}} for
               the FAP to select from.
            
               If {{false}} only a single value SHOULD be
               provided in
               {{param|.CellConfig.UMTS.RAN.RF.MaxULTxPower}}.";
          }
          leaf LACRACURAConfig {
            type boolean;
            description
              "Indicates whether the FAP supports the
               self-configuration capability to determine the
               LAC, RAC, and URA.
            
               If {{true}} multiple values MAY be provided in
               {{param|.CellConfig.UMTS.CN.LACRAC}} and
               {{param|.CellConfig.UMTS.RAN.URAList}} for the FAP
               to select from.
            
               If {{false}} only a single value SHOULD be
               provided in {{param|.CellConfig.UMTS.CN.LACRAC}}
               and {{param|.CellConfig.UMTS.RAN.URAList}}.";
          }
          leaf NeighborListConfig {
            type boolean;
            description
              "Indicates whether the FAP supports the
               self-configuration capability to determine the
               neighbor list.
            
               If {{true}} the ACS uses the
               {{object|.CellConfig.UMTS.RAN.NeighborList.IntraFreqCell.{i}.}},
               {{object|.CellConfig.UMTS.RAN.NeighborList.InterFreqCell.{i}.}},
               {{object|.CellConfig.UMTS.RAN.NeighborList.InterRATCell.}}
               tables to explicitly include or exclude entries
               and the FAP uses that information to determine the
               final configuration found in the
               {{object|.CellConfig.UMTS.RAN.NeighborListInUse.IntraFreqCell.{i}.}},
               {{object|.CellConfig.UMTS.RAN.NeighborListInUse.InterFreqCell.{i}.}},
               {{object|.CellConfig.UMTS.RAN.NeighborListInUse.InterRATCell.}}
               tables.
            
               If {{false}} the ACS uses the
               {{object|.CellConfig.UMTS.RAN.NeighborList.IntraFreqCell.{i}.}},
               {{object|.CellConfig.UMTS.RAN.NeighborList.InterFreqCell.{i}.}},
               {{object|.CellConfig.UMTS.RAN.NeighborList.InterRATCell.}}
               tables to only specify the included entries and
               the FAP uses that list.";
          }
          leaf CellReSelectionConfig {
            type boolean;
            description
              "Indicates whether the FAP supports the
               self-configuration capability to determine
               cell-reselection values.
            
               If {{true}}
               {{object|.CellConfig.UMTS.RAN.CellSelection.}} can
               be self-configured.
            
               If {{false}}
               {{object|.CellConfig.UMTS.RAN.CellSelection.}} is
               provided by the ACS.";
          }
          leaf IntraFreqMeasConfig {
            type boolean;
            description
              "Indicates whether the FAP supports the
               self-configuration capability to determine
               intra-frequency measurement values.
            
               If {{true}}
               {{object|.CellConfig.UMTS.RAN.IntraFreqMeas.}} can
               be self-configured.
            
               If {{false}}
               {{object|.CellConfig.UMTS.RAN.IntraFreqMeas.}} is
               provided by the ACS.";
          }
          leaf InterFreqMeasConfig {
            type boolean;
            description
              "Indicates whether the FAP supports the
               self-configuration capability to determine
               inter-frequency measurement values.
            
               If {{true}}
               {{object|.CellConfig.UMTS.RAN.InterFreqMeas.}} can
               be self-configured.
            
               If {{false}}
               {{object|.CellConfig.UMTS.RAN.InterFreqMeas.}} is
               provided by the ACS.";
          }
          leaf InterRATMeasConfig {
            type boolean;
            description
              "Indicates whether the FAP supports the
               self-configuration capability to determine
               inter-RAT measurement values.
            
               If {{true}}
               {{object|.CellConfig.UMTS.RAN.InterRATMeas.}} can
               be self-configured.
            
               If {{false}}
               {{object|.CellConfig.UMTS.RAN.InterRATMeas.}} is
               provided by the ACS.";
          }
          leaf UEInternalMeasConfig {
            type boolean;
            description
              "Indicates whether the FAP supports the
               self-configuration capability to determine UE
               internal measurement values.
            
               If {{true}}
               {{object|.CellConfig.UMTS.RAN.UEInternalMeas.}}
               can be self-configured.
            
               If {{false}}
               {{object|.CellConfig.UMTS.RAN.UEInternalMeas.}} is
               provided by the ACS.";
          }
          leaf NoiseRiseLimitConfig {
            type boolean;
            description
              "Indicates whether the FAP supports the
               selfconfiguration capability to determine the
               Noise Rise Limit.
            
               If {{true}}
               {{param|.CellConfig.UMTS.RAN.RF.NoiseRiseLimitLowerValue}}
               and
               {{param|.CellConfig.UMTS.RAN.RF.NoiseRiseLimitUpperValue}}.
               MAY provide a range of values to select from.
            
               If {{false}}
               {{param|.CellConfig.UMTS.RAN.RF.NoiseRiseLimitUpperValue}}
               provides only a single value to be used.  The
               value of
               {{param|.CellConfig.UMTS.RAN.RF.NoiseRiseLimitLowerValue}}
               is ignored.";
          }
        }
      }

      container LTE {
        description
          "This object contains parameters relating to the system
           and RF aspect of the FAP device that supports the LTE
           system.";
        leaf DuplexMode {
          type enumeration {
            enum "FDDMode";
            enum "TDDMode";
          }
          description
            "Indicates the mode supported by the LTE FAP.  {{enum}}";
        }
        leaf BandsSupported {
          type uint32 {
            range "1..21 | 33..40";
          }
          description
            "{{list}} Indicates the LTE bands that the LTE FAP
             supports {{bibref|3GPP-TS.36.101|Section 5.5}}.  At
             least one band MUST be supported and multiple bands
             MAY be supported.
          
             Each individual band is identified by arabic number
             (1, 2,...).  The order of the band indicators in the
             string has no significance.
          
             In case a new band is defined in the 3GPP standard
             in a future release of {{bibref|3GPP-TS.36.101}},
             the corresponding new band number will be included
             in the valid band indicators.
          
             The followings are examples of valid values:
          
             :\"1\" (specifies only band-1 is supported)
          
             :\"1,2,11\" (specifies 3 bands are supported)
          
             :\"2,11,1\" (specifies 3 bands are supported)";
        }
        leaf NNSFSupported {
          type boolean;
          description
            "Indicates whether LTE FAP supports the NAS Node
             Selection Function (NNSF) or not.  NNSF is described
             in {{bibref|3GPP-TS.36.300|Section 19.2.1.7 and
             Section 4.6.1}}.";
        }
        leaf UMTSRxSupported {
          type boolean;
          description
            "Indicates whether the LTE FAP hardware supports the
             receiving function of UMTS or not.";
        }
        leaf UMTSRxBandsSupported {
          type string;
          description
            "{{list}} Indicates the UMTS receive bands that the LTE
             FAP supports {{bibref|3GPP-TS.25.104}}, Release 8.
             If {{param|UMTSRxSupported}} is {{true}}, then at
             least one band MUST be supported and multiple bands
             MAY be supported.
          
             Each individual band is identified by its upper case
             Roman numeral.  The order of the band indicators in
             the string has no significance.
          
             In case a new band is defined in the 3GPP standard
             in a future release of {{bibref|3GPP-TS.25.104}},
             the corresponding new upper case Roman numeral will
             be included in the valid band indicators.
          
             The followings are examples of valid values:
          
             :\"I\" (specifies only band-I is supported)
          
             :\"I,II,V\" (specifies 3 bands are supported)
          
             :\"II,VII,I\" (specifies 3 bands are supported)";
        }
        leaf GSMRxSupported {
          type boolean;
          description
            "Indicates whether the LTE FAP hardware supports the
             receiving function of GSM or not.";
        }
        leaf GSMRxBandsSupported {
          type enumeration {
            enum "T-GSM380";
            enum "T-GSM410";
            enum "GSM450";
            enum "GSM480";
            enum "GSM710";
            enum "GSM750";
            enum "T-GSM810";
            enum "GSM850";
            enum "P-GSM900";
            enum "E-GSM900";
            enum "R-GSM900";
            enum "T-GSM900";
            enum "DCS1800";
            enum "PCS1900";
          }
          description
            "{{list}} Indicates the GSM receive bands that the LTE
             FAP supports {{bibref|3GPP-TS.45.005}}.  If
             {{param|GSMRxSupported}} is {{true}}, then at least
             one band MUST be supported and multiple bands MAY be
             supported.
          
             {{bibref|3GPP-TS.45.005}} defines 14 GSM bands.
             {{enum}}
          
             The order of the band indicators in the string has
             no significance.
          
             The following is an example of a valid value.
          
             :\"GSM850,PCS1900\"";
        }
        leaf CDMA2000RxSupported {
          type boolean;
          description
            "Indicates whether the LTE FAP hardware supports the
             receiving function of CDMA2000 or not.";
        }
        leaf CDMA2000RxBandsSupported {
          type string;
          description
            "{{list}} Indicates the CDMA2000 receive bands that the
             LTE FAP supports.  If {{param|CDMA2000RxSupported}}
             is {{true}}, then at least one band MUST be
             supported and multiple bands MAY be supported.  The
             order of the band indicators in the string has no
             significance.  Bandclass is a 1 or 2-digit number as
             defined in {{bibref|3GPP2-C.S0057-B}}.
          
             The following are example values:
          
             :\"0\" (specifies US Cellular)
          
             :\"1,3,14\" (specifies US PCS, Japan Cellular and US
             PCS 1.9Ghz) specifies 3 bands are supported)";
        }
      }

      container CDMA2000 {
        description
          "This object contains parameters relating to the
           capability attributes for CDMA2000 FAP.";
        leaf RemoteIPAccessCapable {
          type boolean;
          description
            "Indicates whether the FAP is capable of providing
             remote IP access service as defined in
             {{bibref|3GPP2-X.S0059}}.  If {{true}}, the FAP is
             capable of remote IP access service.  If {{false}},
             the FAP is not capable of remote IP access service.";
        }
        leaf BandClassSupportedFAPBeacon {
          type string;
          description
            "{{list}} Indicates the band classes that the FAP
             supports for beacon transmission.  One or multiple
             bands MAY be supported.  Bandclass is a 1 or 2-digit
             number as defined in {{bibref|3GPP2-C.S0057}}.  List
             is empty if FAP can not support beacon
             transmissions.";
        }

        container OneX {
          description
            "This object contains parameters relating to the
             capability attributes for the CDMA2000 1x radio
             technology portions of a CDMA2000 FAP.";
          leaf BandClassSupportedFAP {
            type string {
              length "0..32";
            }
            description
              "{{list}} Indicates the CDMA bands that the FAP
               supports.  At least one band MUST be supported and
               multiple bands MAY be supported.
            
               Bandclass is a 1 or 2-digit number as defined in
               {{bibref|3GPP2-C.S0057}}.  The following are
               example values:
            
               \"0\" (specifies US Cellular)
            
               \"1,3,14\" (specifies US PCS, Japan Cellular and
               US PCS 1.9Ghz)";
          }
          leaf ActiveHandinCapable {
            type boolean;
            description
              "Indicates whether the FAP is capable of accepting
               hand-in of active 1x call from another base
               station.  If {{true}}, the FAP is capable of
               accepting hand-in.  If {{false}}, the FAP is not
               capable of accepting hand-in.";
          }
          leaf FemtoOverheadMessagesCapable {
            type boolean;
            description
              "Indicates whether the FAP supports Access Point
               Identification, Access Point Pilot Information,
               and Access Point Identification Text messages
               specified in {{bibref|3GPP2-C.S0005}}.  If
               {{true}}, the FAP supports these messages.  If
               {{false}}, the FAP does not supports these
               messages.";
          }

          container SelfConfig {
            description
              "This object contains parameters relating to the
               self-configuration capabilities of the FAP.
               Self-configuration is enabled in
               {{object|.FAPControl.CDMA2000.OneX.SelfConfig.}}.";
            leaf RFCNFLConfig {
              type boolean;
              description
                "Indicates whether the FAP supports the
                 self-configuration capability to determine the
                 Radio Frequency Channel Number.  If {{true}}
                 multiple values MAY be provided in
                 {{param|.CellConfig.CDMA2000.OneX.RAN.RF.RFCNFL}}
                 for the FAP to select from.  If {{false}} only a
                 single value SHOULD be provided in
                 {{param|.CellConfig.CDMA2000.OneX.RAN.RF.RFCNFL}}.";
            }
            leaf PilotPNConfig {
              type boolean;
              description
                "Indicates whether the FAP supports the
                 self-configuration capability to determine the
                 pilot PN offset.  If {{true}} multiple values or
                 a range of values MAY be provided in
                 {{param|.CellConfig.CDMA2000.OneX.RAN.RF.PilotPN}}
                 for the FAP to select from.  If {{false}} only a
                 single value SHOULD be provided in
                 {{param|.CellConfig.CDMA2000.OneX.RAN.RF.PilotPN}}.";
            }
            leaf MaxFAPTxPowerConfig {
              type boolean;
              description
                "Indicates whether the FAP supports the
                 self-configuration capability to determine the
                 Maximum FAP Transmit Power.  If {{true}} a range
                 of values MAY be provided in
                 {{param|.CellConfig.CDMA2000.OneX.RAN.RF.MaxFAPTxPower}}
                 for the FAP to select from.  If {{false}} only a
                 single value SHOULD be provided in
                 {{param|.CellConfig.CDMA2000.OneX.RAN.RF.MaxFAPTxPower}}.";
            }
            leaf MaxFAPBeaconTxPowerConfig {
              type boolean;
              description
                "Indicates whether the FAP supports the
                 self-configuration capability to determine the
                 Maximum FAP Beacon Transmit Power.  If {{true}}
                 a range of values MAY be provided in
                 {{param|.CellConfig.CDMA2000.Beacon.MaxFAPBeaconTxPower}}
                 for the FAP to select from.  If {{false}} only a
                 single value SHOULD be provided in
                 {{param|.CellConfig.CDMA2000.Beacon.MaxFAPBeaconTxPower}}.";
            }
          }
        }

        container HRPD {
          description
            "This object contains parameters relating to the
             capability attributes for the CDMA2000 HRPD radio
             technology portions of a CDMA2000 FAP.";
          leaf A13SessionTransferCapable {
            type boolean;
            description
              "Indicates whether the FAP is capable of supporting
               A13 session transfer.  See
               {{bibref|3GPP2-C.S0024-B}}.";
          }
          leaf A16SessionTransferCapable {
            type boolean;
            description
              "Indicates whether the FAP is capable of supporting
               A16 session transfer.  See
               {{bibref|3GPP2-C.S0024-B}}.";
          }
          leaf LocalIPAccessCapable {
            type boolean;
            description
              "Indicates whether the FAP is capable of supporting
               Local IP access.  See {{bibref|3GPP2-C.S0024-B}}.";
          }
          leaf DedicatedHRPDBeacon {
            type boolean;
            description
              "Indicated whether the FAP supports a dedicated
               transmission of HRPD beacon independent of the
               generalized beacon.";
          }

          container SelfConfig {
            description
              "This object contains parameters relating to the
               self-configuration capability attributes for the
               CDMA2000 HRPD radio technology portions of a
               CDMA2000 FAP.";
            leaf RFCNFLConfig {
              type boolean;
              description
                "Indicates whether the FAP supports the
                 self-configuration capability to determine the
                 Radio Frequency Channel Number.  If {{true}}
                 multiple values MAY be provided in
                 {{param|.CellConfig.CDMA2000.HRPD.RAN.RF.RFCNFL}}
                 for the FAP to select from.  If {{false}} only a
                 single value SHOULD be provided in
                 {{param|.CellConfig.CDMA2000.HRPD.RAN.RF.RFCNFL}}.";
            }
            leaf PilotPNConfig {
              type boolean;
              description
                "Indicates whether the FAP supports the
                 self-configuration capability to determine the
                 pilot PN offset.  If {{true}} multiple values or
                 a range of values MAY be provided in
                 {{param|.CellConfig.CDMA2000.HRPD.RAN.RF.PilotPN}}
                 for the FAP to select from.  If {{false}} only a
                 single value SHOULD be provided in
                 {{param|.CellConfig.CDMA2000.HRPD.RAN.RF.PilotPN}}.";
            }
            leaf MaxFAPTxPowerConfig {
              type boolean;
              description
                "Indicates whether the FAP supports the
                 self-configuration capability to determine the
                 Maximum FAP Transmit Power.  If {{true}} a range
                 of values MAY be provided in
                 {{param|.CellConfig.CDMA2000.HRPD.RAN.RF.MaxFAPTxPower}}
                 for the FAP to select from.  If {{false}} only a
                 single value SHOULD be provided in
                 {{param|.CellConfig.CDMA2000.HRPD.RAN.RF.MaxFAPTxPower}}.";
            }
            leaf MaxFAPBeaconTxPowerConfig {
              type boolean;
              description
                "Indicates whether the FAP supports the
                 self-configuration capability to determine the
                 Maximum FAP Beacon Transmit Power.  If {{true}}
                 a range of values MAY be provided in
                 {{param|.CellConfig.CDMA2000.Beacon.MaxFAPBeaconTxPower}}
                 for the FAP to select from.  If {{false}} only a
                 single value SHOULD be provided in
                 {{param|.CellConfig.CDMA2000.Beacon.MaxFAPBeaconTxPower}}.";
            }
          }
        }
      }
    }

    container FAPControl {
      description
        "This object contains parameters relating to state
         management and provisioning aspects of the FAP.";
      leaf SelfConfigEvents {
        type enumeration {
          enum "InitialREM";
        }
        description
          "{{list}} Each item is an event that causes the FAP to
           perform self configuration as defined by
           {{object|.FAPControl.UMTS.SelfConfig.}},
           {{object|.FAPControl.CDMA2000.OneX.SelfConfig.}}, or
           {{object|.FAPControl.CDMA2000.HRPD.SelfConfig.}}.
        
           Vendors can extend the enumerated values with
           vendor-specific extensions, in which case the rules
           outlined in {{bibref|TR-106a2|Section3.3}} MUST be
           adhered to.";
      }
      leaf EnclosureTamperingDetected {
        type boolean;
        description
          "This parameter indicates whether or not physical
           tampering of the device enclosure occurred, such as
           illegal opening of the box.
        
           If {{true}} device tampering is detected.
        
           If {{false}} no sign of device tampering is detected.
        
           Tampering state MUST be persisted across reboots and
           the device MUST never reset it back from {{true}} to
           {{false}} even after a factory reset.";
      }

      container UMTS {
        description
          "This object contains parameters relating to the UMTS
           system specific information.";
        leaf OpState {
          type boolean;
          config false;
          description
            "Current operational state of the UMTS FAP as defined in
             {{bibref|ITU-X.731}}.
          
             If {{true}} the UMTS FAP is currently enabled.
          
             If {{false}} the UMTS FAP is currently disabled.";
        }
        leaf AdminState {
          type boolean;
          description
            "Lock or unlock the UMTS FAP.  This controls the
             administrative state of the UMTS FAP as defined in
             {{bibref|ITU-X.731}}.
          
             If {{true}} Unlocked with permission to serve
             traffic (and enable RF transmitter(s)).
          
             If {{false}} Locked.  Transition UMTS FAP to state
             where it is NOT permitted to serve traffic.  RF
             transmitter is disabled.
          
             Given that this command controls the UMTS FAP's RF
             transmitter, the underlying expectation is that the
             unlock is done when all necessary conditions are met
             to allow the transmitter to key on and provide
             service, including aspects such as:
          
             # location verification (including meeting the
             governing regulatory requirements)
          
             # verifying the UMTS FAP configuration
          
             # if physical tampering is supported and no physical
             tampering is detected.
          
             The default value after power-on is {{false}}.";
        }
        leaf RFTxStatus {
          type boolean;
          config false;
          description
            "Current status of this UMTS FAP RF transmitter.
          
             {{true}} indicates that the UMTS FAP Tx transmitter
             is on.
          
             {{false}} indicates that the UMTS FAP Tx transmitter
             is off.
          
             This state is tied to the Administrative state which
             is controlled by the ACS.
          
             :When the ACS sets {{param|AdminState}} to {{true}},
             then the UMTS FAP has permission to turn on the RF
             transmitter.
          
             :When the ACS sets {{param|AdminState}} to
             {{false}}, then the UMTS FAP is not allowed to
             provide service and MUST turn off the RF
             transmitter.";
        }
        leaf PMConfig {
          type string {
            length "0..256";
          }
          description
            "The value MUST be the path name of a row in the
             optional ''FAP.PerfMgmt.Config.'' table (see
             {{bibref|TR-262}}).
          
             This is the performance management related
             configuration for the UMTS FAP.  In case of a
             multiple-radio-technology FAP product, each radio
             technology can have its own PM configuration or
             share a common PM configuration.  In the former
             case, {{param}} can contain a unique instance
             number.  In the latter case, {{param}} under all
             radio technologies can have the same instance
             number.
          
             If the referenced object is deleted, the parameter
             value MUST be set to an empty string.";
        }

        container SelfConfig {
          description
            "This object contains parameters relating to the
             controlling of self-configuration capabilities in
             the FAP.";
          leaf UARFCNSelfConfigEnable {
            type boolean;
            description
              "Indicates whether the self-configuration capability
               in the FAP is used or not to determine the values
               of
               {{param|.CellConfig.UMTS.RAN.CSG.UARFCNDLList}}.
            
               If {{true}} The FAP self-configures the value.
            
               If {{false}} The ACS MUST provide the specific
               value to be used.";
          }
          leaf PrimaryScramblingCodeSelfConfigEnable {
            type boolean;
            description
              "Indicates whether the self-configuration capability
               in the FAP is used or not to determine the value
               of
               {{param|.CellConfig.UMTS.RAN.RF.PrimaryScramblingCode}}.
            
               If {{true}} the FAP self-configures the value.
            
               If {{false}} the ACS MUST provide the specific
               value to be used.";
          }
          leaf MaxFAPTxPowerExpandedSelfConfigEnable {
            type boolean;
            description
              "Indicates whether the self-configuration capability
               in the FAP is used or not to determine the value
               of
               {{param|.CellConfig.UMTS.RAN.RF.MaxFAPTxPowerExpanded}}.
            
               If {{true}} The FAP self-configures the value.
            
               If {{false}} The ACS MUST provide the specific
               value to be used.";
          }
          leaf PCPICHPowerSelfConfigEnable {
            type boolean;
            description
              "Indicates whether the self-configuration capability
               in the FAP is used or not to determine the value
               of {{param|.CellConfig.UMTS.RAN.RF.PCPICHPower}}.
            
               If {{true}} The FAP self-configures the value.
            
               If {{false}} The ACS MUST provide the specific
               value to be used.";
          }
          leaf MaxULTxPowerSelfConfigEnable {
            type boolean;
            description
              "Indicates whether the self-configuration capability
               in the FAP is used or not to determine the value
               of {{param|.CellConfig.UMTS.RAN.RF.MaxULTxPower}}.
            
               If {{true}} The FAP self-configures the value.
            
               If {{false}} The ACS MUST provide the specific
               value to be used.";
          }
          leaf LACRACURASelfConfigEnable {
            type boolean;
            description
              "Indicates whether the self-configuration capability
               in the FAP is used or not to determine the values
               of {{param|.CellConfig.UMTS.CN.LACRAC}} and
               {{param|.CellConfig.UMTS.RAN.URAList}}.
            
               If {{true}} The FAP self-configures the value.
            
               If {{false}} The ACS MUST provide the specific
               value to be used.";
          }
          leaf NeighborListSelfConfigEnable {
            type boolean;
            description
              "Indicates whether the self-configuration capability
               in the FAP is used or not to determine the values
               in the object
               {{object|.CellConfig.UMTS.RAN.NeighborList.}}
            
               If {{true}} The FAP self-configures the value.
            
               If {{false}} The ACS MUST provide the specific
               value to be used.";
          }
          leaf CellReSelectionSelfConfigEnable {
            type boolean;
            description
              "Indicates whether the self-configuration capability
               in the FAP is used or not to determine Cell
               Selection/Reselection-related parameters in
               {{object|.CellConfig.UMTS.RAN.CellSelection.}}
            
               If {{true}} The FAP self-configures the value.
            
               If {{false}} The ACS MUST provide the specific
               value to be used.";
          }
          leaf IntraFreqMeasSelfConfigEnable {
            type boolean;
            description
              "Indicates whether the self-configuration capability
               in the FAP is used or not to determine
               intra-frequency measurement -related parameters in
               {{object|.CellConfig.UMTS.RAN.IntraFreqMeas.}}
            
               If {{true}} The FAP self-configures the value.
            
               If {{false}} The ACS MUST provide the specific
               value to be used.";
          }
          leaf InterFreqMeasSelfConfigEnable {
            type boolean;
            description
              "Indicates whether the self-configuration capability
               in the FAP is used or not to determine
               inter-frequency measurement -related parameters in
               {{object|.CellConfig.UMTS.RAN.InterFreqMeas.}}
            
               If {{true}} The FAP self-configures the value.
            
               If {{false}} The ACS MUST provide the specific
               value to be used.";
          }
          leaf InterRATMeasSelfConfigEnable {
            type boolean;
            description
              "Indicates whether the self-configuration capability
               in the FAP is used or not to determine inter-RAT
               measurement -related parameters in
               {{object|.CellConfig.UMTS.RAN.InterRATMeas.}}
            
               If {{true}} The FAP self-configures the value.
            
               If {{false}} The ACS MUST provide the specific
               value to be used.";
          }
          leaf UEInternalMeasConfigEnable {
            type boolean;
            description
              "Indicates whether the self-configuration capability
               in the FAP is used or not to determine UE internal
               measurement-related parameters in
               {{object|.CellConfig.UMTS.RAN.UEInternalMeas.}}
            
               If {{true}} The FAP self-configures the value.
            
               If {{false}} The ACS MUST provide the specific
               value to be used.";
          }
          leaf NoiseRiseLimitConfigEnable {
            type boolean;
            description
              "Indicates whether the self-configuration capability
               in the FAP is used or not to determine the value
               of
               {{param|.CellConfig.UMTS.RAN.RF.NoiseRiseLimitInUse}}.
            
               If {{true}} the FAP self-configures the value,
               based on the limits specified in
               {{param|.CellConfig.UMTS.RAN.RF.NoiseRiseLimitLowerValue}}
               and
               {{param|.CellConfig.UMTS.RAN.RF.NoiseRiseLimitUpperValue}}.
            
               If {{false}} the ACS must provide the specific
               value to be used.";
          }
        }

        container Gateway {
          description
            "This object contains parameters relating to the
             Gateways that FAP is connected to.";
          leaf SecGWServer1 {
            type string {
              length "0..64";
            }
            description
              "First SecGW the FAP attempts to establish connection
               with.  Either hostname or IPaddress.";
          }
          leaf SecGWServer2 {
            type string {
              length "0..64";
            }
            description
              "Second SecGW the FAP attempts to establish connection
               with.  Either hostname or IPaddress.";
          }
          leaf SecGWServer3 {
            type string {
              length "0..64";
            }
            description
              "Third SecGW the FAP attempts to establish connection
               with.  Either hostname or IPaddress.";
          }
          leaf FAPGWServer1 {
            type string {
              length "0..64";
            }
            description
              "First FAPGW the FAP attempts to establish connection
               with.  Either hostname or IPaddress.";
          }
          leaf FAPGWServer2 {
            type string {
              length "0..64";
            }
            description
              "Second FAPGW the FAP attempts to establish connection
               with.  Either hostname or IPaddress.";
          }
          leaf FAPGWServer3 {
            type string {
              length "0..64";
            }
            description
              "Third FAPGW the FAP attempts to establish connection
               with.  Either hostname or IPaddress.";
          }
          leaf FAPGWPort {
            type uint32 {
              range "min..65535";
            }
            description
              "Port number of FAPGW used for initial Iuh SCTP
               contact.  This value is specified as 29169
               according to IANA definition per
               {{bibref|IANA-portnumbers}}, registered on
               2009-09-08.  Use of IANA-defined value is
               recommended.";
          }
        }
      }

      container LTE {
        description
          "This object contains parameters relating to the LTE
           system specific information.";
        leaf OpState {
          type boolean;
          config false;
          description
            "Current operational state of the LTE FAP as defined in
             {{bibref|ITU-X.731}}.
          
             If {{true}} the LTE FAP is currently enabled.
          
             If {{false}} the LTE FAP is currently disabled.";
        }
        leaf AdminState {
          type boolean;
          description
            "Lock or unlock the LTE FAP.  This controls the
             administrative state of the LTE FAP as defined in
             {{bibref|ITU-X.731}}.
          
             If {{true}} Unlocked with permission to serve
             traffic (and enable RF transmitter(s)).
          
             If {{false}} Locked.  Transition LTE FAP to state
             where it is NOT permitted to serve traffic.  RF
             transmitter is disabled.
          
             Given that this command controls the LTE FAP's RF
             transmitter, the underlying expectation is that the
             unlock is done when all necessary conditions are met
             to allow the transmitter to key on and provide
             service, including aspects such as:
          
             # location verification (including meeting the
             governing regulatory requirements)
          
             # verifying the LTE FAP configuration
          
             # if physical tampering is supported and no physical
             tampering is detected.
          
             The default value after power-on is {{false}}.";
        }
        leaf RFTxStatus {
          type boolean;
          config false;
          description
            "Current status of this LTE FAP RF transmitter.
          
             {{true}} indicates that the LTE FAP Tx transmitter
             is on.
          
             {{false}} indicates that the LTE FAP Tx transmitter
             is off.
          
             This state is tied to the Administrative state which
             is controlled by the ACS.
          
             :When the ACS sets {{param|AdminState}} to {{true}},
             then the LTE FAP has permission to turn on the RF
             transmitter.
          
             :When the ACS sets {{param|AdminState}} to
             {{false}}, then the LTE FAP is not allowed to
             provide service and MUST turn off the RF
             transmitter.";
        }
        leaf PMConfig {
          type string {
            length "0..256";
          }
          description
            "The value MUST be the path name of a row in optional
             the ''.FAP.PerfMgmt.Config.'' table (see
             {{bibref|TR-262}}).
          
             This is the performance management related
             configuration for the LTE FAP.  In case of a
             multiple-radio-technology FAP product, each radio
             technology can have its own PM configuration or
             share a common PM configuration.  In the former
             case, {{param}} can contain a unique instance
             number.  In the latter case, {{param}} under all
             radio technologies can have the same instance
             number.
          
             If the referenced object is deleted, the parameter
             value MUST be set to an empty string.";
        }

        container Gateway {
          description
            "This object contains parameters relating to the
             Gateways that the LTE FAP is connected to.";
          leaf SecGWServer1 {
            type string {
              length "0..64";
            }
            description
              "First SecGW the LTE FAP attempts to establish
               connection with.  Either hostname or IPaddress.";
          }
          leaf SecGWServer2 {
            type string {
              length "0..64";
            }
            description
              "Second SecGW the LTE FAP attempts to establish
               connection with.  Either hostname or IPaddress.";
          }
          leaf SecGWServer3 {
            type string {
              length "0..64";
            }
            description
              "Third SecGW the LTE FAP attempts to establish
               connection with.  Either hostname or IPaddress.";
          }
          leaf S1SigLinkServerList {
            type string;
            description
              "{{list}} Each item is a S1 signaling connection end
               point (-GW or MME) the LTE FAP attempts to
               establish connection with.  It is in the form of
               either hostname or IPaddress.  LTE FAP's behavior
               in terms of the number of S1 connection to
               established with is determined by
               {{param|S1ConnectionMode}} parameter.  If
               {{param|S1ConnectionMode}} has the value of
               {{enum|One|S1ConnectionMode}}, then LTE FAP
               attempts to establish S1 connection with only one
               address following the ordering of the list.  If
               {{param|S1ConnectionMode}} has the value of
               {{enum|All|S1ConnectionMode}}, then LTE FAP
               attempts to establish connection with all
               addresses in the list.";
          }
          leaf S1ConnectionMode {
            type enumeration {
              enum "One";
              enum "All";
            }
            description
              "Indicates how many of the configured far-end S1 link
               address(es),as defined in
               {{param|S1SigLinkServerList}}, LTE FAP SHOULD
               attempt to establish connection with
               simultaneously.  If {{param}} parameter is not
               explicitly configured, then LTE FAP shall assume
               the value to be {{enum|One|S1ConnectionMode}} as
               default.";
          }
          leaf S1SigLinkPort {
            type uint32 {
              range "min..65535";
            }
            description
              "Port number of S1AP signaling connection end point
               (-GW or MME) used for initial S1 SCTP contact.
               This value is specified as 36412 according to IANA
               definition per {{bibref|IANA-portnumbers}},
               registered on 2009-09-01.  Use of IANA-defined
               value is recommended.";
          }
        }
      }

      container CDMA2000 {
        description
          "This object contains parameters relating to the
           configuration for the control portions of a CDMA2000
           FAP.";
        leaf HomeDomain {
          type string {
            length "0..256";
          }
          description
            "A string containing one of operator's home domains in
             URI format.  FAP is preconfigured with a default
             home domain, which can be overwritten later by ACS.
             See {{bibref|3GPP2-X.S0059}}.
          
             If the''.ManagementServer.URL'' is null, then the
             FAP shall use the value of this attribute to
             construct the ''.ManagementServer.URL'' attribute.
          
             If
             {{param|.FAPControl.CDMA2000.Gateway.SecGWServer1}}
             is null, then the FAP shall use the value of this
             attribute to construct the
             {{param|.FAPControl.CDMA2000.Gateway.SecGWServer1}}
             attribute.
          
             If the FAP is unable to connect to the management
             server indicated by the value of the
             ''.ManagementServer.URL'' attribute and this
             attribute is not null, the FAP may use the value of
             this attribute to construct the
             ''.ManagementServer.URL'' attribute.
          
             If the FAP is unable to connect to any security
             gateway indicated by the value of the
             {{param|.FAPControl.CDMA2000.Gateway.SecGWServer1}},
             {{param|.FAPControl.CDMA2000.Gateway.SecGWServer2}},
             and
             {{param|.FAPControl.CDMA2000.Gateway.SecGWServer3}}
             attributes and this attribute is not null, the FAP
             may use the value of this attribute to construct the
             {{param|.FAPControl.CDMA2000.Gateway.SecGWServer1}}
             attribute.";
        }
        leaf RemoteIPAccessEnable {
          type boolean;
          description
            "Enable or disable remote IP access service as defined
             in {{bibref|3GPP2-X.S0059}}.  If {{true}} remote IP
             access is enabled.  If {{false}} remove IP access is
             disabled.";
        }
        leaf PMConfig {
          type string {
            length "0..256";
          }
          description
            "The value MUST be the path name of a row in the
             ''.FAP.PerfMgmt.Config.'' table.
          
             This is the performance management related
             configuration for the CDMA2000 FAP.  In case of a
             multiple-radio-technology FAP product, each radio
             technology can have its own PM configuration or
             share a common PM configuration.  In the former
             case, {{param}} can contain a unique instance
             number.  In the latter case, {{param}} under all
             radio technologies can have the same instance
             number.
          
             If the referenced object is deleted, the parameter
             value MUST be set to an empty string.";
        }

        container Time {
          description
            "This object contains parameters related to time
             syncronization with CDMA2000 System Time (see
             {{bibref|3GPP2-C.S0005}}).";
          leaf LocalTimeZone {
            type string {
              length "0..256";
            }
            description
              "The local time zone for CDMA2000 operational
               purposes.  E.g., \"+HH:MM JST\" for Japan.  See
               {{bibref|3GPP2-C.S0005}}.";
          }
          leaf CurrentLocalTime {
            type string {
              length "0..64";
            }
            config false;
            description
              "The current CDMA System Time (see
               {{bibref|3GPP2-C.S0005}}), expressed as date and
               time in the CPE's local time zone.  The format of
               this field is \"YYYY-MM-DDThh:mm:ss.sTZD\" (e.g.,
               1997-07-16T19:20:30.45+01:00),
            
               where:
            
               YYYY = four-digit year
            
               MM = two-digit month (01=January, etc.)
            
               DD = two-digit day of month (01 through 31)
            
               hh = two digits of hour (00 through 23) (am/pm NOT
               allowed)
            
               mm = two digits of minute (00 through 59)
            
               ss = two digits of second (00 through 59)
            
               s = one or more digits representing a decimal
               fraction of a second
            
               TZD = time zone designator (Z or +hh:mm or -hh:mm)";
          }
          leaf LeapSeconds {
            type int32 {
              range "0..255";
            }
            description
              "Number of leap seconds (in {{units}} to be applied
               between CurrentLocalTime and CDMA System Time.
               See {{bibref|3GPP2-C.S0005}}.";
          }
          leaf DaylightSavingsUsed {
            type boolean;
            description
              "Whether or not daylight savings time is in use in the
               FAP's local time zone with respect to CDMA2000
               System Time (see {{bibref|3GPP2-C.S0005}}).
               {true}} if daylight savings time is being used;
               otherwise {{false}}.  See
               {{bibref|3GPP2-C.S0005}}.";
          }
        }

        container OneX {
          description
            "This object contains all global attributes of the
             1xFemto application.";
          leaf AdminState {
            type enumeration {
              enum "Lock";
              enum "Unlock";
            }
            description
              "Administrative state for 1x";
          }
          leaf OpState {
            type enumeration {
              enum "Enabled";
              enum "Disabled";
            }
            config false;
            description
              "Operational state of the 1x";
          }
          leaf RFTxStatus {
            type boolean;
            config false;
            description
              "Current status of this RF transmitter.  {{true}}
               indicates that the 3G Tx transmitter is on.
               {{false}} indicates that the 3G Tx transmitter is
               off.  This state is tied to the Administrative
               state which is controlled by the ACS.  When the
               ACS sets AdminState to {{true}}, then the FAP has
               permission to turn on the RF transmitter.  When
               the ACS sets AdminState to {{false}}, then the FAP
               is not allowed to provide service and MUST turn
               off the RF transmitter.";
          }
          leaf Daylight {
            type int32 {
              range "0..1";
            }
            description
              "If Daylight Savings Time is being used with respect
               to CDMA2000 1x overhead parameters (see
               {{bibref|3GPP2-C.S0005}}), then {{param}} should
               be set to {{true}}.  Otherwise, {{param}} should
               be set to {{false}}.";
          }
          leaf MaxPRev {
            type int32 {
              range "6..9";
            }
            description
              "Protocol revision supported by the FAP.";
          }
          leaf Reregister {
            type uint32;
            description
              "{{param}} triggers a re-registration of all mobiles.
               The FAP triggers re-registration of all registered
               mobiles everytime this number changes";
          }
          leaf EmergencySessionPeriod {
            type uint32 {
              range "15..1800";
            }
            description
              "The period (in {{units}}) the session of an
               unauthorized user is kept alive after an emergency
               call.";
          }
          leaf LocationAreaCode {
            type uint32 {
              range "0..65535";
            }
            description
              "This is the location area code.";
          }
          leaf MSCId {
            type uint32;
            description
              "This is the FAP's MSCID.  This ID is used in PANI
               header.";
          }
          leaf ActiveHandinEnable {
            type boolean;
            description
              "Indicates whether the FAP performs active hand-in
               from another base station.  If {{true}} active
               hand-in is enabled; if {{false}} active hand-in is
               disabled.";
          }

          container ActiveHandinMeasurement {
            description
              "CDMA2000 1x active handin operational parameters.";
            leaf ActiveHandinMeasurementEnable {
              type boolean;
              description
                "Indicates whether the FAP performs active hand-in
                 measurement if a request is received.  If
                 {{true}} active hand-in measurement is enabled;
                 if {{false}} active hand-in measurement is
                 disabled.";
            }
            leaf ActiveHandInMeasurementDuration {
              type uint32 {
                range "0..65535";
              }
              description
                "The minimum duration in {{units}} for which FAP
                 should take a mobile's RL pilot strength
                 measurements for active hand-in purpose when
                 directed by the network.  Instead of continuous
                 measurement for this entire duration, a FAP can
                 make multiple measurements by sampling over
                 shorter durations.  In such a case, this value
                 specifies the minimum time separation required
                 between the first and last measurement samples.";
            }
            leaf MeasurementReportThreshold {
              type int32 {
                range "-150..0";
              }
              description
                "The threshold (in {{units}}) for the FAP to report
                 an active hand-in measurement.  If the metric to
                 be reported is below the threshold, the FAP may
                 not send any report.";
            }
          }

          container SelfConfig {
            description
              "This object contains parameters relating to the
               controlling of self-configuration capabilities in
               the FAP.";
            leaf RFCNFLSelfConfigEnable {
              type boolean;
              description
                "Indicates whether the self-configuration capability
                 in the FAP is used or not to determine the
                 values of
                 {{param|.CellConfig.CDMA2000.OneX.RAN.RF.RFCNFL}}.
                 If {{true}}, the FAP self-configures the value.
                 If {{false}}, the ACS must provide the specific
                 value to be used.";
            }
            leaf PilotPNSelfConfigEnable {
              type boolean;
              description
                "Indicates whether the self-configuration capability
                 in the FAP is used or not to determine the value
                 of
                 {{param|.CellConfig.CDMA2000.OneX.RAN.RF.PilotPN}}.
                 If {{true}} the FAP self-configures the value.
                 If {{false}} the ACS must provide the specific
                 value to be used.";
            }
            leaf MaxFAPTxPowerSelfConfigEnable {
              type boolean;
              description
                "Indicates whether the self-configuration capability
                 in the FAP is used or not to determine the value
                 of
                 {{param|.CellConfig.CDMA2000.OneX.RAN.RF.MaxFAPTxPower}}.
                 If {{true}} the FAP self-configures the value.
                 If {{false}} the ACS must provide the specific
                 value to be used.";
            }
            leaf MaxFAPBeaconTxPowerSelfConfigEnable {
              type boolean;
              description
                "Indicates whether the self-configuration capability
                 in the FAP is used or not to determine the value
                 of
                 {{param|.CellConfig.CDMA2000.Beacon.MaxFAPBeaconTxPower}}.
                 If {{true}}, the FAP self-configures the value.
                 If {{false}}, the ACS must provide the specific
                 value to be used.";
            }
          }
        }

        container Gateway {
          description
            "CDMA2000 FAP Security Gateway operational parameters.";
          leaf SecGWServer1 {
            type string {
              length "0..64";
            }
            description
              "First SecGW the FAP attempts to contact.  Either FQDN
               or IP address";
          }
          leaf SecGWServer2 {
            type string {
              length "0..64";
            }
            description
              "Second SecGW the FAP attempts to contact.  Either
               FQDN or IP address";
          }
          leaf SecGWServer3 {
            type string {
              length "0..64";
            }
            description
              "Third SecGW that the FAP attempts to contact.  Can
               contain either FQDN or IP address";
          }
          leaf SecGWSwitchoverCount {
            type uint32;
            config false;
            description
              "Counter indicating how many times FAP has switched
               between SecGW";
          }
        }

        container HRPD {
          description
            "Operational parameters for the HRPD portion of a
             CDMA2000 FAP.";
          leaf OpState {
            type boolean;
            config false;
            description
              "Current operational state of the FAP as defined in
               ITU-X.731 [32].  If {{true}} the FAP is currently
               enabled.  If {{false}} the FAP is currently
               disabled.";
          }
          leaf AdminState {
            type boolean;
            description
              "Lock or unlock the FAP.  This controls the
               administrative state of the FAP as defined in
               ITU-X.731 [32].  If {{true}} Unlocked with
               permission to serve traffic (and enable RF
               transmitter(s)).  If {{false}} Locked.  Transition
               FAP to state where it is NOT permitted to serve
               traffic.  RF transmitter is disabled.  Given that
               this command controls the FAP's RF transmitter,
               the underlying expectation is that the unlock is
               done when all necessary conditions are met to
               allow the transmitter to key on and provide
               service, including aspects such as: location
               verification (including meeting the governing
               regulatory requirements) verifying the FAP
               configuration if physical tampering is supported
               and no physical tampering is detected.  The
               default value after power-on is {{false}}.";
          }
          leaf RFTxStatus {
            type boolean;
            config false;
            description
              "Current status of this RF transmitter.  {{true}}
               indicates that the 3G Tx transmitter is on.
               {{false}} indicates that the 3G Tx transmitter is
               off.  This state is tied to the Administrative
               state which is controlled by the ACS.  When the
               ACS sets AdminState to {{true}}, then the FAP has
               permission to turn on the RF transmitter.  When
               the ACS sets AdminState to {{false}}, then the FAP
               is not allowed to provide service and MUST turn
               off the RF transmitter.";
          }
          leaf A13SessionTransferEnable {
            type boolean;
            description
              "Indicates whether the FAP performs A13 session
               transfer.  If {{true}} A13 session transfer is
               enabled; if {{false}} A13 session transfer is
               disabled.";
          }
          leaf LocalIPAccessEnable {
            type boolean;
            description
              "Indicates whether the FAP can assign local IP address
               to capable ATs.  If {{true}} local IP address is
               assigned.; if {{false}} local IP address is not
               assigned.";
          }

          container SelfConfig {
            description
              "This object contains parameters relating to the
               controlling of self-configuration capabilities in
               the FAP.";
            leaf RFCNFLSelfConfigEnable {
              type boolean;
              description
                "Indicates whether the self-configuration capability
                 in the FAP is used or not to determine the
                 values of
                 {{param|.CellConfig.CDMA2000.HRPD.RAN.RF.RFCNFL}}.
                 If {{true}}, the FAP self-configures the value.
                 If {{false}}, the ACS must provide the specific
                 value to be used.";
            }
            leaf PilotPNSelfConfigEnable {
              type boolean;
              description
                "Indicates whether the self-configuration capability
                 in the FAP is used or not to determine the value
                 of
                 {{param|.CellConfig.CDMA2000.HRPD.RAN.RF.PilotPN}}.
                 If {{true}}, the FAP self-configures the value.
                 If {{false}}, the ACS must provide the specific
                 value to be used.";
            }
            leaf MaxFAPTxPowerSelfConfigEnable {
              type boolean;
              description
                "Indicates whether the self-configuration capability
                 in the FAP is used or not to determine the value
                 of
                 {{param|.CellConfig.CDMA2000.HRPD.RAN.RF.MaxFAPTxPower}}
                 .  If {{true}}, the FAP self-configures the
                 value.  If {{false}}, the ACS must provide the
                 specific value to be used.";
            }
            leaf MaxHRPDBeaconTxPowerSelfConfigEnable {
              type boolean;
              description
                "Indicates whether the self-configuration capability
                 in the FAP is used or not to determine the value
                 of
                 {{param|.CellConfig.CDMA2000.Beacon.MaxHRPDBeaconTxPower}}.
                 If {{true}} the FAP self-configures the value.
                 If {{false}} The ACS must provide the specific
                 value to be used.";
            }
          }

          container A13 {
            description
              "This object contains attributes related to A13
               Session Transfer";

            list ColorCodeToUATI104 {
              key "ColorCode UATI104";
              min-elements 1;
              description
                "HRPD ColorCode to UATI Mapping Table number of
                 entries.";
              leaf Enable {
                type boolean;
                default "false";
                description
                  "Enables or disables the {{object}} entry.";
              }
              leaf ColorCode {
                type uint32 {
                  range "0..256";
                }
                default "0";
                description
                  "Color Code mapped to UATI104 in the following
                   field";
              }
              leaf UATI104 {
                type yang:hex-string {
                  length "0..13";
                }
                default "";
                description
                  "The UATI104 of the AT that accesses with the
                   ColorCode field";
              }
            }

            list HRPDSubnetToIP {
              key "A13IPAddress";
              min-elements 1;
              description
                "This object contains attributes related to A13
                 Session Transfer";
              leaf Enable {
                type boolean;
                default "false";
                description
                  "Enables or disables the {{object}} entry.";
              }
              leaf HRPDSubnetLength {
                type uint32 {
                  range "1..104";
                }
                default "104";
                description
                  "The number of MSBs (in {{units}}) in the
                   following field that is part of HRPDSubnet";
              }
              leaf HRPDSubnet {
                type yang:hex-string {
                  length "0..13";
                }
                default "";
                description
                  "The {{param|HRPDSubnetLength}} MSBs of this field
                   contain the HRPD subnet that maps to the IP
                   address in the following field";
              }
              leaf A13IPAddress {
                type types:IPAddress;
                default "";
                description
                  "This field contains the IP address of A13
                   endpoint that corresponds to the HRPD subnet";
              }
            }
          }
        }
      }
    }

    container AccessMgmt {
      description
        "This object contains parameters relating to Access
         Management for the different radio technologies.";

      container UMTS {
        description
          "This object contains parameters relating to Access
           Management for UMTS FAP (ACL, CSG, LIPA).
        
           Closed Subscriber Group (CSG) service behavior is
           specified in {{bibref|3GPP-TS.22.011}}.
        
           Note: Cell barring and 3GPP access class parameters
           are contained in
           {{object|.CellConfig.UMTS.RAN.CellRestriction.}} (UMTS
           FAP).";
        leaf AccessMode {
          type enumeration {
            enum "Open Access";
            enum "Closed Access";
            enum "Hybrid Access";
          }
          default "Open Access";
          description
            "Indicates the type of access mode the FAP operates in.
             {{enum}}
          
             When the value is not {{enum|Open Access}}
             non-CSG-capable UE are handled according to
             {{param|NonCSGUEAccessDecision}}.  Note: This
             parameter controls the setting of the CSGindicator
             bit, specified in MIB in {{bibref|3GPP-TS.25.331}}.";
        }
        leaf NonCSGUEAccessDecision {
          type enumeration {
            enum "Local";
            enum "Query FAPGW";
            enum "By Core";
          }
          default "Local";
          description
            "Indicates how the access decision is made for
             non-CSG-capable UE.  Parameter is ignored when
             {{param|AccessMode}} is {{enum|Open
             Access|AccessMode}}.";
        }
        leaf CSGMembershipDeterminedLocally {
          type boolean;
          default "false";
          description
            "Indicates how the access decision is made for
             CSG-capable UE.  Parameter is ignored when
             {{param|AccessMode}} is {{enum|Open
             Access|AccessMode}}.
          
             If {{true}} access decision is determined the same
             way as for {{param|NonCSGUEAccessDecision}}.  (E.g.
             if core network doesn't (yet) support full CSG
             functionality.)
          
             If {{false}} FAP always allows access for
             CSG-capable UE.
          
             CSG enforcement is performed by MSC/SGSN (with
             support from HSS), or by FGW.
          
             {{bibref|3GPP-TS.22.011}}";
        }
        leaf MaxUEsServed {
          type int32 {
            range "-1..max";
          }
          default "-1";
          description
            "Maximum number of concurrent UEs allowed at a cell.
             Valid for any {{param|AccessMode}}.  A value of -1
             allows an unlimited number of concurrent UEs up to
             the limit of FAP capacity.  The setting does not
             affect emergency calls.";
        }
        leaf MaxCSGMembers {
          type int32 {
            range "-1..max";
          }
          default "-1";
          description
            "Maximum number of concurrent CSG member UEs allowed at
             a hybrid or closed cell.  A value of -1 allows an
             unlimited number of CSG members up to the limit of
             FAP capacity.  The setting cannot be larger than the
             value of {{param|MaxUEsServed}}.  The setting does
             not affect emergency calls.
             {{bibref|3GPP-TS.22.011}},
             {{bibref|3GPP-TS.22.220}}.";
        }
        leaf MaxNonCSGMembers {
          type int32 {
            range "-1..max";
          }
          default "-1";
          description
            "Maximum number of concurerent non-CSG member UEs
             allowed at a hybrid cell.  Valid only if
             {{param|AccessMode}} is {{enum|Hybrid
             Access|AccessMode}}.  The setting cannot be larger
             than the value of {{param|MaxUEsServed}}.  The
             setting does not affect emergency calls.";
        }
        leaf MaxResourceNonCSGMembers {
          type uint32 {
            range "0..100";
          }
          description
            "Maximum percentage of physical resource that can be
             assigned to non-CSG members aggregately at one time.
             In UMTS FAP, this applies to RB resource.";
        }
        leaf HNBName {
          type string {
            length "0..48";
          }
          description
            "Home NodeB name.  An operator-defined string that is
             broadcast by a CSG cell or a hybrid cell and
             displayed on the UE for the purpose of manual cell
             selection or indication that the UE is camped on the
             cell as specified in {{bibref|3GPP-TS.22.220|Section
             5.4.2}}.  Corresponds to parameter 'hnb-Name'
             specified in SIB20 in
             {{bibref|3GPP-TS.25.331|Section 10.2.48.8.23}}.";
        }
        leaf CSGID {
          type uint32 {
            range "min..134217727";
          }
          description
            "Defines the Closed Subscriber Group of the Access
             Control List.  The UMTS FAP broadcasts this CSG ID
             in SIB3 depending on the AccessMode.  The LTE FAP
             broadcasts this in SIB1, and corresponds to
             parameter csg-Identity in SIB1 in
             {{bibref|3GPP-TS.36.331}}.";
        }
        leaf AccessControlList {
          type string {
            length "0..15";
          }
          description
            "{{list}} Each entry is an IMSI.";
        }
        leaf MaxMemberDetailEntries {
          type uint32;
          config false;
          description
            "The maximum number of entries available in the
             {{object|.AccessMgmt.UMTS.MemberDetail.{i}.}} table.";
        }

        list MemberDetail {
          key "IMSI";
          description
            "Details for CSG and Non-CSG members.";
          leaf Enable {
            type boolean;
            default "false";
            description
              "Enables or disables the MemberDetail entry.";
          }
          leaf IMSI {
            type string {
              length "0..15";
            }
            default "";
            description
              "International Mobile Subscriber Identity of the UE.";
          }
          leaf MSISDN {
            type string {
              length "0..15";
            }
            default "";
            description
              "Mobile Station International Subscriber Identity
               Number.  Set to {{empty}} if unknown.";
          }
          leaf MembershipExpires {
            type yang:date-and-time;
            default "0001-01-01T00:00:00Z";
            description
              "Time when the ACL membership expires.
            
               An Unknown Time value, as defined in
               {{bibref|TR-106a2|Section 3.2}}, indicates that
               the membership doesn't expire.
            
               Upon expiry the FAP MUST remove the IMSI from the
               {{param|.AccessMgmt.UMTS.AccessControlList}}, but
               the entry in
               {{object|.AccessMgmt.UMTS.MemberDetail.{i}.}}
               remains.  {{bibref|3GPP-TS.22.011}}";
          }
        }

        container LocalIPAccess {
          description
            "Local IP access for UMTS FAP.";
          leaf Enable {
            type boolean;
            default "false";
            description
              "Enables/disables the Local IP Access (LIPA)
               functionality.";
          }
        }
      }

      container LTE {
        description
          "This object contains parameters relating to Access
           Management, as defined in {{bibref|3GPP-TS.32.592}}/
        
           Closed Subscriber Group (CSG) service behavior is
           specified in {{bibref|3GPP-TS.22.011}}.
        
           Note: Cell barring and 3GPP access class parameters
           are contained in SIB1 in {{bibref|3GPP-TS.36.331}}.";
        leaf AccessMode {
          type enumeration {
            enum "Open Access";
            enum "Closed Access";
            enum "Hybrid Access";
          }
          default "Open Access";
          description
            "Indicates the type of access mode the FAP operates in.
             {{enum}}
          
             Note: This parameter controls the setting of the
             CSGindicator bit, specified in SIB1 in
             {{bibref|3GPP-TS.36.331}}.";
        }
        leaf MaxUEsServed {
          type int32 {
            range "-1..max";
          }
          default "-1";
          description
            "Maximum number of concurrent UEs allowed at a cell.
             Valid for any {{param|AccessMode}}.  A value of -1
             allows an unlimited number of concurrent UEs up to
             the limit of FAP capacity.  The setting does not
             affect emergency calls.";
        }
        leaf MaxCSGMembers {
          type int32 {
            range "-1..max";
          }
          default "-1";
          description
            "Maximum number of concurrent CSG member UEs allowed at
             a hybrid or closed cell.  A value of -1 allows an
             unlimited number of CSG members up to the limit of
             FAP capacity.  The setting cannot be larger than the
             value of {{param|MaxUEsServed}}.  The setting does
             not affect emergency calls.
             {{bibref|3GPP-TS.22.011}},
             {{bibref|3GPP-TS.22.220}}.";
        }
        leaf MaxNonCSGMembers {
          type int32 {
            range "-1..max";
          }
          default "-1";
          description
            "Maximum number of concurerent non-CSG member UEs
             allowed at a hybrid cell.  Valid only if
             {{param|AccessMode}} is {{enum|Hybrid
             Access|AccessMode}}.  The setting cannot be larger
             than the value of {{param|MaxUEsServed}}.  The
             setting does not affect emergency calls.";
        }
        leaf MaxResourceNonCSGMembers {
          type uint32 {
            range "0..100";
          }
          description
            "Maximum percentage of physical resource that can be
             assigned to non-CSG members aggregately at one time.
             This applies to PDSCH physical resource blocks.";
        }
        leaf CSGID {
          type uint32 {
            range "min..134217727";
          }
          description
            "Defines the Closed Subscriber Group of the Access
             Control List.  The LTE FAP broadcasts this in SIB1,
             and corresponds to parameter csg-Identity in SIB1 in
             {{bibref|3GPP-TS.36.331}}.";
        }
        leaf HNBName {
          type string {
            length "0..48";
          }
          description
            "Home NodeB name.  An operator-defined string that is
             broadcast by a CSG cell or a hybrid cell and
             displayed on the UE for the purpose of manual cell
             selection or indication that the UE is camped on the
             cell as specified in {{bibref|3GPP-TS.22.220|Section
             5.4.2}}.  Corresponds to parameter 'hnb-Name'
             specified in SIB9 in {{bibref|3GPP-TS.36.331|Section
             6.3.1}}.";
        }

        container LocalIPAccess {
          description
            "Local IP access for LTE FAP.";
          leaf Enable {
            type boolean;
            default "false";
            description
              "Enables/disables the Local IP Access (LIPA)
               functionality.";
          }
        }
      }

      container CDMA2000 {
        description
          "This object contains configurable and observable
           attributes related to CDMA2000 Access and Admission
           Control of the FAP.";
        leaf AccessMode {
          type uint32 {
            range "0 | 1 | 3";
          }
          description
            "Defines the access control mode of FAP.  Allowed modes
             are Open, Closed, and Signaling Association (refer
             to {{bibref|3GPP2-A.S0024}}).  AccessMode 2 (Hybrid)
             is not applicable to CDMA2000 FAPs.  0-
             Open,1-Closed, 2-Reserved, 3-Signaling Association.";
        }
        leaf MaxTotalActiveCallsAllowed {
          type uint32 {
            range "1..1024";
          }
          description
            "Total number of active calls allowed.";
        }
        leaf AccessControlList {
          type string {
            length "0..1024";
          }
          description
            "{{list}} (maximum item length 15).  Each entry is an
             IMSI.";
        }
        leaf MaxMemberDetailEntries {
          type uint32;
          config false;
          description
            "The maximum number of entries available in the
             {{object|.AccessMgmt.CDMA2000.MemberDetail.{i}.}}
             table.";
        }

        list MemberDetail {
          key "IMSI";
          min-elements 1;
          description
            "At most one enabled entry in this table can exist with
             a given value for IMSI and HRPDIdentifierValue.  The
             IMSI field may be empty.";
          leaf Enable {
            type boolean;
            default "false";
            description
              "Enables or disables the {{object}} entry.";
          }
          leaf IMSI {
            type string {
              length "0..15";
            }
            default "";
            description
              "International Mobile Subscriber Identity of the UE.";
          }
          leaf HRPDIdentifierType {
            type int32 {
              range "0..3";
            }
            default "0";
            description
              "Type of identifier used for the HRPD AT.  0-invalid
               1-ESN 2-MEID 3-A12NAI.  If IMSI in this record is
               valid, then this attribute is set to 0.";
          }
          leaf HRPDIdentifierValue {
            type string {
              length "0..128";
            }
            default "";
            description
              "The value of this attribute depends on
               {{param|HRPDIdentifierType}}.  ESN and MEID shall
               be defined as Hex.";
          }
          leaf MembershipExpires {
            type yang:date-and-time;
            default "";
            description
              "The time that the current ACL membership expires.";
          }
        }

        container LocalIPAccess {
          description
            "Local IP access support as defined in 3GPP2";

          container HRPD {
            description
              "Local IP access support as defined in 3GPP2";
            leaf FilterType {
              type uint32 {
                range "0..3";
              }
              description
                "Value of '0' indicates that the FAP shall allow
                 only IP packets with destination address
                 matching the local IP subnet on Local IP access
                 interface.  Value of '1' indicates that the FAP
                 shall allow any IP packets with destination
                 address matching either the local IP subnet or
                 the subnets listed in Local IP egress filter
                 parameter on Local IP access interface.  Value
                 of '2' indicates that the FAP shall allow any IP
                 packets with destination addresses that do not
                 match the Local IP egress filter parameter on
                 Local IP access interface.Value of '3' indicates
                 that the FAP shall allow any IP packets on the
                 local IP address interface.";
            }
            leaf FilterInUse {
              type string {
                length "0..256";
              }
              config false;
              description
                "This parameter is set to the IPCP Vendor Specific
                 Option which the FAP uses to send Local IP
                 access packet filter on AN-PPP interface.";
            }

            list EgressFilter {
              key "Subnet SubnetMask";
              min-elements 1;
              description
                "HRPD LIPA Egress Filter Table entries.";
              leaf Enable {
                type boolean;
                default "false";
                description
                  "Enables or disables the {{object}} entry.";
              }
              leaf Subnet {
                type types:IPv4Address;
                default "";
                description
                  "The IP subnet of the egress filter to be
                   installed to the AT.  The meaning of this
                   field depends on the
                   {{param|.AccessMgmt.CDMA2000.LocalIPAccess.HRPD.FilterType}}
                   field.";
              }
              leaf SubnetMask {
                type uint32 {
                  range "0..32";
                }
                default "0";
                description
                  "The length of the IP subnetmask associated with
                   the IP subnet in the previous field.";
              }
            }
          }
        }
      }

      container Legacy {
        description
          "This object contains configurable and observable
           attributes related to Access and Admission Control of
           the FAP, which are not not covered by 3GPP and 3GPP2
           specifications.";

        container LocalIPAccess {
          description
            "Old Local IP access object, included on special
             request.";
          leaf Enable {
            type boolean;
            default "false";
            description
              "Enables/disables the Local IP Access (LIPA)
               functionality.";
          }
          leaf MaxRulesEntries {
            type uint32;
            config false;
            description
              "The maximum number of entries available in the
               {{object|.AccessMgmt.Legacy.LocalIPAccess.Rule.{i}.}}
               table.";
          }

          list Rule {
            key "DestIPAddress DestSubnetMask Protocol";
            description
              "Policy for selecting traffic for local IP access.
               Originated traffic will be NAT'ed.  The rule is
               bi-directional, i.e.  return traffic is allowed.
               Rules do NOT affect traffic to/from the FAP itself
               (such as TR-069 or control).  The rules are
               applied to the mobile station data traffic
               (PS-domain) via deep packet inspection or similar
               method.";
            leaf Enable {
              type boolean;
              default "false";
              description
                "Enables or disables the forwarding entry.";
            }
            leaf DestIPAddress {
              type types:IPAddress;
              default "";
              description
                "Destination IP Address.  {{empty}} indicates no
                 destination address is specified.  An entry for
                 which {{param}} and {{param|DestSubnetMask}} are
                 both {{empty}} is a default route.";
            }
            leaf DestSubnetMask {
              type types:IPAddress;
              default "";
              description
                "Destination subnet mask (IPv4) or prefix (IPv6).
                 {{empty}} indicates no destination subnet mask
                 or prefix is specified.  If a destination subnet
                 mask or prefix is specified, {{param}} is ANDed
                 with the destination address before comparing
                 with {{param|DestIPAddress}}.  Otherwise, the
                 full destination address is used as-is.
              
                 An entry for which {{param|DestIPAddress}} and
                 {{param}} are both {{empty}} is a default route.";
            }
            leaf Protocol {
              type int32 {
                range "-1..max";
              }
              default "-1";
              description
                "IP Protocol Identifier.  -1 matches any protocol.";
            }
            leaf Action {
              type enumeration {
                enum "Tunnel";
                enum "NAPT";
              }
              default "Tunnel";
              description
                "Action to be taken for traffic matching this rule.";
            }
            leaf Interface {
              type string {
                length "0..256";
              }
              description
                "Specifies the egress interface when
                 {{param|Action}} is set to {{enum|NAPT|Action}}.
                 {{reference}} layer-3 connection object.
              
                 Example:
                 InternetGatewayDevice.LANDevice.{i}.LANEthernetInterfaceConfig.{i}.";
            }
          }
        }
      }
    }

    container CellConfig {
      description
        "This object contains parameters relating to configuring the
         FAP.";

      container UMTS {
        description
          "This object contains parameters relating to configuring
           UMTS system specific information.";
        leaf TunnelInstance {
          type string {
            length "0..256";
          }
          description
            "This is the reference to the IPsec tunnel instance used
             by the UMTS FAP.
          
             For all root data models, which use the tunnel
             definition provided in {{bibref|TR-262}}
             (InternetGatewayDevice:1 {{bibref|TR-098}} and
             Device:1 {{bibref|TR-181i1}}) the {{param}} MUST
             point to a row in the 'FAP.Tunnel.IKESA.{i}.'
             table, defined in {{bibref|TR-262}}.
          
             If the root data model used is Device:2
             {{bibref|TR-181i2}} than the {{param}} MUST point to
             IPsec tunnel instance defined in
             {{bibref|TR-181i2}}.
          
             If the referenced object is deleted, the parameter
             value MUST be set to an empty string.
          
             In case of a multiple-radio-technology FAP product,
             each radio technology can have its own tunnels or
             share common tunnels.  In the former case, {{param}}
             can contain a unique instance number.  In the latter
             case, {{param}} under all radio technologies can
             have the same instance number.";
        }

        container CN {
          description
            "This object contains parameters relating to configuring
             UMTS CN.";
          leaf PLMNType {
            type enumeration {
              enum "GSM-MAP";
              enum "ANSI-41";
            }
            description
              "Type of Public Land Mobile Network (PLMN).";
          }
          leaf PLMNID {
            type string {
              length "0..6";
            }
            description
              "PLMN ID consists of Mobile Country Code (MCC) and
               Mobile Network Code (MNC)
               {{bibref|3GPP-TS.23.003}},
               {{bibref|3GPP-TS.24.008}}.
            
               Mobile Country Code consists of three digits and
               uniquely identifies the country of domicile of the
               subscriber.
            
               Mobile Network Code consists of two or three
               digits and identifies the Home PLMN within a
               country.
            
               For a 2-digit MNC the total string length of
               {{param}} is 5.";
          }
          leaf EquivPLMNID {
            type string {
              length "0..6";
            }
            description
              "{{list}} Each item is a PLMNID.
            
               PLMN ID consists of Mobile Country Code (MCC) and
               Mobile Network Code (MNC)
               {{bibref|3GPP-TS.23.003}},
               {{bibref|3GPP-TS.24.008}}.
            
               Mobile Country Code consists of three digits and
               uniquely identifies the country of domicile of the
               subscriber.
            
               Mobile Network Code consists of two or three
               digits and identifies the Home PLMN within a
               country.
            
               For a 2-digit MNC the total string length of the
               PLMNID is 5.";
          }
          leaf SAC {
            type uint32 {
              range "0..65535";
            }
            description
              "Service Area Code (SAC) {{bibref|3GPP-TS.23.003}}.
            
               The concatenation of PLMN ID (MCC+MNC), LAC, and
               SAC uniquely identifies the Service Area ID (SAI).";
          }
          leaf BroadcastSAC {
            type uint32 {
              range "0..65535";
            }
            description
              "Service Area Code (SAC) for broadcast.  The format of
               this parameter is the same with {{param|SAC}}, and
               it uniquely identifies the Service Area ID (SAI)
               for Earthquake and Tsunami Warning Services (ETWS)
               {{bibref|3GPP-TS.25.469|Section 9.1.3}}.";
          }
          leaf LACRAC {
            type string;
            description
              "{{list}} Each item is a LAC/RAC combination expressed
               in the following format:
            
               :<LAC or LACrange>':'<RAC or RACrange>
            
               Where LAC and RAC are single values, while
               LACrange and RACrange are inclusive and can be
               expressed in the following format:
            
               :<Start-value>\"..\"<End-value>
            
               Location Area Code (LAC) consists of up to 5
               numerical characters.  The concatenation of PLMN
               ID (MCC+MNC) and LAC uniquely identifies the
               Location Area ID (LAI).
               {{bibref|3GPP-TS.23.003|Section 4.1}}
               {{bibref|3GPP-TS.25.413|Section 9.2.3.6}}.
            
               Routing Area Code (RAC) consists of up to 3
               numerical characters.  The concatenation of PLMN
               ID (MCC+MNC), LAC, and RAC uniquely identifies the
               Routing Area ID (RAI).
               {{bibref|3GPP-TS.23.003|Section 4.2}}
               {{bibref|3GPP-TS.25.413|Section 9.2.3.7}}.
            
               The FAP is to select one LAC and RAC from the
               combination(s) expressed in this parameter for use
               in {{param|LACInUse}} and {{param|RACInUse}}
               respectively.
            
               If a LAC occurs more than once in the list, this
               shall not increase the chance that it is selected
               over other LAC values in the list.
            
               The following are examples of the valid LACRAC
               combination formats:
            
               :\"64000:210\"
            
               ::(one list item with single value for LAC and
               RAC)
            
               :\"64000..64100:210, 64101:211\"
            
               ::(two list items, first item has a LAC range)
            
               :\"64000:210..214, 64001:215..219\"
            
               ::(two list items, both items have a RAC range for
               a specific LAC value)
            
               :\"64000..64100:210..214\"
            
               ::(one list item both have a LAC range and a RAC
               range)";
          }
          leaf LACInUse {
            type uint32 {
              range "min..65535";
            }
            config false;
            description
              "The LAC being used by the FAP.
            
               Self-configuration for LAC is controlled by
               {{param|.Capabilities.UMTS.SelfConfig.LACRACURAConfig}}
               from an availability perspective and
               {{param|.FAPControl.UMTS.SelfConfig.LACRACURASelfConfigEnable}}
               from an enabled perspective.
            
               If the self-configuration capability is available
               and enabled, this parameter indicates the value
               selected by the FAP among the choices provided in
               {{param|LACRAC}}.
            
               If the self-configuration capability is not
               available or not enabled, then this parameter
               contains the first LAC value in {{param|LACRAC}}.";
          }
          leaf RACInUse {
            type uint32 {
              range "min..255";
            }
            config false;
            description
              "The RAC being used by the FAP.
            
               Self-configuration for RAC is controlled by
               {{param|.Capabilities.UMTS.SelfConfig.LACRACURAConfig}}
               from an availability perspective and
               {{param|.FAPControl.UMTS.SelfConfig.LACRACURASelfConfigEnable}}
               from an enabled perspective.
            
               If the self-configuration capability is available
               and enabled, this parameter indicates the value
               selected by the FAP among the choices provided in
               {{param|LACRAC}}.
            
               If the self-configuration capability is not
               available or not enabled, then this parameter
               contains the first RAC value in {{param|LACRAC}}.";
          }

          container CSDomain {
            description
              "This object contains parameters relating to
               configuring the CS domain of the UMTS CN.";
            leaf T3212 {
              type uint32 {
                range "0..91800";
              }
              description
                "T3212 timeout value specified in {{units}}
                 {{bibref|3GPP-TS.24.008|section 10.5.1.12.2}}.
                 The values are implemented by steps of 360
                 {{units}}, which aligns with values in decihours
                 in {{bibref|3GPP-TS.24.008}}.
              
                 The value of 0 is used for infinite timeout
                 value i.e.  periodic updating shall not be used.";
            }
            leaf IMSIAttachDetachEnable {
              type boolean;
              description
                "Indicates the UE behavior regarding IMSI
                 attach/detach procedure to the CN
                 {{bibref|3GPP-TS.24.008}}.
              
                 If {{true}} UE SHALL apply IMSI attach and
                 detach procedure
              
                 If {{false}} UE SHALL NOT apply IMSI attach and
                 detach procedure";
            }

            container RAB {
              config false;
              description
                "This object provides monitoring of the Circuit
                 Switch RAB in the HNB.";

              container Stats {
                description
                  "This object provides the RAB statistics in the CS
                   Domain as defined in
                   {{bibref|3GPP-TS.32.452}}.";
                leaf AttEstabCS {
                  type uint32;
                  description
                    "This measurement provides the total number of
                     requested RABs in establishment attempts.";
                }
                leaf FailEstabCS {
                  type uint32;
                  description
                    "This measurement provides the number of RABs
                     establishment failures for the CS domain.";
                }
                leaf SuccEstabCS {
                  type uint32;
                  description
                    "This measurement provides the number of
                     successfully established RABs for the CS
                     domain.";
                }
                leaf RelDropCS {
                  type uint32;
                  description
                    "This measurement provides the total number of
                     dropped RAB connections for service type CS
                     Domain.";
                }
              }
            }

            container HHO {
              config false;
              description
                "This object provides monitoring of the circuit
                 switch Hard Handover (HHO) in the HNB.";

              container Stats {
                description
                  "This object provides the circuit switch HHO
                   statistics as defined in
                   {{bibref|3GPP-TS.32.452}}.";
                leaf Att3GMacroToHnbCSHO {
                  type uint32;
                  description
                    "This measurement provides the number of
                     attempted 3G Macro to HNB CS handovers.";
                }
                leaf Succ3GMacroToHnbCSHO {
                  type uint32;
                  description
                    "This measurement provides the number of
                     successful 3G Macro to HNB CS handovers.";
                }
                leaf Att2GMacroToHnbCSHO {
                  type uint32;
                  description
                    "This measurement provides the number of
                     attempted 2G Macro to HNB CS handovers.";
                }
                leaf Succ2GMacroToHnbCSHO {
                  type uint32;
                  description
                    "This measurement provides the number of
                     successful 2G Macro to HNB CS handovers.";
                }
              }
            }
          }

          container PSDomain {
            description
              "This object contains parameters relating to
               configuring the PS domain of the UMTS CN.";
            leaf NetworkModeOperationCombined {
              type boolean;
              description
                "Network Mode of Operation of the CN.
                 {{bibref|3GPP-TS.23.060}}
                 {{bibref|3GPP-TS.24.008}}
              
                 If {{true}} (Network Mode of Operation II)
                 Combined procedures between CS and PS domain are
                 not supported (i.e.  Gs interface is not
                 present).
              
                 If {{false}} (Network Mode of Operation I)
                 Combined procedures between CS and PS domain are
                 supported (i.e.  Gs interface is present).";
            }

            container RAB {
              config false;
              description
                "This object provides monitoring of the Packet
                 Switch RAB in the HNB.";

              container Stats {
                description
                  "This object provides the RAB statistics in the PS
                   Domain as defined in
                   {{bibref|3GPP-TS.32.452}}.";
                leaf AttEstabPS {
                  type string;
                  description
                    "This measurement provides the number of
                     requested RAB in establishment attempts for
                     the PS domain by traffic class.
                  
                     {{list| where each item is defined as the
                     \"traffic class name=measurement value\"}}
                     The total of all the measurements is
                     provided using the traffic class name=
                     \"sum\".";
                }
                leaf SuccEstabPS {
                  type uint32;
                  description
                    "This measurement provides the total number of
                     successfully established RABs for the PS
                     domain";
                }
                leaf FailEstabPS {
                  type uint32;
                  description
                    "This measurement provides the total number of
                     RABs establishment failures for the PS
                     domain.";
                }
                leaf RelDropPS {
                  type uint32;
                  description
                    "This measurement provides the total number of
                     abnormally released PS RAB connections.";
                }
                leaf ULNumUserBitsEDCH {
                  type uint64;
                  description
                    "This measurement provides the number of uplink
                     User Bits for PS RABs related with EDCH
                     above RLC.  The average uplink data
                     throughput on EDCH RABs can be derived from
                     this measurement.";
                }
                leaf ULNumUserBits64K {
                  type uint32;
                  description
                    "This measurement provides the number of Uplink
                     User Bits for PS RABs with UL 64 kbps data
                     rate.  The average uplink data throughput on
                     64 kbps RABs can be derived from this
                     measurement.";
                }
                leaf ULNumUserBits128K {
                  type uint32;
                  description
                    "This measurement provides the number of Uplink
                     User Bits for PS RABs with UL 128 kbps data
                     rate.  The average uplink data throughput on
                     128 kbps RABs can be derived from this
                     measurement.";
                }
                leaf ULNumUserBits384K {
                  type uint32;
                  description
                    "This measurement provides the number of Uplink
                     User Bits for PS RABs with UL 384 kbps data
                     rate.  The average uplink data throughput on
                     384 kbps RABs can be derived from this
                     measurement.";
                }
                leaf DLNumUserBitsHSDPA {
                  type uint32;
                  description
                    "This measurement provides the number of
                     Downlink User Bits for PS RABs related with
                     HSDPA above RLC.  The average downlink data
                     throughput on HSDPA RABs can be derived from
                     this measurement.";
                }
                leaf DLNumUserBits64K {
                  type uint32;
                  description
                    "This measurement provides the number of
                     Downlink User Bits for PS RABs (non-HSDPA)
                     with DL 64 kbps data rate above RLC.  The
                     average downlink data throughput on 64 kbps
                     RABs (non-HSDPA) can be derived from this
                     measurement.";
                }
                leaf DLNumUserBits128K {
                  type uint32;
                  description
                    "This measurement provides the number of
                     Downlink User Bits for PS RABs (non-HSDPA)
                     with DL 128 kbps data rate above RLC.  The
                     average downlink data throughput on 128 kbps
                     RABs (non-HSDPA) can be derived from this
                     measurement.";
                }
                leaf DLNumUserBits384K {
                  type uint32;
                  description
                    "This measurement provides the number of
                     Downlink User Bits for PS RABs (non-HSDPA)
                     with DL 384 kbps data rate above RLC.  The
                     average downlink data throughput on 384 kbps
                     RABs (non-HSDPA) can be derived from this
                     measurement.";
                }

                list LGW {
                  key "CorrelationID";
                  description
                    "This object provides statistics for the Direct
                     User Plane Path between HNB and Local
                     Gateway as defined in
                     {{bibref|3GPP-TS.32.452}}.";
                  leaf CorrelationID {
                    type string;
                    description
                      "The value of this parameter is equal to the
                       user plane GGSN TEID that the Gn-SGSN has
                       received or the user plane PDN GW TEID
                       that the S4-SGSN has received.
                       {{bibref|3GPP-TS.25.413}}.";
                  }
                  leaf EstabDirectPathLGWAttNbr {
                    type uint32;
                    description
                      "This measurement provides the number of
                       direct user plane path between HNB and
                       Local GW attempted to setup.";
                  }
                  leaf EstabDirectPathLGWSuccNbr {
                    type uint32;
                    description
                      "This measurement provides the number of
                       direct user plane path between HNB and
                       Local GW successfully established.";
                  }
                  leaf EstabDirectPathLGWFailNbr {
                    type string;
                    description
                      "This measurement provides the number of
                       direct user plane path between HNB and
                       Local GW RABs failed to setup by cause.
                    
                       {{list| where each item is defined as the
                       \"cause name=measurement value\"}} The
                       total of all the measurements is provided
                       using the cause name= \"sum\".";
                  }
                }
              }
            }
          }

          container HHO {
            config false;
            description
              "This object provides monitoring of the Hard Handover
               (HHO) properties in the HNB.";

            container Stats {
              description
                "This object provides the HHO statistics as defined
                 in {{bibref|3GPP-TS.32.452}}.";
              leaf SuccHnbUmtsIntraFreq {
                type uint32;
                description
                  "This measurement provides the number of
                   successful HNB to UMTS macro cell intra
                   frequency hard handovers.";
              }
              leaf AttHnbUmtsIntraFreq {
                type uint32;
                description
                  "This measurement provides the number of attempted
                   HNB to UMTS macro cell intra frequency hard
                   handovers.";
              }
              leaf AttHnbUmtsInterFreq {
                type uint32;
                description
                  "This measurement provides the number of attempted
                   HNB to UMTS macro cell inter frequency hard
                   handovers.";
              }
            }
          }
        }

        container RAN {
          description
            "This object contains parameters relating to the
             RAN-level configuration.";
          leaf URAList {
            type uint32 {
              range "min..65535";
            }
            description
              "{{list}} Each item is a URA (UTRAN Registration Area)
               to which the FAP belongs.
            
               The order of the URA values has no significance.
            
               {{bibref|3GPP-TS.25.331|Section 10.3.2.6}}";
          }
          leaf URAInUse {
            type uint32 {
              range "min..65535";
            }
            config false;
            description
              "The URA being used by the FAP.
            
               Self-configuration for URA is controlled by
               {{param|.Capabilities.UMTS.SelfConfig.LACRACURAConfig}}
               from an availability perspective and
               {{param|.FAPControl.UMTS.SelfConfig.LACRACURASelfConfigEnable}}
               from an enabled perspective.
            
               If the FAP's self-configuration capability for URA
               is available and enabled, this parameter indicates
               the value selected by the FAP among the choices
               provided in {{param|URAList}}.
            
               If the self-configuration capability is not
               available or not enabled, then this parameter
               contains the first URA value in {{param|URAList}}.";
          }
          leaf RNCID {
            type uint32 {
              range "0..65535";
            }
            description
              "RNC-ID allocated to the FAP.  It uniquely identifies
               an RNC within a PLMN.
            
               Normally, RNC-ID consists of 12 bits (i.e.  a
               range of [0:4095]).  However, if the value is
               larger than 4095, then Extended RNC-ID (range of
               [4096:65535]) is used in RANAP.
            
               The RNC-ID and Extended RNC-ID are combined into a
               single parameter here as there is no explicit need
               to have them separated.
            
               {{bibref|3GPP-TS.25.413|Section 9.2.1.39}}";
          }
          leaf CellID {
            type uint32 {
              range "min..268435455";
            }
            description
              "Cell Identity.  {{bibref|3GPP-TS.25.401|Section
               6.1.5}}";
          }
          leaf TRatC {
            type uint32;
            description
              "Guard period in {{units}} before sending a
               \"RANAP:RESET ACKNOWLEDGE\" message towards the
               Femto GW.  {{bibref|3GPP-TS.25.413|Section 9.5}}";
          }
          leaf TRafC {
            type uint32;
            description
              "Maximum amount of time in {{units}} that the FAP
               SHOULD wait for receiving a \"RANAP:RESET
               ACKNOWLEDGE\" message from the Femto GW after
               sending a Reset to the Femto GW.
               {{bibref|3GPP-TS.25.413|Section 9.5}}";
          }
          leaf NRafC {
            type uint32 {
              range "1..max";
            }
            description
              "Maximum number for RESET procedure that can be
               repeated in FAP.  {{bibref|3GPP-TS.25.413|Section
               8.26.3.2}}";
          }
          leaf TigOR {
            type uint32;
            description
              "Amount of time in {{units}} used to determine when
               the additional level of traffic reduction in CN
               overload SHOULD take place.  While this timer is
               running all OVERLOAD messages or signalling
               pointing to congested information received by the
               FAP are ignored.  {{bibref|3GPP-TS.25.413|Section
               9.5}}";
          }
          leaf TinTR {
            type uint32;
            description
              "Amount of time in {{units}} used to determine when
               the CN overload can be considered cleared.  While
               this timer is running, the FAP is not allowed to
               increase traffic.  {{bibref|3GPP-TS.25.413|Section
               9.5}}";
          }
          leaf TDataFwd {
            type uint32;
            description
              "Maximum amount of time in {{units}} for Data
               Forwarding at FAP.  Timer is started when a
               \"RANAP:SRNS Data Forward Command\" message (or a
               \"RANAP:Relocation Command\" message) is received.
               At timer expiry the \"SRNS Data Forwarding\"
               procedure is completed.
               {{bibref|3GPP-TS.25.413|Section 9.5}}";
          }
          leaf TRelocPrep {
            type uint32;
            description
              "Maximum amount of time in {{units}} for the
               Relocation Preparation procedure.  Timer is
               started when a \"RANAP:Relocation Required\"
               message is sent.  Timer is stopped when a
               \"RANAP:Relocation Command\" or a
               \"RANAP:Relocation Preparation Failure\" message
               is received.  {{bibref|3GPP-TS.25.413|Section
               9.5}}";
          }
          leaf TRelocOverall {
            type uint32;
            description
              "Maximum amount of time in {{units}} for protection of
               the overall Relocation procedure.  Timer is
               started when a \"RANAP:Relocation Command\"
               message is received.  Timer is stopped when a
               \"RANAP:Iu Release Command\" is received or the
               relocation procedure is cancelled.
               {{bibref|3GPP-TS.25.413|Section 9.5}}";
          }
          leaf HNBIDRealm {
            type string {
              length "0..182";
            }
            description
              "The \"realm\" portion of the HNB-ID where HNB-ID is
               defined in {{bibref|3GPP-TS.25.469}} and is shown
               as follows:
            
               0<IMSI>@<realm>
            
               Or
            
               1<OUI>-<SerialNumber>@<realm>
            
               The other identifiers before \"@\" are device
               dependent values.  Both <OUI> and <SerialNumber>
               are defined in {{bibref|TR-069a2|Table 36}}.
            
               <IMSI> is obtained from the USIM if it is equipped
               in the FAP.";
          }
          leaf HSFlag {
            type boolean;
            description
              "Enables/disables the HSDPA function in the FAP.
            
               If {{true}} HSDPA is enabled (this is equivalent
               to a \"1\" in {{bibref|3GPP-TS.32.642|Section
               6.3.9}})
            
               If {{false}} HSDPA is disabled (this is equivalent
               to a \"0\" in {{bibref|3GPP-TS.32.642|Section
               6.3.9}})";
          }
          leaf HSEnable {
            type boolean;
            description
              "Enables or disables HSDPA in the cell.
            
               If {{true}} HSDPA is enabled (this is equivalent
               to a \"1\" in {{bibref|3GPP-TS.32.642|Section
               6.3.9}})
            
               If {{false}} HSDPA is not enabled (this is
               equivalent to a \"0\" in
               {{bibref|3GPP-TS.32.642|Section 6.3.9}})
            
               If {{param|HSFlag}} is {{false}} then this value
               MUST be {{false}}.";
          }
          leaf NumOfHSPDSCHs {
            type uint32 {
              range "0..15";
            }
            description
              "The number of codes at the defined spreading factor
               (SF=16), within the complete code tree.
               {{bibref|3GPP-TS.32.642|Section 6.3.9}}";
          }
          leaf NumOfHSSCCHs {
            type uint32;
            description
              "The number of HS-SCCHs for one cell.
               {{bibref|3GPP-TS.32.642|Section 6.3.9}}";
          }

          container CSG {
            description
              "This object contains parameters relating to the
               Closed Subscriber Group (CSG).";
            leaf CSGIndicator {
              type boolean;
              config false;
              description
                "The CSG-indicator Information Element (IE) in the
                 Master Information Block reflects the access
                 mode of the CSG cell.  It is hence dependent on
                 the value of
                 {{param|.AccessMgmt.UMTS.AccessMode}}.
              
                 If {{true}} the CSG-indicator IE is present,
                 reflecting access to the CSG cell is closed.
              
                 If {{false}} the CSG-indicator IE is absent,
                 reflecting access to the CSG cell is not closed.
              
                 {{bibref|3GPP-TS.25.331|Section 10.2.48.8.1}}";
            }
            leaf UARFCNDLList {
              type uint32 {
                range "min..16383";
              }
              description
                "{{list}} Each item is a UTRA Absolute Radio
                 Frequency Channel Number (UARFCN) in the DL
                 direction dedicated to the CSG cells.
              
                 {{param}} is broadcast in SIB 11bis
                 {{bibref|3GPP-TS.25.331|Section 10.2.48.8.14a}}.
              
                 The corresponding UTRA Absolute Radio Frequency
                 Channel Number (UARFCN) in the UL direction is
                 derived based on the fixed offset applicable for
                 the frequency band.";
            }

            container CSGPSCSplitInfo {
              description
                "This object contains parameters relating to the
                 Primary Scrambling Code (PSC) split information
                 for the CSG.  Defined in SIB3/11bis
                 {{bibref|3GPP-TS.25.331|Section 10.3.2.8 and
                 10.3.2.9}}.";
              leaf StartPSCRange1Coefficient {
                type uint32 {
                  range "0..63";
                }
                description
                  "The value of this Information Element (IE)
                   multiplied by 8 specifies the start PSC value
                   of the first PSC range as specified in
                   {{bibref|3GPP-TS.25.331|Section 8.6.2.4}}.";
              }
              leaf NumberOfPSCs {
                type enumeration {
                  enum "5";
                  enum "10";
                  enum "15";
                  enum "20";
                  enum "30";
                  enum "40";
                  enum "50";
                  enum "64";
                  enum "80";
                  enum "120";
                  enum "160";
                  enum "256";
                  enum "alltherest";
                  enum "spare3";
                  enum "spare2";
                  enum "spare1";
                }
                description
                  "This Information Element (IE) specifies the
                   number of PSCs reserved for CSG cells in each
                   PSC range.";
              }
              leaf PSCRange2Offset {
                type uint32 {
                  range "0..63";
                }
                description
                  "If this Information Element (IE) is included, the
                   UE shall calculate the second PSC range as
                   specified in {{bibref|3GPP-TS.25.331|Section
                   8.6.2.4}}.
                
                   If this Information Element (IE) is not
                   included, the UE shall consider the second PSC
                   range to be not present.";
              }
            }
          }

          container CellSelection {
            description
              "This object contains parameters related to cell
               selection and reselection.";
            leaf QualityMeasureCPICH {
              type enumeration {
                enum "Ec/No";
                enum "RSCP";
              }
              description
                "Which mechanism to use when doing CPICH quality
                 measurements.  {{bibref|3GPP-TS.25.331|Section
                 10.3.7.47}}";
            }
            leaf QqualMin {
              type int32 {
                range "-24..0";
              }
              description
                "Minimum required quality measure, specified in
                 {{units}}.  {{bibref|3GPP-TS.25.331|Section
                 10.3.2.3 and Section 10.3.2.4}}
              
                 This value is only meaningful if
                 {{param|QualityMeasureCPICH}} has the value
                 {{enum|Ec/No|QualityMeasureCPICH}} and it MUST
                 otherwise be ignored.";
            }
            leaf QqualMinOffset {
              type uint32 {
                range "1..16";
              }
              default "1";
              description
                "Offset for {{param|QqualMin}} specified in
                 {{units}}.  {{bibref|3GPP-TS.25.331|Section
                 10.3.2.3}}
              
                 This value is only meaningful if
                 {{param|QualityMeasureCPICH}} has the value
                 {{enum|Ec/No|QualityMeasureCPICH}} and it MUST
                 otherwise be ignored.";
            }
            leaf QRxLevMin {
              type int32 {
                range "-115..-25";
              }
              description
                "Minimum required RX level in the cell, specified in
                 {{units}}.  {{bibref|3GPP-TS.25.331|Section
                 10.3.2.3}}
              
                 Only odd values are valid, use of an even value
                 MUST be rejected by the CPE.
              
                 This value is only meaningful if
                 {{param|QualityMeasureCPICH}} has the value
                 {{enum|RSCP|QualityMeasureCPICH}} and it MUST
                 otherwise be ignored.";
            }
            leaf DeltaQRxLevMin {
              type int32 {
                range "-4 | -2";
              }
              description
                "Delta for the minimum required RX level in the
                 cell, specified in {{units}}.
                 {{bibref|3GPP-TS.25.331|Section 10.3.2.3 and
                 Section 10.3.2.4}}
              
                 The actual value of {{param|QRxLevMin}} =
                 {{param|QRxLevMin}} + {{param}}
              
                 This value is only meaningful if
                 {{param|QualityMeasureCPICH}} has the value
                 {{enum|RSCP|QualityMeasureCPICH}} and it MUST
                 otherwise be ignored.";
            }
            leaf QRxLevMinOffset {
              type uint32 {
                range "2 | 4 | 6 | 8 | 10 | 12 | 14 | 16";
              }
              default "2";
              description
                "Offset for {{param|QRxLevMin}}, specified in
                 {{units}}.  {{bibref|3GPP-TS.25.331|Section
                 10.3.2.3}}
              
                 This value is only meaningful if
                 {{param|QualityMeasureCPICH}} has the value
                 {{enum|RSCP|QualityMeasureCPICH}} and it MUST
                 otherwise be ignored.";
            }
            leaf QHyst1s {
              type uint32 {
                range "0..40";
              }
              description
                "GSM and FDD Cell reselection hysteresis 1.
                 {{bibref|3GPP-TS.25.331|Section 10.3.2.3}}
              
                 Only even values are valid, use of an odd value
                 MUST be rejected by the CPE.";
            }
            leaf QHyst2s {
              type uint32 {
                range "0..40";
              }
              description
                "FDD Cell reselection hysteresis 2.
                 {{bibref|3GPP-TS.25.331|Section 10.3.2.3}}
              
                 Only even values are valid, use of an odd value
                 MUST be rejected by the CPE.
              
                 This value is only meaningful if
                 {{param|QualityMeasureCPICH}} has the value
                 {{enum|Ec/No|QualityMeasureCPICH}} and it MUST
                 otherwise be ignored.
              
                 By default when {{param|QHyst1s}} is set and
                 {{param}} is not, then the value for {{param}}
                 SHOULD match the value of {{param|QHyst1s}}.";
            }
            leaf TReselections {
              type uint32 {
                range "0..31";
              }
              description
                "A member of the set of parameters used for cell
                 reselection functionality.
              
                 A UE triggers the reselection of a new cell if
                 the cell reselection criteria are fulfilled
                 during the time interval in {{units}}.
              
                 Parameter defined in SIB3
                 {{bibref|3GPP-TS.25.331|Section 10.3.2.3}}.";
            }
            leaf SIntrasearch {
              type int32 {
                range "-32..20";
              }
              description
                "A member of the set of parameters used for cell
                 reselection functionality.
              
                 Defines the threshold for intra-frequency
                 measurements, and for the HCS measurement rules.
              
                 Only even values are valid, use of an odd value
                 MUST be rejected by the CPE.
              
                 Parameter defined in SIB3
                 {{bibref|3GPP-TS.25.331|Section 10.3.2.3}}.";
            }
            leaf SIntersearch {
              type int32 {
                range "-32..20";
              }
              description
                "A member of the set of parameters used for cell
                 reselection functionality.
              
                 Defines the threshold for inter-frequency
                 measurements, and for the HCS measurement rules.
              
                 Only even values are valid, use of an odd value
                 MUST be rejected by the CPE.
              
                 Parameter defined in SIB3
                 {{bibref|3GPP-TS.25.331|Section 10.3.2.3}}.";
            }
            leaf SSearchHCS {
              type int32 {
                range "-105..91";
              }
              description
                "A member of the set of parameters used for cell
                 reselection functionality.
              
                 Defines the threshold for intrafrequency and
                 interfrequency measurement rules in HCS.
              
                 Below this limit in the serving cell, the UE
                 initiates measurements of all intrafrequency and
                 interfrequency neighbouring cells of the serving
                 cell.
              
                 Only odd values are valid, use of an even value
                 MUST be rejected by the CPE.
              
                 Parameter defined in SIB3
                 {{bibref|3GPP-TS.25.331|Section 10.3.2.3}}.";
            }
            leaf SSearchRAT {
              type int32 {
                range "-32..20";
              }
              description
                "A member of the set of parameters used for cell
                 reselection functionality.
              
                 Defines the RAT (GSM) specific threshold for
                 inter-RAT measurement rules.
              
                 Only even values are valid, use of an odd value
                 MUST be rejected by the CPE.
              
                 Parameter defined in SIB3
                 {{bibref|3GPP-TS.25.331|Section 10.3.2.3}}.";
            }
            leaf SHCSRAT {
              type int32 {
                range "-105..91";
              }
              description
                "A member of the set of parameters used for cell
                 reselection functionality.
              
                 Defines the RAT (GSM) specific threshold for
                 inter-RAT measurement rules in HCS.
              
                 Only odd values are valid, use of an even value
                 MUST be rejected by the CPE.
              
                 Parameter defined in SIB3
                 {{bibref|3GPP-TS.25.331|Section 10.3.2.3}}.";
            }
            leaf SLimitSearchRAT {
              type int32 {
                range "-32..20";
              }
              description
                "A member of the set of parameters used for cell
                 reselection functionality.
              
                 Defines the threshold for skipping inter-RAT
                 measurement rules in HCS.  Above this RAT (GSM)
                 specific threshold in the serving UTRA cell, the
                 UE does not need to perform any inter-RAT
                 measurements.
              
                 Only even values are valid, use of an odd value
                 MUST be rejected by the CPE.
              
                 Parameter defined in SIB3
                 {{bibref|3GPP-TS.25.331|Section 10.3.2.3}}.";
            }
            leaf NonHCSTCRMax {
              type enumeration {
                enum "not used";
                enum "30";
                enum "60";
                enum "120";
                enum "180";
                enum "240";
              }
              description
                "A member of the set of parameters used for cell
                 reselection functionality.
              
                 Defines the duration in seconds for evaluating
                 the allowed amount of cell reselections.  If the
                 number of cell reselections during the time
                 period defined by {{param}} exceeds
                 {{param|NonHCSNCR}}, high mobility has been
                 detected.
              
                 Parameter defined in SIB3
                 {{bibref|3GPP-TS.25.331|Section 10.3.2.3}}.";
            }
            leaf NonHCSNCR {
              type uint32 {
                range "1..16";
              }
              description
                "A member of the set of parameters used for cell
                 reselection functionality.
              
                 Defines the maximum number of cell reselections.
                 If the number of cell reselections during the
                 {{param|NonHCSTCRMax}} time period exceeds the
                 value of {{param}}, high mobility has been
                 detected.
              
                 Parameter defined in SIB3
                 {{bibref|3GPP-TS.25.331|Section 10.3.2.3}}.";
            }
            leaf NonHCSTCRMaxHyst {
              type enumeration {
                enum "not used";
                enum "10";
                enum "20";
                enum "30";
                enum "40";
                enum "50";
                enum "60";
                enum "70";
              }
              description
                "A member of the set of parameters used for cell
                 reselection functionality.
              
                 Defines the cell reselection hysteresis for
                 reverting from UE high-mobility measurements.
                 The additional time period in seconds before UE
                 reverts to low-mobility measurements.  When the
                 number of cell reselections during the time
                 period defined by {{param|TCRMax}} no longer
                 exceeds {{param|NCR}}, UE continues measurements
                 during the time period defined by
                 {{param|TCRMaxHyst}}.
              
                 Parameter defined in SIB3
                 {{bibref|3GPP-TS.25.331|Section 10.3.2.3}}.";
            }
            leaf QHCS {
              type uint32 {
                range "0..99";
              }
              default "0";
              description
                "A member of the set of parameters used for cell
                 reselection functionality.
              
                 Defines the quality threshold levels for
                 applying prioritised hierarchical cell
                 reselection.
              
                 {{bibref|3GPP-TS.25.331|Section 10.3.7.12 and
                 Section 10.3.7.54a}}";
            }
            leaf UseOfHCS {
              type boolean;
              description
                "A member of the set of parameters used for cell
                 reselection functionality.
              
                 Indicate whether HCS is used in this cell or
                 not.
              
                 {{bibref|3GPP-TS.25.331|Section 10.3.7.47}}";
            }
            leaf HCSPrio {
              type uint32 {
                range "0..7";
              }
              default "0";
              description
                "A member of the set of parameters used for cell
                 reselection functionality.
              
                 Defines the HCS priority of this cell.
              
                 {{bibref|3GPP-TS.25.331|Section 10.3.7.12}}";
            }
            leaf TCRMax {
              type enumeration {
                enum "not used";
                enum "30";
                enum "60";
                enum "120";
                enum "180";
                enum "240";
              }
              description
                "A member of the set of parameters used for cell
                 reselection functionality.
              
                 Defines the duration in seconds for evaluating
                 the allowed amount of cell reselections.  If the
                 number of cell reselections during the time
                 period defined by {{param}} exceeds
                 {{param|NCR}}, high mobility has been detected.
              
                 Parameter defined in SIB3
                 {{bibref|3GPP-TS.25.331|Section 10.3.7.12}}.";
            }
            leaf NCR {
              type uint32 {
                range "1..16";
              }
              description
                "A member of the set of parameters used for cell
                 reselection functionality.
              
                 Defines the maximum number of cell reselections.
                 If the number of cell reselections during the
                 {{param|TCRMax}} time period exceeds the value
                 of {{param}}, high mobility has been detected.
              
                 Parameter defined in SIB3
                 {{bibref|3GPP-TS.25.331|Section 10.3.7.12}}.";
            }
            leaf TCRMaxHyst {
              type enumeration {
                enum "not used";
                enum "10";
                enum "20";
                enum "30";
                enum "40";
                enum "50";
                enum "60";
                enum "70";
              }
              description
                "A member of the set of parameters used for cell
                 reselection functionality.
              
                 Defines the cell reselection hysteresis for
                 reverting from UE high-mobility measurements.
                 The additional time period in seconds before UE
                 reverts to low-mobility measurements.  When the
                 number of cell reselections during the time
                 period defined by {{param|TCRMax}} no longer
                 exceeds {{param|NCR}}, UE continues measurements
                 during the time period defined by {{param}}.
              
                 Parameter defined in SIB3
                 {{bibref|3GPP-TS.25.331|Section 10.3.7.12}}.";
            }
            leaf UETxPwrMaxRACH {
              type int32 {
                range "-50..33";
              }
              description
                "A member of the set of parameters used for cell
                 reselection functionality.
              
                 Defines the maximum transmit power level,
                 specified in {{units}}, that an UE MAY use when
                 accessing the cell on RACH.  Used to calculate
                 Pcompensation, which is: max(UE_TXPWR_MAX_RACH -
                 P_MAX, 0), where UE_TXPWR_MAX_RACH is {{param}}
                 and P_MAX is the max transmit power for a UE.
              
                 {{bibref|3GPP-TS.25.331|Section 10.3.2.3}}
                 {{bibref|3GPP-TS.25.304|Section 5.2.3}}";
            }
          }

          container RRCTimers {
            description
              "This object contains parameters related to
               miscellaneous RRC timers and constants.";
            leaf T300 {
              type uint32 {
                range "100..8000";
              }
              default "1000";
              description
                "Timer measured in {{units}}.
              
                 Only the following values are considered valid:
              
                 :100, 200, 400, 600, 800, 1000, 1200, 1400,
                 1600, 1800, 2000, 3000, 4000, 6000, and 8000
              
                 Any value other than those and the CPE MUST
                 reject the request.
              
                 Defined in SIB1 {{bibref|3GPP-TS.25.331|Section
                 13.1 and Section 10.3.3.44}}.";
            }
            leaf T301 {
              type uint32 {
                range "100..8000";
              }
              default "2000";
              description
                "Timer measured in {{units}}.
              
                 Only the following values are considered valid:
              
                 :100, 200, 400, 600, 800, 1000, 1200, 1400,
                 1600, 1800, 2000, 3000, 4000, 6000, and 8000
              
                 Any value other than those and the CPE MUST
                 reject the request.
              
                 Defined in SIB1 {{bibref|3GPP-TS.25.331|Section
                 13.1 and section 10.3.3.44}}.";
            }
            leaf T302 {
              type uint32 {
                range "100..8000";
              }
              default "4000";
              description
                "Timer measured in {{units}}.
              
                 Only the following values are considered valid:
              
                 :100, 200, 400, 600, 800, 1000, 1200, 1400,
                 1600, 1800, 2000, 3000, 4000, 6000, and 8000
              
                 Any value other than those and the CPE MUST
                 reject the request.
              
                 Defined in SIB1 {{bibref|3GPP-TS.25.331|Section
                 13.1 and Section 10.3.3.44}}.";
            }
            leaf T304 {
              type uint32 {
                range "100 | 200 | 400 | 1000 | 2000";
              }
              default "2000";
              description
                "Timer measured in {{units}}.  Defined in SIB1
                 {{bibref|3GPP-TS.25.331|Section 13.1 and Section
                 10.3.3.44}}.";
            }
            leaf T305 {
              type int32 {
                range "-1 | 5 | 10 | 30 | 60 | 120 | 360 | 720";
              }
              default "30";
              description
                "Timer measured in {{units}}.
              
                 -1 indicates an unbounded timer in which there
                 is no update.
              
                 Defined in SIB1 {{bibref|3GPP-TS.25.331|Section
                 13.1 and Section 10.3.3.44}}.";
            }
            leaf T307 {
              type uint32 {
                range "5 | 10 | 15 | 20 | 30 | 40 | 50";
              }
              default "30";
              description
                "Timer measured in {{units}}.  Defined in SIB1
                 {{bibref|3GPP-TS.25.331|Section 13.1 and Section
                 10.3.3.44}}.";
            }
            leaf T308 {
              type uint32 {
                range "40 | 80 | 160 | 320";
              }
              default "160";
              description
                "Timer measured in {{units}}.  Defined in SIB1
                 {{bibref|3GPP-TS.25.331|Section 13.1 and Section
                 10.3.3.44}}.";
            }
            leaf T309 {
              type uint32 {
                range "1..8";
              }
              default "5";
              description
                "Timer measured in {{units}}.  Defined in SIB1
                 {{bibref|3GPP-TS.25.331|Section 13.1 and Section
                 10.3.3.44}}.";
            }
            leaf T310 {
              type uint32 {
                range "40 | 80 | 120 | 160 | 200 | 240 | 280 | 320";
              }
              default "160";
              description
                "Timer measured in {{units}}.  Defined in SIB1
                 {{bibref|3GPP-TS.25.331|Section 13.1 and Section
                 10.3.3.44}}.";
            }
            leaf T311 {
              type uint32 {
                range "250 | 500 | 750 | 1000 | 1250 | 1500 | 1750 | 2000";
              }
              default "2000";
              description
                "Timer measured in {{units}}.  Defined in SIB1
                 {{bibref|3GPP-TS.25.331|Section 13.1 and Section
                 10.3.3.43}}.";
            }
            leaf T312 {
              type uint32 {
                range "0..15";
              }
              default "1";
              description
                "Timer measured in {{units}}.  Defined in SIB1
                 {{bibref|3GPP-TS.25.331|Section 13.1 and Section
                 10.3.3.44}}.";
            }
            leaf T313 {
              type uint32 {
                range "0..15";
              }
              default "3";
              description
                "Timer measured in {{units}}.  Defined in SIB1
                 {{bibref|3GPP-TS.25.331|Section 13.1 and Section
                 10.3.3.43}}.";
            }
            leaf T314 {
              type uint32 {
                range "0 | 2 | 4 | 6 | 8 | 12 | 16 | 20";
              }
              default "12";
              description
                "Timer measured in {{units}}.  Defined in SIB1
                 {{bibref|3GPP-TS.25.331|Section 13.1 and Section
                 10.3.3.43}}.";
            }
            leaf T315 {
              type uint32 {
                range "0 | 10 | 30 | 60 | 180 | 600 | 1200 | 1800";
              }
              default "180";
              description
                "Timer measured in {{units}}.  Defined in SIB1
                 {{bibref|3GPP-TS.25.331|Section 13.1 and Section
                 10.3.3.43}}.";
            }
            leaf T316 {
              type int32 {
                range "-1 | 0 | 10 | 20 | 30 | 40 | 50";
              }
              default "30";
              description
                "Timer measured in {{units}}.  Defined in SIB1
                 {{bibref|3GPP-TS.25.331|Section 13.1 and Section
                 10.3.3.43}}.
              
                 -1 indicates an unbounded timer in which there
                 is no update.";
            }
            leaf T317 {
              type uint32 {
                range "0 | 10 | 30 | 60 | 180 | 600 | 1200 | 1800";
              }
              description
                "Timer measured in {{units}}.  Defined in SIB1
                 {{bibref|3GPP-TS.25.331|Section 13.1 and Section
                 10.3.3.43}}.";
            }
            leaf N300 {
              type uint32 {
                range "0..7";
              }
              default "3";
              description
                "Counter.  Defined in SIB1
                 {{bibref|3GPP-TS.25.331|Section 13.1 and Section
                 10.3.3.44}}.";
            }
            leaf N301 {
              type uint32 {
                range "0..7";
              }
              default "2";
              description
                "Counter.  Defined in SIB1
                 {{bibref|3GPP-TS.25.331|Section 13.1 and Section
                 10.3.3.43}}.";
            }
            leaf N302 {
              type uint32 {
                range "0..7";
              }
              default "3";
              description
                "Counter.  Defined in SIB1
                 {{bibref|3GPP-TS.25.331|Section 13.1 and Section
                 10.3.3.43}}.";
            }
            leaf N304 {
              type uint32 {
                range "0..7";
              }
              default "2";
              description
                "Counter.  Defined in SIB1
                 {{bibref|3GPP-TS.25.331|Section 13.1 and Section
                 10.3.3.43}}.";
            }
            leaf N310 {
              type uint32 {
                range "0..7";
              }
              default "4";
              description
                "Counter.  Defined in SIB1
                 {{bibref|3GPP-TS.25.331|Section 13.1 and Section
                 10.3.3.43}}.";
            }
            leaf N312 {
              type uint32 {
                range "1..1000";
              }
              default "1";
              description
                "Counter.
              
                 Only the following values are considered valid:
              
                 1, 2, 4, 10, 20, 50, 100, 200, 400, 600, 800,
                 and 1000.
              
                 Any value other than those and the CPE MUST
                 reject the request.
              
                 Defined in SIB1 {{bibref|3GPP-TS.25.331|Section
                 13.1 and Section 10.3.3.44}}.";
            }
            leaf N313 {
              type uint32 {
                range "1 | 2 | 4 | 10 | 20 | 50 | 100 | 200";
              }
              default "20";
              description
                "Counter.  Defined in SIB1
                 {{bibref|3GPP-TS.25.331|Section 13.1 and Section
                 10.3.3.43}}.";
            }
            leaf N315 {
              type uint32 {
                range "1..1000";
              }
              default "1";
              description
                "Counter.
              
                 Only the following values are considered valid:
              
                 :1, 2, 4, 10, 20, 50, 100, 200, 400, 600, 800,
                 and 1000.
              
                 Any value other than those and the CPE MUST
                 reject the request.
              
                 Defined in SIB1 {{bibref|3GPP-TS.25.331|Section
                 13.1 and Section 10.3.3.43}}.";
            }
            leaf WaitTime {
              type uint32 {
                range "0..15";
              }
              description
                "Time period the UE has to wait before repeating the
                 rejected procedure.  This is an IE used when
                 sending RRC connection reject, redirecting the
                 requesting UE to another frequency.
              
                 0 indicates that repetition is not allowed.
              
                 {{bibref|3GPP-TS.25.331|Section 10.3.3.50}}.";
            }
          }

          container DRX {
            description
              "This object contains parameters related to DRX
               parameters.";
            leaf DRXCycleLengthCoefficientCS {
              type uint32 {
                range "6..9";
              }
              description
                "Defines the DRX cycle length coefficient for CS
                 domain to optimize paging in idle mode.  Defined
                 in SIB1 {{bibref|3GPP-TS.25.331|Section
                 10.3.3.6}}.
              
                 {{param}} refers to 'k' in the formula as
                 specified in {{bibref|3GPP-TS.25.304}},
                 Discontinuous reception.  Used by the CN CS
                 domain to count paging occasions for
                 discontinuous reception in Idle Mode.
              
                 The duration of the DRX cycle is 2 <power> k
                 frames, where 'k' is the used DRX cycle length
                 coefficient for CN.";
            }
            leaf DRXCycleLengthCoefficientPS {
              type uint32 {
                range "6..9";
              }
              description
                "Defines the DRX cycle length coefficient for PS
                 domain to optimize paging in idle mode.  Defined
                 in SIB1 {{bibref|3GPP-TS.25.331|Section
                 10.3.3.6}}.
              
                 {{param}} refers to 'k' in the formula as
                 specified in {{bibref|3GPP-TS.25.304}},
                 Discontinuous reception.  Used by the CN PS
                 domain to count paging occasions for
                 discontinuous reception in Idle Mode.
              
                 The duration of the DRX cycle is 2 <power> k
                 frames, where 'k' is the used DRX cycle length
                 coefficient for CN.";
            }
            leaf UTRANDRXCycleLengthCoefficient {
              type uint32 {
                range "3..9";
              }
              description
                "Defines the DRX cycle length used by UTRAN to count
                 paging occasions for discontinuous reception in
                 Connected Mode.
              
                 The duration of the DRX cycle is 2 <power> k
                 frames, where 'k' is the used DRX cycle length
                 coefficient for UTRAN.
              
                 {{param}} SHOULD be used by the UTRAN/FAP for
                 UEs in Cell_PCH/Cell_FACH state.
              
                 {{bibref|3GPP-TS.25.331|Section 10.3.3.49}}";
            }
          }

          container PowerControl {
            description
              "This object contains parameters related to power
               control and RACH.";
            leaf ConstantValue {
              type int32 {
                range "-35..-10";
              }
              description
                "Used by the UE to calculate the initial output
                 power, specified in {{units}}, on PRACH
                 according to the open loop power control
                 procedure.
              
                 Parameter in SIB5.
              
                 {{bibref|3GPP-TS.25.331|Section 10.3.6.11}}";
            }
            leaf PowerRampStepUp {
              type uint32 {
                range "1..8";
              }
              description
                "Used for the Uplink Common Channel.
              
                 Defines the Power ramp setup, specified in
                 {{units}}, on PRACH preamble when no acquisition
                 indicator (AI) is detected by the UE.
              
                 Parameter in SIB5.
              
                 {{bibref|3GPP-TS.25.331|Section 10.3.6.54}}";
            }
            leaf PreambleRetransMax {
              type uint32 {
                range "1..64";
              }
              description
                "Used for the Uplink Common Channel.
              
                 Defines the maximum number of preambles allowed
                 in one preamble ramping cycle.
              
                 PRACH Preamble Retrans Max is part of \"PRACH
                 power offset\" which is part of \"PRACH system
                 information list\".
              
                 Parameter in SIB5.
              
                 {{bibref|3GPP-TS.25.331|Section 10.3.6.54}}";
            }
            leaf PersistenceScaleFactor {
              type uint32 {
                range "2..9";
              }
              description
                "Persistence Scaling Factor for overload control.
              
                 Parameter in SIB5.
              
                 The value is the scaling factor multiplied by
                 10, e.g.  2 is a scaling factor of 0.2";
            }
            leaf MMax {
              type uint32 {
                range "1..32";
              }
              description
                "Maximum number of RACH preamble cycles.
              
                 Defines how many times the PRACH preamble
                 ramping procedure can be repeated before UE MAC
                 reports a failure on RACH transmission to higher
                 layers.  Maximum number of RACH preamble cycles
                 is part of \"RACH transmission parameters\"
                 which is part of \"PRACH system information
                 list\" which is part of SIB5.
              
                 {{bibref|3GPP-TS.25.331|Section 10.3.6.67}}";
            }
            leaf NB01Min {
              type uint32 {
                range "0..50";
              }
              description
                "RACH random back-off lower bound.
              
                 {{param}} is the lower bound of the waiting time
                 in 10 millisecond increments (i.e.  1
                 corresponds to 10 ms and 50 corresponds to 500
                 ms).
              
                 {{param}} is part of \"RACH transmission
                 parameters\" which is part of \"PRACH system
                 information list\" which is part of SIB5.
              
                 {{bibref|3GPP-TS.25.331|Section 10.3.6.67}}";
            }
            leaf NB01Max {
              type uint32 {
                range "0..50";
              }
              description
                "RACH random back-off upper bound.
              
                 {{param}} is the Upper bound of the waiting time
                 in 10 millisecond increments (i.e.  1
                 corresponds to 10 ms and 50 corresponds to 500
                 ms).
              
                 {{param}} is part of \"RACH transmission
                 parameters\" which is part of \"PRACH system
                 information list\" which is part of SIB5.
              
                 {{bibref|3GPP-TS.25.331|Section 10.3.6.67}}";
            }
          }

          container CellRestriction {
            description
              "This object contains parameters related to cell
               access restriction.";
            leaf CellBarred {
              type boolean;
              description
                "Indicates whether the FAP is barred from service or
                 not.
              
                 {{bibref|3GPP-TS.25.331|Section 10.3.2}}";
            }
            leaf IntraFreqCellReselectionIndicator {
              type boolean;
              description
                "When {{param|CellBarred}} is {{true}}, this
                 indicates whether the intra-frequency cell
                 re-selection is allowed or not.
              
                 {{param}} has no meaning if {{param|CellBarred}}
                 is {{false}} and MUST be ignored in such cases.
              
                 {{true}} means that intra-frequency cell
                 re-selection is allowed.
              
                 {{false}} means that intra-frequency cell
                 re-selection is not allowed.
              
                 {{bibref|3GPP-TS.25.331|Section 10.3.2}}";
            }
            leaf TBarred {
              type uint32 {
                range "10 | 20 | 40 | 80 | 160 | 320 | 640 | 1280";
              }
              description
                "The time period in {{units}} during which the UE is
                 barred from accessing the FAP.
              
                 {{bibref|3GPP-TS.25.331|Section 10.3.2}}";
            }
            leaf AccessClassBarredListCS {
              type uint32 {
                range "0..15";
              }
              description
                "{{list}} Each entry is an Access Class that is
                 barred from CS service.
              
                 The order of the list has no significance.
              
                 {{bibref|3GPP-TS.25.331|Section 10.3.2}}";
            }
            leaf AccessClassBarredListPS {
              type uint32 {
                range "0..15";
              }
              description
                "{{list}} Each entry is an Access Class that is
                 barred from PS service.
              
                 The order of the list has no significance.
              
                 {{bibref|3GPP-TS.25.331|Section 10.3.2}}";
            }
            leaf CellReservedForOperatorUse {
              type boolean;
              description
                "Indicates whether the FAP is reserved for operator
                 use or not.
              
                 {{bibref|3GPP-TS.25.331|Section 10.3.2}}";
            }
          }

          container IntraFreqMeas {
            description
              "This object contains parameters relating to the
               intra-freq HO control parameters.";
            leaf MeasurementQuantity {
              type enumeration {
                enum "CPICH Ec/No";
                enum "CPICH RSCP";
                enum "Pathloss";
              }
              description
                "Defines the measurement quantity for intra-freq HO
                 measurement when the UE is in Cell-DCH state.
              
                 Enumeration of:
              
                 {{enum}}
              
                 {{bibref|3GPP-TS.25.331|Section 10.3.7.38}}";
            }
            leaf FilterCoefficient {
              type uint32 {
                range "0..9 | 11 | 13 | 15 | 17 | 19";
              }
              description
                "Defines the equivalent time constant of the low
                 pass filter applied to the CPICH quality
                 measurements, or {{enum|CPICH
                 Ec/No|MeasurementQuantity}}.
              
                 {{bibref|3GPP-TS.25.331|Section 8.6.7.2 and
                 Section 10.3.7.9}}";
            }
            leaf IntraFrequencyEventIdentity {
              type string;
              description
                "{{list}} Each entry is an Event ID from the list
                 of: 1a, 1b, 1c, 1d, 1e, 1f, 1g, 1h, 1i
              
                 Defines the identity of the event used to
                 trigger UE reporting (in case of event-triggered
                 reporting).
              
                 {{bibref|3GPP-TS.25.331|Section 10.3.7.34}}
              
                 Since the FAP can determine this on its own, it
                 might not be necessary to configure it.";
            }
            leaf TriggeringCondition2Event1a {
              type enumeration {
                enum "Active";
                enum "Monitored";
                enum "Active and Monitored";
                enum "Detected";
                enum "Detected and Monitored";
              }
              description
                "{{list}} Indicates which cells can trigger Event
                 1a.  {{enum}}
              
                 {{bibref|3GPP-TS.25.331|Section 14.1.2 and
                 Section 10.3.7.39}}";
            }
            leaf TriggeringCondition1Event1b {
              type enumeration {
                enum "Active";
                enum "Monitored";
                enum "Active and Monitored";
              }
              description
                "{{list}} Indicates which cells can trigger Event
                 1b.  {{enum}}
              
                 {{bibref|3GPP-TS.25.331|Section 14.1.2 and
                 Section 10.3.7.39}}";
            }
            leaf TriggeringCondition2Event1e {
              type enumeration {
                enum "Active";
                enum "Monitored";
                enum "Active and Monitored";
                enum "Detected";
                enum "Detected and Monitored";
              }
              description
                "{{list}} Indicates which cells can trigger Event
                 1e.  {{enum}}
              
                 {{bibref|3GPP-TS.25.331|Section 14.1.2 and
                 Section 10.3.7.39}}";
            }
            leaf TriggeringCondition1Event1f {
              type enumeration {
                enum "Active";
                enum "Monitored";
                enum "Active and Monitored";
              }
              description
                "{{list}} Indicates which cells can trigger Event
                 1f.  {{enum}}
              
                 {{bibref|3GPP-TS.25.331|Section 14.1.2 and
                 Section 10.3.7.39}}";
            }
            leaf ReportingRangeEvent1a {
              type uint32 {
                range "0..29";
              }
              description
                "Defines a constant in the inequality criterion that
                 needs to be satisfied for an Event 1a to occur.
              
                 Actual values of the range are 0.0 to 14.5
                 {{units}} in steps of 0.5 {{units}}.  The value
                 of {{param}} divided by 2 yields the actual
                 value of the range.
              
                 {{bibref|3GPP-TS.25.331|Section 14.1.2 and
                 Section 10.3.7.39}}";
            }
            leaf ReportingRangeEvent1b {
              type uint32 {
                range "0..29";
              }
              description
                "Defines a constant in the inequality criterion that
                 needs to be satisfied for an Event 1b to occur.
              
                 Actual values of the range are 0.0 to 14.5
                 {{units}} in steps of 0.5 {{units}}.  The value
                 of {{param}} divided by 2 yields the actual
                 value of the range.
              
                 {{bibref|3GPP-TS.25.331|Section 14.1.2 and
                 Section 10.3.7.39}}";
            }
            leaf WeightingFactorEvent1a {
              type uint32 {
                range "0..20";
              }
              description
                "Defines the weighting factor for intra-freq HO
                 measurement when the UE is in Cell-DCH state.
              
                 Actual values of the weighting factor are 0.0 to
                 2.0 in steps of 0.1.  The value of {{param}}
                 divided by 10 yields the actual value of the
                 weighting factor.
              
                 {{bibref|3GPP-TS.25.331|Section 10.3.7.39}}";
            }
            leaf WeightingFactorEvent1b {
              type uint32 {
                range "0..20";
              }
              description
                "Defines the weighting factor for intra-freq HO
                 measurement when the UE is in Cell-DCH state.
              
                 Actual values of the weighting factor are 0.0 to
                 2.0 in steps of 0.1.  The value of {{param}}
                 divided by 10 yields the actual value of the
                 weighting factor.
              
                 {{bibref|3GPP-TS.25.331|Section 10.3.7.39}}";
            }
            leaf ReportDeactivationThresholdEvent1a {
              type uint32 {
                range "0..7";
              }
              description
                "Defines the maximum number of cells allowed in the
                 \"active cell set\" for Event 1a to occur.
              
                 {{bibref|3GPP-TS.25.331|Section 14.1.2 and
                 Section 10.3.7.39}}";
            }
            leaf ReportingAmountEvent1a {
              type int32 {
                range "-1 | 1..2 | 4 | 8 | 16 | 32 | 64";
              }
              description
                "Defines the maximum number of MEASUREMENT REPORT
                 messages sent by the UE in case of periodic
                 reporting triggered by an Event 1a
              
                 The value -1 is used to represent an unbounded
                 maximum.
              
                 {{bibref|3GPP-TS.25.331|Section 14.1.2 and
                 Section 10.3.7.39}}";
            }
            leaf ReportingAmountEvent1c {
              type int32 {
                range "-1 | 1..2 | 4 | 8 | 16 | 32 | 64";
              }
              description
                "Defines the maximum number of MEASUREMENT REPORT
                 messages sent by the UE in case of periodic
                 reporting triggered by an Event 1c
              
                 The value -1 is used to represent an unbounded
                 maximum.
              
                 {{bibref|3GPP-TS.25.331|Section 14.1.2 and
                 Section 10.3.7.39}}";
            }
            leaf ReportingIntervalEvent1a {
              type uint32 {
                range "0 | 250 | 500 | 1000 | 2000 | 4000 | 8000 | 16000";
              }
              description
                "Defines the transmission period in {{units}} of
                 MEASUREMENT REPORT messages sent by the UE in
                 case of periodic reporting triggered by an Event
                 1a.
              
                 {{bibref|3GPP-TS.25.331|Section 14.1.2 and
                 Section 10.3.7.39}}";
            }
            leaf ReportingIntervalEvent1c {
              type uint32 {
                range "0 | 250 | 500 | 1000 | 2000 | 4000 | 8000 | 16000";
              }
              description
                "Defines the transmission period in {{units}} of
                 MEASUREMENT REPORT messages sent by the UE in
                 case of periodic reporting triggered by an Event
                 1c.
              
                 {{bibref|3GPP-TS.25.331|Section 14.1.2 and
                 Section 10.3.7.39}}";
            }
            leaf HysteresisEvent1a {
              type uint32 {
                range "0..15";
              }
              description
                "Defines the hysteresis for intra-freq HO
                 measurement when the UE is in Cell-DCH state.
              
                 Actual values of the range are 0.0 to 7.5 in
                 steps of 0.5.  The value of {{param}} divided by
                 2 yields the actual value of the hysteresis.
              
                 {{bibref|3GPP-TS.25.331|Section 10.3.7.39 and
                 Section 14.1.2}}";
            }
            leaf HysteresisEvent1b {
              type uint32 {
                range "0..15";
              }
              description
                "Defines the hysteresis for intra-freq HO
                 measurement when the UE is in Cell-DCH state.
              
                 Actual values of the range are 0.0 to 7.5 in
                 steps of 0.5.  The value of {{param}} divided by
                 2 yields the actual value of the hysteresis.
              
                 {{bibref|3GPP-TS.25.331|Section 10.3.7.39 and
                 Section 14.1.2}}";
            }
            leaf HysteresisEvent1c {
              type uint32 {
                range "0..15";
              }
              description
                "Defines the hysteresis for intra-freq HO
                 measurement when the UE is in Cell-DCH state.
              
                 Actual values of the range are 0.0 to 7.5 in
                 steps of 0.5.  The value of {{param}} divided by
                 2 yields the actual value of the hysteresis.
              
                 {{bibref|3GPP-TS.25.331|Section 10.3.7.39 and
                 Section 14.1.2}}";
            }
            leaf HysteresisEvent1d {
              type uint32 {
                range "0..15";
              }
              description
                "Defines the hysteresis for intra-freq HO
                 measurement when the UE is in Cell-DCH state.
              
                 Actual values of the range are 0.0 to 7.5 in
                 steps of 0.5.  The value of {{param}} divided by
                 2 yields the actual value of the hysteresis.
              
                 {{bibref|3GPP-TS.25.331|Section 10.3.7.39 and
                 Section 14.1.2}}";
            }
            leaf HysteresisEvent1e {
              type uint32 {
                range "0..15";
              }
              description
                "Defines the hysteresis for intra-freq HO
                 measurement when the UE is in Cell-DCH state.
              
                 Actual values of the range are 0.0 to 7.5 in
                 steps of 0.5.  The value of {{param}} divided by
                 2 yields the actual value of the hysteresis.
              
                 {{bibref|3GPP-TS.25.331|Section 10.3.7.39 and
                 Section 14.1.2}}";
            }
            leaf HysteresisEvent1f {
              type uint32 {
                range "0..15";
              }
              description
                "Defines the hysteresis for intra-freq HO
                 measurement when the UE is in Cell-DCH state.
              
                 Actual values of the range are 0.0 to 7.5 in
                 steps of 0.5.  The value of {{param}} divided by
                 2 yields the actual value of the hysteresis.
              
                 {{bibref|3GPP-TS.25.331|Section 10.3.7.39 and
                 Section 14.1.2}}";
            }
            leaf TimeToTriggerEvent1a {
              type uint32 {
                range "0 | 10 | 20 | 40 | 60 | 80 | 100 | 120 | 160 | 200 | 240 | 320 | 640 | 1280 | 2560 | 5000";
              }
              description
                "Defines the time-to-trigger in {{units}} for
                 intra-freq HO measurement when the UE is in
                 Cell-DCH state.
              
                 Only the specified values are considered valid,
                 any value other than those and the CPE MUST
                 reject the request.
              
                 {{bibref|3GPP-TS.25.331|Section 10.3.7.39 and
                 Section 10.3.7.64}}";
            }
            leaf TimeToTriggerEvent1b {
              type uint32 {
                range "0 | 10 | 20 | 40 | 60 | 80 | 100 | 120 | 160 | 200 | 240 | 320 | 640 | 1280 | 2560 | 5000";
              }
              description
                "Defines the time-to-trigger in {{units}} for
                 intra-freq HO measurement when the UE is in
                 Cell-DCH state.
              
                 Only the specified values are considered valid,
                 any value other than those and the CPE MUST
                 reject the request.
              
                 {{bibref|3GPP-TS.25.331|Section 10.3.7.39 and
                 Section 10.3.7.64}}";
            }
            leaf TimeToTriggerEvent1c {
              type uint32 {
                range "0 | 10 | 20 | 40 | 60 | 80 | 100 | 120 | 160 | 200 | 240 | 320 | 640 | 1280 | 2560 | 5000";
              }
              description
                "Defines the time-to-trigger in {{units}} for
                 intra-freq HO measurement when the UE is in
                 Cell-DCH state.
              
                 Only the specified values are considered valid,
                 any value other than those and the CPE MUST
                 reject the request.
              
                 {{bibref|3GPP-TS.25.331|Section 10.3.7.39 and
                 Section 10.3.7.64}}";
            }
            leaf TimeToTriggerEvent1d {
              type uint32 {
                range "0 | 10 | 20 | 40 | 60 | 80 | 100 | 120 | 160 | 200 | 240 | 320 | 640 | 1280 | 2560 | 5000";
              }
              description
                "Defines the time-to-trigger in {{units}} for
                 intra-freq HO measurement when the UE is in
                 Cell-DCH state.
              
                 Only the specified values are considered valid,
                 any value other than those and the CPE MUST
                 reject the request.
              
                 {{bibref|3GPP-TS.25.331|Section 10.3.7.39 and
                 Section 10.3.7.64}}";
            }
            leaf TimeToTriggerEvent1e {
              type uint32 {
                range "0 | 10 | 20 | 40 | 60 | 80 | 100 | 120 | 160 | 200 | 240 | 320 | 640 | 1280 | 2560 | 5000";
              }
              description
                "Defines the time-to-trigger in {{units}} for
                 intra-freq HO measurement when the UE is in
                 Cell-DCH state.
              
                 Only the specified values are considered valid,
                 any value other than those and the CPE MUST
                 reject the request.
              
                 {{bibref|3GPP-TS.25.331|Section 10.3.7.39 and
                 Section 10.3.7.64}}";
            }
            leaf TimeToTriggerEvent1f {
              type uint32 {
                range "0 | 10 | 20 | 40 | 60 | 80 | 100 | 120 | 160 | 200 | 240 | 320 | 640 | 1280 | 2560 | 5000";
              }
              description
                "Defines the time-to-trigger in {{units}} for
                 intra-freq HO measurement when the UE is in
                 Cell-DCH state.
              
                 Only the specified values are considered valid,
                 any value other than those and the CPE MUST
                 reject the request.
              
                 {{bibref|3GPP-TS.25.331|Section 10.3.7.39 and
                 Section 10.3.7.64}}";
            }
            leaf ThresholdUsedFrequencyEvent1e {
              type int32 {
                range "-120..165";
              }
              description
                "Defines the reporting threshold for intra-freq HO
                 measurement when the UE is in Cell-DCH state.
                 This is the \"Threshold used frequency\" as
                 defined in {{bibref|3GPP-TS.25.331|Section
                 10.3.7.39}}.
              
                 Each valid value of
                 {{param|MeasurementQuantity}} has a different
                 valid range.
              
                 {{enum|CPICH RSCP|MeasurementQuantity}} has a
                 range of -120 dBm to -25 dBm
              
                 {{enum|CPICH Ec/No|MeasurementQuantity}} has a
                 range of -24 dB to 0 dB
              
                 {{enum|Pathloss|MeasurementQuantity}} has a
                 range of 30 dB to 165 dB";
            }
            leaf ThresholdUsedFrequencyEvent1f {
              type int32 {
                range "-120..165";
              }
              description
                "Defines the reporting threshold for intra-freq HO
                 measurement when the UE is in Cell-DCH state.
                 This is the \"Threshold used frequency\" as
                 defined in {{bibref|3GPP-TS.25.331|Section
                 10.3.7.39}}.
              
                 Each valid value of
                 {{param|MeasurementQuantity}} has a different
                 valid range.
              
                 {{enum|CPICH RSCP|MeasurementQuantity}} has a
                 range of -120 dBm to -25 dBm
              
                 {{enum|CPICH Ec/No|MeasurementQuantity}} has a
                 range of -24 dB to 0 dB
              
                 {{enum|Pathloss|MeasurementQuantity}} has a
                 range of 30 dB to 165 dB";
            }
            leaf ReplacementActivationThresholdEvent1c {
              type uint32 {
                range "0..7";
              }
              description
                "Defines the minimum number of cells allowed in the
                 \"active cell set\" for Event 1c to occur.
              
                 {{bibref|3GPP-TS.25.331|Section 14.1.2 and
                 Section 10.3.7.39}}";
            }

            list Instance {
              key "IntraFrequencyEventIdentity";
              description
                "Table containing parameters relating to a
                 particular instance of intra-freq events.";
              leaf Enable {
                type boolean;
                default "false";
                description
                  "Enables or disables this {{object}} entry.";
              }
              leaf IntraFrequencyEventIdentity {
                type enumeration {
                  enum "1a";
                  enum "1b";
                  enum "1c";
                  enum "1d";
                  enum "1e";
                  enum "1f";
                }
                config false;
                description
                  "Each entry is an Event ID from the list of:
                   {{enum}}
                
                   Defines the identity of the event used to
                   trigger UE reporting (in case of
                   event-triggered reporting).
                
                   {{bibref|3GPP-TS.25.331|Section 10.3.7.34}}
                
                   This attribute is readable, as it is highly
                   dependent on how the FAP makes use of the
                   event.";
              }
              leaf EventDescription {
                type string {
                  length "0..256";
                }
                config false;
                description
                  "A free-form description of the way the event
                   instance is meant to be used.
                
                   E.g.  \"hand-out to macro cells\", \"addition
                   of enterprise HNB cell to Active Set\".";
              }
              leaf MeasurementQuantity {
                type enumeration {
                  enum "CPICH Ec/No";
                  enum "CPICH RSCP";
                  enum "Pathloss";
                }
                description
                  "Defines the measurement quantity for intra-freq
                   HO measurement when the UE is in Cell-DCH
                   state.
                
                   Enumeration of:
                
                   {{enum}}
                
                   {{bibref|3GPP-TS.25.331|Section 10.3.7.38}}";
              }
              leaf FilterCoefficient {
                type uint32 {
                  range "0..9 | 11 | 13 | 15 | 17 | 19";
                }
                description
                  "Defines the equivalent time constant of the low
                   pass filter applied to the CPICH quality
                   measurements, or {{enum|CPICH
                   Ec/No|MeasurementQuantity}}.
                
                   {{bibref|3GPP-TS.25.331|Section 8.6.7.2 and
                   Section 10.3.7.9}}";
              }
              leaf TriggeringCondition {
                type enumeration {
                  enum "Active";
                  enum "Monitored";
                  enum "Active and Monitored";
                  enum "Detected";
                  enum "Detected and Monitored";
                }
                description
                  "{{list}} Indicates which cells can trigger the
                   event instance.  {{enum}}
                
                   {{bibref|3GPP-TS.25.331|Section 14.1.2 and
                   Section 10.3.7.39}}";
              }
              leaf ReportingRange {
                type uint32 {
                  range "0..29";
                }
                description
                  "Applicable to events 1a, 1b, otherwise not
                   needed.
                
                   Defines a constant in the inequality criterion
                   that needs to be satisfied for an Event 1b to
                   occur.
                
                   Actual values of the range are 0.0 to 14.5
                   {{units}} in steps of 0.5 {{units}}.  The
                   value of {{param}} divided by 2 yields the
                   actual value of the range.
                
                   {{bibref|3GPP-TS.25.331|Section 14.1.2 and
                   Section 10.3.7.39}}";
              }
              leaf WeightingFactor {
                type uint32 {
                  range "0..20";
                }
                description
                  "Applicable to events 1a, 1b, otherwise not
                   needed.
                
                   Defines the weighting factor for intra-freq HO
                   measurement when the UE is in Cell-DCH state.
                
                   Actual values of the weighting factor are 0.0
                   to 2.0 in steps of 0.1.  The value of
                   {{param}} divided by 10 yields the actual
                   value of the weighting factor.
                
                   {{bibref|3GPP-TS.25.331|Section 10.3.7.39}}";
              }
              leaf ReportDeactivationThreshold {
                type uint32 {
                  range "0..7";
                }
                description
                  "Applicable to events 1a, otherwise not needed.
                
                   Defines the maximum number of cells allowed in
                   the \"active cell set\" for Event 1a to occur.
                
                   {{bibref|3GPP-TS.25.331|Section 14.1.2 and
                   Section 10.3.7.39}}";
              }
              leaf ReportingAmount {
                type int32 {
                  range "-1 | 1..2 | 4 | 8 | 16 | 32 | 64";
                }
                description
                  "Applicable to events 1a, 1c, otherwise not
                   needed.
                
                   Defines the maximum number of MEASUREMENT
                   REPORT messages sent by the UE in case of
                   periodic reporting triggered by an Event 1a
                
                   The value -1 is used to represent an unbounded
                   maximum.
                
                   {{bibref|3GPP-TS.25.331|Section 14.1.2 and
                   Section 10.3.7.39}}";
              }
              leaf ReportingInterval {
                type uint32 {
                  range "0 | 250 | 500 | 1000 | 2000 | 4000 | 8000 | 16000";
                }
                description
                  "Applicable to events 1a, 1c, otherwise not
                   needed.
                
                   Defines the transmission period in {{units}}
                   of MEASUREMENT REPORT messages sent by the UE
                   in case of periodic reporting triggered by an
                   Event 1a.
                
                   {{bibref|3GPP-TS.25.331|Section 14.1.2 and
                   Section 10.3.7.39}}";
              }
              leaf Hysteresis {
                type uint32 {
                  range "0..15";
                }
                description
                  "Defines the hysteresis for intra-freq HO
                   measurement when the UE is in Cell-DCH state.
                
                   Actual values of the range are 0.0 to 7.5 in
                   steps of 0.5.  The value of {{param}} divided
                   by 2 yields the actual value of the
                   hysteresis.
                
                   {{bibref|3GPP-TS.25.331|Section 10.3.7.39 and
                   Section 14.1.2}}";
              }
              leaf TimeToTrigger {
                type uint32 {
                  range "0 | 10 | 20 | 40 | 60 | 80 | 100 | 120 | 160 | 200 | 240 | 320 | 640 | 1280 | 2560 | 5000";
                }
                description
                  "Defines the time-to-trigger in {{units}} for
                   intra-freq HO measurement when the UE is in
                   Cell-DCH state.
                
                   Only the specified values are considered
                   valid, any value other than those and the CPE
                   MUST reject the request.
                
                   {{bibref|3GPP-TS.25.331|Section 10.3.7.39 and
                   Section 10.3.7.64}}";
              }
              leaf ThresholdUsedFrequency {
                type int32 {
                  range "-120..165";
                }
                description
                  "Applicable to events 1e, 1f, otherwise not
                   needed.
                
                   Defines the reporting threshold for intra-freq
                   HO measurement when the UE is in Cell-DCH
                   state.  This is the \"Threshold used
                   frequency\" as defined in
                   {{bibref|3GPP-TS.25.331|Section 10.3.7.39}}.
                
                   Each valid value of
                   {{param|MeasurementQuantity}} has a different
                   valid range.
                
                   {{enum|CPICH RSCP|MeasurementQuantity}} has a
                   range of -120 dBm to -25 dBm
                
                   {{enum|CPICH Ec/No|MeasurementQuantity}} has a
                   range of -24 dB to 0 dB
                
                   {{enum|Pathloss|MeasurementQuantity}} has a
                   range of 30 dB to 165 dB";
              }
              leaf ReplacementActivationThreshold {
                type uint32 {
                  range "0..7";
                }
                description
                  "Applicable only to event 1c
                
                   Defines the minimum number of cells allowed in
                   the \"active cell set\" for Event 1c to occur.
                
                   {{bibref|3GPP-TS.25.331|Section 14.1.2 and
                   Section 10.3.7.39}}";
              }
            }
          }

          container InterFreqMeas {
            description
              "This object contains parameters relating to the
               inter-freq HO related control parameters.";
            leaf MeasurementQuantity {
              type enumeration {
                enum "CPICH Ec/No";
                enum "CPICH RSCP";
              }
              description
                "Defines the measurement quantity for inter-freq HO
                 measurement when the UE is in Cell-DCH state.
              
                 Enumeration of:
              
                 {{enum}}
              
                 {{bibref|3GPP-TS.25.331|Section 10.3.7.18}}";
            }
            leaf FilterCoefficient {
              type uint32 {
                range "0..9 | 11 | 13 | 15 | 17 | 19";
              }
              description
                "Defines the filter coefficient for inter-freq HO
                 measurement when the UE is in Cell-DCH state.
              
                 {{bibref|3GPP-TS.25.331|Section 10.3.7.9 and
                 Section 10.3.7.18}}";
            }
            leaf InterFrequencyEventIdentity {
              type string;
              description
                "{{list}} Each entry is an Event ID from the list
                 of: 2a, 2b, 2c, 2d, 2e,2f
              
                 Defines the identity of the event used to
                 trigger inter-frequency UE reporting (in case of
                 event-triggered reporting).
              
                 {{bibref|3GPP-TS.25.331|Section 10.3.7.14}}";
            }
            leaf WeightingFactorEvent2a {
              type uint32 {
                range "0..20";
              }
              description
                "Defines the weighting factor for inter-freq HO
                 measurement when the UE is in Cell-DCH state.
              
                 Actual values of the weighting factor are 0.0 to
                 2.0 in steps of 0.1.  The value of {{param}}
                 divided by 10 yields the actual value of the
                 weighting factor.
              
                 {{bibref|3GPP-TS.25.331|Section 10.3.7.19}}";
            }
            leaf WeightingFactorEvent2b {
              type uint32 {
                range "0..20";
              }
              description
                "Defines the weighting factor for inter-freq HO
                 measurement when the UE is in Cell-DCH state.
              
                 Actual values of the weighting factor are 0.0 to
                 2.0 in steps of 0.1.  The value of {{param}}
                 divided by 10 yields the actual value of the
                 weighting factor.
              
                 {{bibref|3GPP-TS.25.331|Section 10.3.7.19}}";
            }
            leaf WeightingFactorEvent2d {
              type uint32 {
                range "0..20";
              }
              description
                "Defines the weighting factor for inter-freq HO
                 measurement when the UE is in Cell-DCH state.
              
                 Actual values of the weighting factor are 0.0 to
                 2.0 in steps of 0.1.  The value of {{param}}
                 divided by 10 yields the actual value of the
                 weighting factor.
              
                 {{bibref|3GPP-TS.25.331|Section 10.3.7.19}}";
            }
            leaf WeightingFactorEvent2f {
              type uint32 {
                range "0..20";
              }
              description
                "Defines the weighting factor for inter-freq HO
                 measurement when the UE is in Cell-DCH state.
              
                 Actual values of the weighting factor are 0.0 to
                 2.0 in steps of 0.1.  The value of {{param}}
                 divided by 10 yields the actual value of the
                 weighting factor.
              
                 {{bibref|3GPP-TS.25.331|Section 10.3.7.19}}";
            }
            leaf HysteresisEvent2a {
              type uint32 {
                range "0..29";
              }
              description
                "Defines the hysteresis for inter-freq HO
                 measurement when the UE is in Cell-DCH state.
              
                 Actual values of the range are 0.0 to 14.5 in
                 steps of 0.5.  The value of {{param}} divided by
                 2 yields the actual value of the hysteresis.
              
                 {{bibref|3GPP-TS.25.331|Section 10.3.7.19}}";
            }
            leaf HysteresisEvent2b {
              type uint32 {
                range "0..29";
              }
              description
                "Defines the hysteresis for inter-freq HO
                 measurement when the UE is in Cell-DCH state.
              
                 Actual values of the range are 0.0 to 14.5 in
                 steps of 0.5.  The value of {{param}} divided by
                 2 yields the actual value of the hysteresis.
              
                 {{bibref|3GPP-TS.25.331|Section 10.3.7.19}}";
            }
            leaf HysteresisEvent2d {
              type uint32 {
                range "0..29";
              }
              description
                "Defines the hysteresis for inter-freq HO
                 measurement when the UE is in Cell-DCH state.
              
                 Actual values of the range are 0.0 to 14.5 in
                 steps of 0.5.  The value of {{param}} divided by
                 2 yields the actual value of the hysteresis.
              
                 {{bibref|3GPP-TS.25.331|Section 10.3.7.19}}";
            }
            leaf HysteresisEvent2f {
              type uint32 {
                range "0..29";
              }
              description
                "Defines the hysteresis for inter-freq HO
                 measurement when the UE is in Cell-DCH state.
              
                 Actual values of the range are 0.0 to 14.5 in
                 steps of 0.5.  The value of {{param}} divided by
                 2 yields the actual value of the hysteresis.
              
                 {{bibref|3GPP-TS.25.331|Section 10.3.7.19}}";
            }
            leaf TimeToTriggerEvent2a {
              type uint32 {
                range "0 | 10 | 20 | 40 | 60 | 80 | 100 | 120 | 160 | 200 | 240 | 320 | 640 | 1280 | 2560 | 5000";
              }
              description
                "Defines the time-to-trigger in {{units}} for
                 inter-freq HO measurement when the UE is in
                 Cell-DCH state.
              
                 Only the specified values are considered valid,
                 any value other than those and the CPE MUST
                 reject the request.
              
                 {{bibref|3GPP-TS.25.331|Section 10.3.7.19 and
                 Section 10.3.7.64}}";
            }
            leaf TimeToTriggerEvent2b {
              type uint32 {
                range "0 | 10 | 20 | 40 | 60 | 80 | 100 | 120 | 160 | 200 | 240 | 320 | 640 | 1280 | 2560 | 5000";
              }
              description
                "Defines the time-to-trigger in {{units}} for
                 inter-freq HO measurement when the UE is in
                 Cell-DCH state.
              
                 Only the specified values are considered valid,
                 any value other than those and the CPE MUST
                 reject the request.
              
                 {{bibref|3GPP-TS.25.331|Section 10.3.7.19 and
                 Section 10.3.7.64}}";
            }
            leaf TimeToTriggerEvent2d {
              type uint32 {
                range "0 | 10 | 20 | 40 | 60 | 80 | 100 | 120 | 160 | 200 | 240 | 320 | 640 | 1280 | 2560 | 5000";
              }
              description
                "Defines the time-to-trigger in {{units}} for
                 inter-freq HO measurement when the UE is in
                 Cell-DCH state.
              
                 Only the specified values are considered valid,
                 any value other than those and the CPE MUST
                 reject the request.
              
                 {{bibref|3GPP-TS.25.331|Section 10.3.7.19 and
                 Section 10.3.7.64}}";
            }
            leaf TimeToTriggerEvent2f {
              type uint32 {
                range "0 | 10 | 20 | 40 | 60 | 80 | 100 | 120 | 160 | 200 | 240 | 320 | 640 | 1280 | 2560 | 5000";
              }
              description
                "Defines the time-to-trigger in {{units}} for
                 inter-freq HO measurement when the UE is in
                 Cell-DCH state.
              
                 Only the specified values are considered valid,
                 any value other than those and the CPE MUST
                 reject the request.
              
                 {{bibref|3GPP-TS.25.331|Section 10.3.7.19 and
                 Section 10.3.7.64}}";
            }
            leaf ThresholdUsedFrequencyEvent2b {
              type int32 {
                range "-120..0";
              }
              description
                "Defines the reporting threshold for inter-freq HO
                 measurement when the UE is in Cell-DCH state.
                 This is the \"Threshold used frequency\" as
                 defined in {{bibref|3GPP-TS.25.331|Section
                 10.3.7.19}}.
              
                 Each valid value of
                 {{param|MeasurementQuantity}} has a different
                 valid range.
              
                 {{enum|CPICH RSCP|MeasurementQuantity}} has a
                 range of -120 dBm to -25 dBm
              
                 {{enum|CPICH Ec/No|MeasurementQuantity}} has a
                 range of -24 dB to 0 dB";
            }
            leaf ThresholdUsedFrequencyEvent2d {
              type int32 {
                range "-120..0";
              }
              description
                "Defines the reporting threshold for inter-freq HO
                 measurement when the UE is in Cell-DCH state.
                 This is the \"Threshold used frequency\" as
                 defined in {{bibref|3GPP-TS.25.331|Section
                 10.3.7.19}}.
              
                 Each valid value of
                 {{param|MeasurementQuantity}} has a different
                 valid range.
              
                 {{enum|CPICH RSCP|MeasurementQuantity}} has a
                 range of -120 dBm to -25 dBm
              
                 {{enum|CPICH Ec/No|MeasurementQuantity}} has a
                 range of -24 dB to 0 dB";
            }
            leaf ThresholdUsedFrequencyEvent2f {
              type int32 {
                range "-120..0";
              }
              description
                "Defines the reporting threshold for inter-freq HO
                 measurement when the UE is in Cell-DCH state.
                 This is the \"Threshold used frequency\" as
                 defined in {{bibref|3GPP-TS.25.331|Section
                 10.3.7.19}}.
              
                 Each valid value of
                 {{param|MeasurementQuantity}} has a different
                 valid range.
              
                 {{enum|CPICH RSCP|MeasurementQuantity}} has a
                 range of -120 dBm to -25 dBm
              
                 {{enum|CPICH Ec/No|MeasurementQuantity}} has a
                 range of -24 dB to 0 dB";
            }

            list Instance {
              key "IntraFrequencyEventIdentity";
              description
                "Table containing parameters relating to a
                 particular instance of inter-freq events.";
              leaf Enable {
                type boolean;
                default "false";
                description
                  "Enables or disables this {{object}} entry.";
              }
              leaf IntraFrequencyEventIdentity {
                type enumeration {
                  enum "2a";
                  enum "2b";
                  enum "2c";
                  enum "2d";
                  enum "2e";
                  enum "2f";
                }
                config false;
                description
                  "Each entry is an Event ID from the list of:
                   {{enum}}
                
                   Defines the identity of the event used to
                   trigger UE reporting (in case of
                   event-triggered reporting).
                
                   {{bibref|3GPP-TS.25.331|Section 10.3.7.14}}
                
                   This attribute is readable, as it is highly
                   dependent on how the FAP makes use of the
                   event.";
              }
              leaf EventDescription {
                type string {
                  length "0..256";
                }
                config false;
                description
                  "A free-form description of the way the event
                   instance is meant to be used.
                
                   E.g.  \"detecting cell edge to prepare for
                   hand-out\", \"cancel hand-out preparation\".";
              }
              leaf MeasurementQuantity {
                type enumeration {
                  enum "CPICH Ec/No";
                  enum "CPICH RSCP";
                }
                description
                  "Defines the measurement quantity for inter-freq
                   HO measurement when the UE is in Cell-DCH
                   state.
                
                   Enumeration of:
                
                   {{enum}}
                
                   {{bibref|3GPP-TS.25.331|Section 10.3.7.18}}";
              }
              leaf FilterCoefficient {
                type uint32 {
                  range "0..9 | 11 | 13 | 15 | 17 | 19";
                }
                description
                  "Defines the filter coefficient for inter-freq HO
                   measurement when the UE is in Cell-DCH state.
                
                   {{bibref|3GPP-TS.25.331|Section 10.3.7.9 and
                   Section 10.3.7.18}}";
              }
              leaf WeightingFactor {
                type uint32 {
                  range "0..20";
                }
                description
                  "Defines the weighting factor for inter-freq HO
                   measurement when the UE is in Cell-DCH state.
                
                   Actual values of the weighting factor are 0.0
                   to 2.0 in steps of 0.1.  The value of
                   {{param}} divided by 10 yields the actual
                   value of the weighting factor.
                
                   {{bibref|3GPP-TS.25.331|Section 10.3.7.19}}";
              }
              leaf Hysteresis {
                type uint32 {
                  range "0..15";
                }
                description
                  "Defines the hysteresis for inter-freq HO
                   measurement when the UE is in Cell-DCH state.
                
                   Actual values of the range are 0.0 to 14.5 in
                   steps of 0.5.  The value of {{param}} divided
                   by 2 yields the actual value of the
                   hysteresis.
                
                   {{bibref|3GPP-TS.25.331|Section 10.3.7.19}}";
              }
              leaf TimeToTrigger {
                type uint32 {
                  range "0 | 10 | 20 | 40 | 60 | 80 | 100 | 120 | 160 | 200 | 240 | 320 | 640 | 1280 | 2560 | 5000";
                }
                description
                  "Defines the time-to-trigger in {{units}} for
                   inter-freq HO measurement when the UE is in
                   Cell-DCH state.
                
                   Only the specified values are considered
                   valid, any value other than those and the CPE
                   MUST reject the request.
                
                   {{bibref|3GPP-TS.25.331|Section 10.3.7.39 and
                   Section 10.3.7.64}}";
              }
              leaf ThresholdUsedFrequency {
                type int32 {
                  range "-120..0";
                }
                description
                  "Applicable to events 2b, 2d, 2f, otherwise not
                   needed.
                
                   Defines the reporting threshold for inter-freq
                   HO measurement when the UE is in Cell-DCH
                   state.  This is the \"Threshold used
                   frequency\" as defined in
                   {{bibref|3GPP-TS.25.331|Section 10.3.7.19}}.
                
                   Each valid value of
                   {{param|MeasurementQuantity}} has a different
                   valid range.
                
                   {{enum|CPICH RSCP|MeasurementQuantity}} has a
                   range of -120 dBm to -25 dBm
                
                   {{enum|CPICH Ec/No|MeasurementQuantity}} has a
                   range of -24 dB to 0 dB";
              }
              leaf ThresholdNonUsedFrequency {
                type int32 {
                  range "-120..0";
                }
                description
                  "Applicable to events 2a, 2b, 2c, 2e otherwise not
                   needed.
                
                   Defines the reporting threshold for inter-freq
                   HO measurement when the UE is in Cell-DCH
                   state.  This is the \"Threshold non used
                   frequency\" as defined in
                   {{bibref|3GPP-TS.25.331|Section 10.3.7.19}}.
                
                   Each valid value of
                   {{param|MeasurementQuantity}} has a different
                   valid range.
                
                   {{enum|CPICH RSCP|MeasurementQuantity}} has a
                   range of -120 dBm to -25 dBm
                
                   {{enum|CPICH Ec/No|MeasurementQuantity}} has a
                   range of -24 dB to 0 dB";
              }
            }
          }

          container InterRATMeas {
            description
              "This object contains parameters relating to the
               inter-RAT HO related control parameters.  This is
               specifically for GERAN system.";
            leaf GSMFilterCoefficient {
              type uint32 {
                range "0..9 | 11 | 13 | 15 | 17 | 19";
              }
              description
                "Defines the filter coefficient for inter-RAT HO
                 measurement when the UE is in Cell-DCH state.
              
                 {{bibref|3GPP-TS.25.331|Section 10.3.7.9 and
                 Section 10.3.7.29}}";
            }
            leaf BSICVerificationRequired {
              type boolean;
              description
                "Indicates whether the BSIC verification is required
                 or not for inter-RAT HO measurement when the UE
                 is in Cell-DCH state.
              
                 {{bibref|3GPP-TS.25.331|Section 10.3.7.29}}";
            }
            leaf WeightingFactor {
              type uint32 {
                range "0..20";
              }
              description
                "Defines the weighting factor for inter-RAT HO
                 measurement when the UE is in Cell-DCH state.
              
                 Actual values of the weighting factor are 0.0 to
                 2.0 in steps of 0.1.  The value of {{param}}
                 divided by 10 yields the actual value of the
                 weighting factor.
              
                 {{bibref|3GPP-TS.25.331|Section 10.3.7.30}}";
            }
            leaf Hysteresis {
              type uint32 {
                range "0..15";
              }
              description
                "Defines the hysteresis for inter-RAT HO measurement
                 when the UE is in Cell-DCH state.
              
                 Actual values of the range are 0.0 to 7.5 in
                 steps of 0.5.  The value of {{param}} divided by
                 2 yields the actual value of the hysteresis.
              
                 {{bibref|3GPP-TS.25.331|Section 10.3.7.30}}";
            }
            leaf TimeToTrigger {
              type uint32 {
                range "0 | 10 | 20 | 40 | 60 | 80 | 100 | 120 | 160 | 200 | 240 | 320 | 640 | 1280 | 2560 | 5000";
              }
              description
                "Defines the time-to-trigger in {{units}} for
                 inter-RAT HO measurement when the UE is in
                 Cell-DCH state.
              
                 Only the specified values are considered valid,
                 any value other than those and the CPE MUST
                 reject the request.
              
                 {{bibref|3GPP-TS.25.331|Section 10.3.7.39 and
                 Section 10.3.7.64}}";
            }
            leaf ThresholdOwnSystem {
              type int32 {
                range "-115..0";
              }
              description
                "Defines the reporting threshold for inter-RAT HO
                 measurement when the UE is in Cell-DCH state.
                 This is the \"Threshold own system\" as defined
                 in {{bibref|3GPP-TS.25.331|Section 10.3.7.30}}.";
            }
            leaf ThresholdOtherSystem {
              type int32 {
                range "-115..0";
              }
              description
                "Defines the reporting threshold for inter-RAT HO
                 measurement when the UE is in Cell-DCH state.
                 This is the \"Threshold other system\" as
                 defined in {{bibref|3GPP-TS.25.331|Section
                 10.3.7.30}}.";
            }

            list Instance {
              key "InterRATEventIdentity";
              description
                "Table containing parameters relating to a
                 particular instance of inter-freq events.";
              leaf Enable {
                type boolean;
                default "false";
                description
                  "Enables or disables this {{object}} entry.";
              }
              leaf InterRATEventIdentity {
                type enumeration {
                  enum "3a";
                  enum "3b";
                  enum "3c";
                  enum "3d";
                }
                config false;
                description
                  "Each entry is an Event ID from the list of:
                   {{enum}}
                
                   Defines the identity of the event used to
                   trigger UE reporting (in case of
                   event-triggered reporting).
                
                   {{bibref|3GPP-TS.25.331|Section 10.3.7.14}}
                
                   This attribute is readable, as it is highly
                   dependent on how the FAP makes use of the
                   event.";
              }
              leaf EventDescription {
                type string {
                  length "0..256";
                }
                config false;
                description
                  "A free-form description of the way the event
                   instance is meant to be used.
                
                   E.g.  \"hand-out to GSM macrocell\", \"cancel
                   hand-out preparation due to decreasing
                   macrocell quality\".";
              }
              leaf FilterCoefficient {
                type uint32 {
                  range "0..9 | 11 | 13 | 15 | 17 | 19";
                }
                description
                  "Defines the filter coefficient for inter-freq HO
                   measurement when the UE is in Cell-DCH state.
                
                   {{bibref|3GPP-TS.25.331|Section 10.3.7.9 and
                   Section 10.3.7.18}}";
              }
              leaf BSICVerificationRequired {
                type boolean;
                description
                  "Applicable only to GSM events.
                
                   Indicates whether the BSIC verification is
                   required or not for inter-RAT HO measurement
                   when the UE is in Cell-DCH state.
                
                   {{bibref|3GPP-TS.25.331|Section 10.3.7.29}}";
              }
              leaf WeightingFactor {
                type uint32 {
                  range "0..20";
                }
                description
                  "Defines the weighting factor for inter-RAT HO
                   measurement when the UE is in Cell-DCH state.
                
                   Actual values of the weighting factor are 0.0
                   to 2.0 in steps of 0.1.  The value of
                   {{param}} divided by 10 yields the actual
                   value of the weighting factor.
                
                   {{bibref|3GPP-TS.25.331|Section 10.3.7.30}}";
              }
              leaf Hysteresis {
                type uint32 {
                  range "0..15";
                }
                description
                  "Defines the hysteresis for inter-RAT HO
                   measurement when the UE is in Cell-DCH state.
                
                   Actual values of the range are 0.0 to 7.5 in
                   steps of 0.5.  The value of {{param}} divided
                   by 2 yields the actual value of the
                   hysteresis.
                
                   {{bibref|3GPP-TS.25.331|Section 10.3.7.30}}";
              }
              leaf TimeToTrigger {
                type uint32 {
                  range "0 | 10 | 20 | 40 | 60 | 80 | 100 | 120 | 160 | 200 | 240 | 320 | 640 | 1280 | 2560 | 5000";
                }
                description
                  "Defines the time-to-trigger in {{units}} for
                   inter-RAT HO measurement when the UE is in
                   Cell-DCH state.
                
                   Only the specified values are considered
                   valid, any value other than those and the CPE
                   MUST reject the request.
                
                   {{bibref|3GPP-TS.25.331|Section 10.3.7.39 and
                   Section 10.3.7.64}}";
              }
              leaf ThresholdOwnSystem {
                type int32 {
                  range "-115..0";
                }
                description
                  "Applicable only to event 3a, otherwise not
                   needed.
                
                   Defines the reporting threshold for inter-RAT
                   HO measurement when the UE is in Cell-DCH
                   state.  This is the \"Threshold own system\"
                   as defined in {{bibref|3GPP-TS.25.331|Section
                   10.3.7.30}}.";
              }
              leaf ThresholdOtherSystem {
                type int32 {
                  range "-115..0";
                }
                description
                  "Applicable to events 3a, 3b, 3c, otherwise not
                   needed.
                
                   Defines the reporting threshold for inter-RAT
                   HO measurement when the UE is in Cell-DCH
                   state.  This is the \"Threshold other system\"
                   as defined in {{bibref|3GPP-TS.25.331|Section
                   10.3.7.30}}.";
              }
            }
          }

          container UEInternalMeas {
            description
              "This object contains parameters relating to the UE
               internal measurement control parameters.";
            leaf FilterCoefficient {
              type uint32 {
                range "0..9 | 11 | 13 | 15 | 17 | 19";
              }
              description
                "Defines the filter coefficient for UE internal
                 measurement.
              
                 {{bibref|3GPP-TS.25.331|Section 10.3.7.9 and
                 Section 10.3.7.79}}";
            }
            leaf UETxPwrThresholdEvent6a {
              type int32 {
                range "-50..33";
              }
              description
                "Defines the threshold for UE transmit power above
                 which Event 6a is reported.
              
                 {{bibref|3GPP-TS.25.331|Section 10.3.7.80}}";
            }
            leaf TimeToTriggerEvent6a {
              type uint32 {
                range "0 | 10 | 20 | 40 | 60 | 80 | 100 | 120 | 160 | 200 | 240 | 320 | 640 | 1280 | 2560 | 5000";
              }
              description
                "Defines the period in {{units}} between detection
                 of Event 6a and sending of Measurement Report.
              
                 Only the specified values are considered valid,
                 any value other than those and the CPE MUST
                 reject the request.
              
                 {{bibref|3GPP-TS.25.331|Section 10.3.7.80}}";
            }
            leaf UETxPwrThresholdEvent6b {
              type int32 {
                range "-50..33";
              }
              description
                "Defines the threshold for UE transmit power above
                 which Event 6b is reported.
              
                 {{bibref|3GPP-TS.25.331|Section 10.3.7.80}}";
            }
            leaf TimeToTriggerEvent6b {
              type uint32 {
                range "0 | 10 | 20 | 40 | 60 | 80 | 100 | 120 | 160 | 200 | 240 | 320 | 640 | 1280 | 2560 | 5000";
              }
              description
                "Defines the period in {{units}} between detection
                 of Event 6b and sending of Measurement Report.
              
                 Only the specified values are considered valid,
                 any value other than those and the CPE MUST
                 reject the request.
              
                 {{bibref|3GPP-TS.25.331|Section 10.3.7.80}}";
            }
          }

          container RF {
            description
              "This object contains parameters relating to the RF
               configuration.";
            leaf UARFCNDL {
              type string;
              description
                "{{list}} Each item is a DL UTRA Absolute Radio
                 Frequency Channel Number (UARFCN) in an FDD mode
                 cell.
              
                 {{bibref|3GPP-TS.25.433|Section 9.2.1.65}}
              
                 Self-configuration for UARFCN is controlled by
                 {{param|.Capabilities.UMTS.SelfConfig.UARFCNConfig}}
                 from an availability perspective and
                 {{param|.FAPControl.UMTS.SelfConfig.UARFCNSelfConfigEnable}}
                 from an enabled perspective.
              
                 If the FAP's self-configuration capability for
                 UARFCN is available and enabled, this parameter
                 MAY contain more than one item and the FAP is
                 expected to select one from the list for
                 {{param|UARFCNDLInUse}}.
              
                 If the self-configuration capability is not
                 available or not enabled, then this parameter
                 SHOULD contain only a single item.
              
                 The UARFCN values supplied to the list are
                 derived based on the formula defined in
                 {{bibref|3GPP-TS.25.104|Section 5.4.3}}
              
                 The order of the UARFCN entries has no
                 significance.
              
                 The carrier spacing in FDD mode is fixed as
                 defined in {{bibref|3GPP-TS.25.104}}.
                 Therefore, the FAP can unambiguously derive the
                 UL UARFCN value based on the selected DL UARFCN.";
            }
            leaf UARFCNDLInUse {
              type uint32;
              config false;
              description
                "The DL UARFCN being used by the FAP.
              
                 Self-configuration for UARFCN is controlled by
                 {{param|.Capabilities.UMTS.SelfConfig.UARFCNConfig}}
                 from an availability perspective and
                 {{param|.FAPControl.UMTS.SelfConfig.UARFCNSelfConfigEnable}}
                 from an enabled perspective.
              
                 If the self-configuration capability is
                 available and enabled, this parameter indicates
                 the value selected by the FAP among the choices
                 provided in {{param|UARFCNDL}}.
              
                 If the self-configuration capability is not
                 available or not enabled, then this parameter
                 contains the first value in {{param|UARFCNDL}}.";
            }
            leaf UARFCNULInUse {
              type uint32;
              config false;
              description
                "The UL UARFCN being used by the FAP.
              
                 The UL UARFCN that corresponds to
                 {{param|UARFCNDLInUse}}.";
            }
            leaf UARFCNDLToProtect {
              type string;
              description
                "{{list}} Each item is a DL UARFCNs to be protected
                 from adjacent channel interference.  \"Adjacent
                 channel\" in this context means offset from the
                 FAP's UARFCN by 5MHz.
                 {{bibref|3GPP-TS.25.104|Section 6.4.6}}
              
                 If any of the items in the list are adjacent to
                 the FAP's own DL channel, the FAP MUST take the
                 Primary CPICH code power measured on these
                 channels into account as part of its maximum
                 transmit power self-configuration.
              
                 The UARFCNs in the list can belong to any
                 operator, allowing for protection of the FAP
                 operator's own macro layer as well as that of
                 other operators (only the latter is mandated by
                 the {{bibref|3GPP-TS.25.104}} requirements).
              
                 The list SHOULD take into account the ability of
                 the FAP to self-configure its own DL UARFCN and
                 so SHOULD include any channels (requiring
                 protection) which can potentially be adjacent to
                 the UARFCN selected by the FAP.
              
                 For example, if only adjacent operator
                 protection is required and the FAP has the
                 ability to self-configure to any channel owned
                 by its operator, this list would be populated
                 with the UARFCNs immediately above and below the
                 range of channels owned by the FAP operator.
                 Adjacent channel protection can cause the FAP
                 transmit power to be reduced down to as low as
                 8dBm.
              
                 If {{empty}} then it indicates that there are no
                 channels adjacent to the FAP that require
                 protection, or that self-configuration of the
                 FAP transmit power is not enabled.";
            }
            leaf PrimaryScramblingCode {
              type string;
              description
                "{{list}} Each item is a Primary DL Scrambling Code
                 used by the FDD mode cell with a numeric range
                 between 0 and 511 inclusive.
              
                 {{bibref|3GPP-TS.25.433|Section 9.2.2.34}}
              
                 Self-configuration for PSC is controlled by
                 {{param|.Capabilities.UMTS.SelfConfig.PrimaryScramblingCodeConfig}}
                 from an availability perspective and
                 {{param|.FAPControl.UMTS.SelfConfig.PrimaryScramblingCodeSelfConfigEnable}}
                 from an enabled perspective.
              
                 If the FAP's self-configuration capability for
                 {{param}} is available and enabled, this
                 parameter MAY contain more than one item and the
                 FAP is expected to select one from the list for
                 {{param|PrimaryScramblingCodeInUse}}.
              
                 If the self-configuration capability is not
                 available or not enabled, then this parameter
                 SHOULD contain only a single item.
              
                 The multiplicity of the PSC values can also be
                 expressed by defining a range using \"..\" (two
                 periods) between two values.  In this case, the
                 combination of two values defines the
                 lower-bound and upper-bound of the range
                 inclusive.
              
                 The following are examples of valid PSC string:
              
                 :\"20\"
              
                 ::(explicitly specifies a single PSC value)
              
                 :\"20,30,40\"
              
                 ::(specifies 3 possible PSC values to select
                 from)
              
                 \"20..40\"
              
                 ::(specifies 21 possible values between 20 and
                 40, inclusive)
              
                 \"20..40,50\"
              
                 ::(specifies 22 possible values between 20 and
                 40 inclusive and a single value 50)
              
                 The order of the items has no significance.";
            }
            leaf PrimaryScramblingCodeInUse {
              type uint32;
              config false;
              description
                "The PSC being used by the FAP.
              
                 Self-configuration for PSC is controlled by
                 {{param|.Capabilities.UMTS.SelfConfig.PrimaryScramblingCodeConfig}}
                 from an availability perspective and
                 {{param|.FAPControl.UMTS.SelfConfig.PrimaryScramblingCodeSelfConfigEnable}}
                 from an enabled perspective.
              
                 If the self-configuration capability is
                 available and enabled, this parameter indicates
                 the value selected by the FAP among the choices
                 provided in {{param|PrimaryScramblingCode}}.
              
                 If the self-configuration capability is not
                 available or not enabled, then this parameter
                 contains the first value in
                 {{param|PrimaryScramblingCode}}.";
            }
            leaf MaxFAPTxPowerExpanded {
              type string {
                length "0..64";
              }
              description
                "Defines the maximum transmission power allowed on
                 the FAP, maximum value for the linear sum of the
                 power of all downlink physical channels, that is
                 allowed to be used in a cell.
              
                 {{param}} is expressed as a range of allowed
                 maximum power levels with \"..\" (two periods)
                 between the upper and lower values, i.e.
                 \"<Pmax_low>..<Pmax_high>\".
              
                 {{param}} identifies the limits between which
                 the FAP can self-configure its maximum transmit
                 power.
              
                 Self-configuration for maximum transmission
                 power is controlled by
                 {{param|.Capabilities.UMTS.SelfConfig.MaxFAPTxPowerExpandedConfig}}
                 from an availability perspective and
                 {{param|.FAPControl.UMTS.SelfConfig.MaxFAPTxPowerExpandedSelfConfigEnable}}
                 from an enabled perspective.
              
                 <Pmax_low> and <Pmax_high> are measured in dBm
                 and have a range of -30.0 to 20.0 incremented by
                 0.1 dB.
              
                 {{bibref|3GPP-TS.32.642|Section 6.3.9}}
                 {{bibref|3GPP-TS.25.104|Section 6.2.1}}";
            }
            leaf MaxFAPTxPowerInUseExpanded {
              type int32 {
                range "-300..200";
              }
              config false;
              description
                "The maximum transmission power measured in
                 {{units}} currently used by the FAP.
              
                 Actual values of the maximum transmission power
                 are -30.0 {{units}} to 20.0 {{units}} in steps
                 of 0.1 dB.  The value of {{param}} divided by 10
                 yields the actual value of the maximum
                 transmission power.
              
                 Self-configuration for maximum transmission
                 power is controlled by
                 {{param|.Capabilities.UMTS.SelfConfig.MaxFAPTxPowerExpandedConfig}}
                 from an availability perspective and
                 {{param|.FAPControl.UMTS.SelfConfig.MaxFAPTxPowerExpandedSelfConfigEnable}}
                 from an enabled perspective.
              
                 If the self-configuration capability is
                 available and enabled, this parameter indicates
                 the value selected by the FAP among the range
                 provided in {{param|MaxFAPTxPowerExpanded}}.
              
                 If the self-configuration capability is not
                 available or not enabled, then this parameter
                 contains a value selected by the ACS.";
            }
            leaf MaxULTxPower {
              type string {
                length "0..64";
              }
              description
                "Defines the maximum transmission power level a UE
                 can use on PRACH.
              
                 {{param}} is expressed as a range of allowed
                 maximum power levels with \"..\" (two periods)
                 between the upper and lower values, i.e.
                 \"<Pmax_low>..<Pmax_high>\".
              
                 {{param}} identifies the limits between which
                 the FAP can self-configure its maximum transmit
                 power.
              
                 Self-configuration for maximum transmission
                 power is controlled by
                 {{param|.Capabilities.UMTS.SelfConfig.MaxULTxPowerConfig}}
                 from an availability perspective and
                 {{param|.FAPControl.UMTS.SelfConfig.MaxULTxPowerSelfConfigEnable}}
                 from an enabled perspective.
              
                 <Pmax_low> and <Pmax_high> are measured in dBm
                 and have a range of -50 to 33 incremented by 1.
              
                 {{bibref|3GPP-TS.25.331|Section 10.3.6.39}}";
            }
            leaf MaxULTxPowerInUse {
              type int32 {
                range "-50..33";
              }
              config false;
              description
                "The maximum transmission power level a UE can use
                 on PRACH.
              
                 Self-configuration for maximum transmission
                 power is controlled by
                 {{param|.Capabilities.UMTS.SelfConfig.MaxULTxPowerConfig}}
                 from an availability perspective and
                 {{param|.FAPControl.UMTS.SelfConfig.MaxULTxPowerSelfConfigEnable}}
                 from an enabled perspective.
              
                 If the self-configuration capability is
                 available and enabled, this parameter indicates
                 the value selected by the FAP among the range
                 provided in {{param|MaxULTxPower}}.
              
                 If the self-configuration capability is not
                 available or not enabled, then this parameter
                 contains a value selected by the ACS.";
            }
            leaf PCPICHPower {
              type string {
                length "0..64";
              }
              description
                "The value of the transmission power of the Primary
                 Common PIlot CHannel (P-CPICH).  The P-CPICH
                 physical channel carries the common pilots of
                 the cell.  Parameter in SIB5.
              
                 {{param}} is expressed as a range of allowed
                 transmission power levels with \"..\" (two
                 periods) between the upper and lower values,
                 i.e.  \"<Pmax_low>..<Pmax_high>\".
              
                 {{param}} identifies the limits between which
                 the FAP can self-configure its transmission
                 power.
              
                 Self-configuration for transmission power is
                 controlled by
                 {{param|.Capabilities.UMTS.SelfConfig.PCPICHPowerConfig}}
                 from an availability perspective and
                 {{param|.FAPControl.UMTS.SelfConfig.PCPICHPowerSelfConfigEnable}}
                 from an enabled perspective.
              
                 <Pmax_low> and <Pmax_high> are measured in dBm
                 and have a range of -10.0 to 20.0 incremented by
                 0.1 dB.
              
                 {{bibref|3GPP-TS.32.642|Section 6.3.11}}
                 {{bibref|3GPP-TS.25.104|Section 6.2.1}}";
            }
            leaf PCPICHPowerInUse {
              type int32 {
                range "-100..200";
              }
              config false;
              description
                "The P-CPICH power measured in {{units}} currently
                 used by the FAP.
              
                 Actual values of the maximum transmission power
                 are -10.0 {{units}} to 20.0 {{units}} in steps
                 of 0.1 dB.  The value of {{param}} divided by 10
                 yields the actual value of the maximum
                 transmission power.
              
                 Self-configuration for transmission power is
                 controlled by
                 {{param|.Capabilities.UMTS.SelfConfig.PCPICHPowerConfig}}
                 from an availability perspective and
                 {{param|.FAPControl.UMTS.SelfConfig.PCPICHPowerSelfConfigEnable}}
                 from an enabled perspective.
              
                 If the self-configuration capability is
                 available and enabled, this parameter indicates
                 the value selected by the FAP among the range
                 provided in {{param|PCPICHPower}}.
              
                 If the self-configuration capability is not
                 available or not enabled, then this parameter
                 contains a value selected by the ACS.";
            }
            leaf PowerOffsetPilotDPDCH {
              type uint32 {
                range "0..24";
              }
              description
                "Defines the power offset between pilot channel and
                 DPDCH.
              
                 Actual values of the offset are 0.0 {{units}} to
                 6.0 {{units}} in steps of 0.25 {{units}}.  The
                 value of {{param}} divided by 4 yields the
                 actual value of the offset.
              
                 {{bibref|3GPP-TS.25.331|Section 10.3.6.18}}
                 {{bibref|3GPP-TS.25.214|Section 5.2.1}}";
            }
            leaf FAPCoverageTarget {
              type uint32 {
                range "50..150";
              }
              description
                "Defines the target value measured in {{units}} for
                 the range of the FAP's DL coverage, in terms of
                 RF propagation loss.
              
                 This value can be used by the FAP's
                 self-configuration algorithms to help derive
                 transmit power levels in the presence of
                 co-channel and adjacent channel interference.
              
                 {{bibref|3GPP-TS.25.967|Section 7.2.1}}";
            }
            leaf FAPQualityTargetEcIo {
              type int32 {
                range "-200..0";
              }
              description
                "Defines the target value measured in dB for the
                 downlink signal quality of the FAP in terms of
                 CPICH Ec/Io, thereby clarifying the meaning of
                 \"FAPCoverageTarget\".
              
                 Actual values of the FAPQualityTargetEcIo are
                 -20 dB to 0 dB in steps of 0.1 dB.";
            }
            leaf PSCHPower {
              type int32 {
                range "-350..150";
              }
              description
                "Defines the transmission power offset measured in
                 {{units}} of the Primary SCH relative to the
                 Primary CPICH power.
              
                 Actual values of the transmission power offset
                 are -35.0 {{units}} to 15.0 {{units}} in steps
                 of 0.1 {{units}}.  The value of {{param}}
                 divided by 10 yields the actual value of the
                 transmission power offset.
              
                 {{bibref|3GPP-TS.32.642|Section 6.3.11}}
                 {{bibref|3GPP-TS.25.433|Section 9.1.24 and
                 Section 9.2.1.21}}";
            }
            leaf SSCHPower {
              type int32 {
                range "-350..150";
              }
              description
                "Defines the transmission power offset measured in
                 {{units}} of the Secondary SCH relative to the
                 Primary CPICH power.
              
                 Actual values of the transmission power offset
                 are -35.0 {{units}} to 15.0 {{units}} in steps
                 of 0.1 {{units}}.  The value of {{param}}
                 divided by 10 yields the actual value of the
                 transmission power offset.
              
                 {{bibref|3GPP-TS.32.642|Section 6.3.11}}
                 {{bibref|3GPP-TS.25.433|Section 9.1.24 and
                 Section 9.2.1.21}}";
            }
            leaf PICHPower {
              type int32 {
                range "-10..5";
              }
              description
                "Defines the maximum transmission power offset
                 measured in {{units}} of the PICH channel
                 relative to the Primary CPICH transmission
                 power.
              
                 {{bibref|3GPP-TS.32.642|Section 6.3.9}}
                 {{bibref|3GPP-TS.25.433|Section 9.2.1.49A}}
                 {{bibref|3GPP-TS.25.331|Section 10.3.6.50}}";
            }
            leaf PCHPower {
              type int32 {
                range "-350..150";
              }
              description
                "Defines the transmission power offset measured in
                 {{units}} of the PCH relative to the Primary
                 CPICH power.
              
                 Actual values of the transmission power offset
                 are -35.0 {{units}} to 15.0 {{units}} in steps
                 of 0.1 {{units}}.  The value of {{param}}
                 divided by 10 yields the actual value of the
                 transmission power offset.
              
                 {{bibref|3GPP-TS.32.642|Section 6.3.9}}
                 {{bibref|3GPP-TS.25.433|Section 9.1.3.1 and
                 Section 9.2.1.21}}";
            }
            leaf FACHPower {
              type int32 {
                range "-350..150";
              }
              description
                "Defines the transmission power offset measured in
                 {{units}} of the FACH relative to the Primary
                 CPICH power.
              
                 Actual values of the transmission power offset
                 are -35.0 {{units}} to 15.0 {{units}} in steps
                 of 0.1 {{units}}.  The value of {{param}}
                 divided by 10 yields the actual value of the
                 transmission power offset.
              
                 {{bibref|3GPP-TS.32.642|Section 6.3.9}}
                 {{bibref|3GPP-TS.25.433|Section 9.1.6.1 and
                 Section 9.2.1.21}}";
            }
            leaf BCHPower {
              type int32 {
                range "-350..150";
              }
              description
                "Defines the transmission power offset measured in
                 {{units}} of the BCH relative to the Primary
                 CPICH power.
              
                 Actual values of the transmission power offset
                 are -35.0 {{units}} to 15.0 {{units}} in steps
                 of 0.1 {{units}}.  The value of {{param}}
                 divided by 10 yields the actual value of the
                 transmission power offset.
              
                 {{bibref|3GPP-TS.32.642|Section 9.3.11}}
                 {{bibref|3GPP-TS.25.433|Section 9.1.24 and
                 Section 9.2.1.21}}";
            }
            leaf AICHPower {
              type int32 {
                range "-22..5";
              }
              description
                "Defines the transmission power offset measured in
                 {{units}} of one AICH relative to the Primary
                 CPICH power.  Parameter defined in SIB5
                 {{bibref|3GPP-TS.25.331|Section 10.3.6.3}}.
              
                 Transmission power level of AICH, AP-AICH and
                 CD/CA-ICH channels compared to CPICH.
              
                 {{bibref|3GPP-TS.32.642|Section 6.3.11}}
                 {{bibref|3GPP-TS.25.433|Section 9.2.2.D}}";
            }
            leaf CTCHAllocationPeriod {
              type uint32 {
                range "1..255";
              }
              description
                "The value defines 'N' multiples of M(TTI) for CBS
                 DRX calculations at the UE side.";
            }
            leaf CBSFrameOffset {
              type uint32 {
                range "0..255";
              }
              description
                "Value of CBS frame offset (CTCH) on DL FACH.
                 Parameter in SIB5";
            }
            leaf MaxTTI {
              type uint32 {
                range "1..255";
              }
              description
                "Defines the number of radio frames in the TTI of
                 the FACH used for CTCH (MTTI).";
            }
            leaf NoiseRiseLimitLowerValue {
              type uint32 {
                range "0..500";
              }
              description
                "Defines the lower value of the Noise Rise Limit
                 range that UMTS FAP is allowed to pick from.
              
                 The value is measured in dB and has a range of
                 0.0 to 50.0 incremented by 0.1 dB.  the value
                 MUST not exceed the value of
                 {{param|.CellConfig.UMTS.RAN.RF.NoiseRiseLimitUpperValue}}
              
                 The Noise Rise Limit range identifies the limits
                 between which the FAP can self-configure its
                 uplink noise rise limit.
              
                 Self-configuration for noise rise limit is
                 controlled by
                 {{param|.Capabilities.UMTS.SelfConfig.NoiseRiseLimitConfig}}
                 from an availability perspective and
                 {{param|.FAPControl.UMTS.SelfConfig.NoiseRiseLimitConfigEnable}}
                 from an enabled perspective.";
            }
            leaf NoiseRiseLimitUpperValue {
              type uint32 {
                range "0..500";
              }
              description
                "Defines the upper value of the Noise Rise Limit
                 range that UMTS FAP is allowed to pick from.
              
                 The value is measured in dB and has a range of
                 0.0 to 50.0 incremented by 0.1 dB.  the value
                 MUST not be below the value of
                 {{param|.CellConfig.UMTS.RAN.RF.NoiseRiseLimitLowerValue}}
              
                 NoiseRiseLimit identifies the limits between
                 which the FAP can self-configure its uplink
                 noise rise limit.
              
                 Self-configuration for noise rise limit is
                 controlled by
                 {{param|.Capabilities.UMTS.SelfConfig.NoiseRiseLimitConfig}}
                 from an availability perspective and
                 {{param|.FAPControl.UMTS.SelfConfig.NoiseRiseLimitConfigEnable}}
                 from an enabled perspective.";
            }
            leaf NoiseRiseLimitInUse {
              type uint32 {
                range "0..500";
              }
              config false;
              description
                "Actual value of the Noise Rise Limit that the FAP
                 uses.  The value is measured in dB and has a
                 range of 0.0 to 50.0 incremented by 0.1 dB.";
            }
          }

          container NeighborList {
            description
              "This object contains parameters relating to the
               neighbor list.";
            leaf MaxIntraFreqCellEntries {
              type uint32;
              config false;
              description
                "The maximum number of entries in the
                 {{object|.CellConfig.UMTS.RAN.NeighborList.IntraFreqCell.{i}.}}
                 table.";
            }
            leaf MaxInterFreqCellEntries {
              type uint32;
              config false;
              description
                "The maximum number of entries in the
                 {{object|.CellConfig.UMTS.RAN.NeighborList.InterFreqCell.{i}.}}
                 table.";
            }

            list IntraFreqCell {
              key "PCPICHScramblingCode";
              description
                "Table containing the intra-frequency cell list
                 provided by the ACS.  The table contents MAY be
                 added/deleted/modified during operation, in
                 which case these changes shall be reflected in
                 the broadcast information as soon as possible.";
              leaf Enable {
                type boolean;
                default "false";
                description
                  "Enables or disables this entry.";
              }
              leaf MustInclude {
                type boolean;
                default "false";
                description
                  "Indicates whether this instance of the neighbor
                   shall be included or excluded in the FAP's NL
                   configuration.";
              }
              leaf PLMNID {
                type string {
                  length "0..6";
                }
                default "";
                description
                  "PLMN ID consists of Mobile Country Code (MCC) and
                   Mobile Network Code (MNC)
                   {{bibref|3GPP-TS.23.003}},
                   {{bibref|3GPP-TS.24.008}}.
                
                   Mobile Country Code consists of three digits
                   and uniquely identifies the country of
                   domicile of the subscriber.
                
                   Mobile Network Code consists of two or three
                   digits and identifies the Home PLMN within a
                   country.
                
                   For a 2-digit MNC the total string length of
                   {{param}} is 5.";
              }
              leaf RNCID {
                type uint32 {
                  range "0..65535";
                }
                default "0";
                description
                  "RNC-ID of an intra-freq neighbor cell.  It
                   uniquely identifies an RNC within a PLMN.
                
                   Normally, RNC-ID consists of 12 bits (i.e.  a
                   range of [0:4095]).  However, if the value is
                   larger than 4095, then Extended RNC-ID (range
                   of [4096:65535]) is used in RANAP.
                
                   The RNC-ID and Extended RNC-ID are combined
                   into a single parameter here as there is no
                   explicit need to have them separated.
                
                   {{bibref|3GPP-TS.25.413|Section 9.2.1.39}}";
              }
              leaf CID {
                type uint32 {
                  range "1..65535";
                }
                description
                  "Cell Identifier (C-id) that identifies a cell
                   within an RNS.  This Cell Identifier together
                   with the controlling RNC (RNC-ID) constitutes
                   the UTRAN Cell ID (UC-ID) and is used to
                   identify a cell uniquely within UTRAN.  C-ID
                   is either 12-bit or 16-bit value.
                   {{bibref|3GPP-TS.25.401|Section 6.1.5}}.";
              }
              leaf LAC {
                type uint32 {
                  range "0..65535";
                }
                default "0";
                description
                  "Location Area Code (LAC).  The concatenation of
                   PLMN ID (MCC+MNC) and LAC uniquely identifies
                   the Location Area ID (LAI).
                
                   {{bibref|3GPP-TS.23.003|Section 4.1}}
                   {{bibref|3GPP-TS.25.413|Section 9.2.3.6}}";
              }
              leaf RAC {
                type uint32 {
                  range "0..255";
                }
                default "0";
                description
                  "Routing Area Code (RAC).  The concatenation of
                   PLMN ID (MCC+MNC), LAC, and RAC uniquely
                   identifies the Routing Area ID (RAI).
                
                   {{bibref|3GPP-TS.23.003|Section 4.2}}
                   {{bibref|3GPP-TS.25.413|Section 9.2.3.7}}";
              }
              leaf URA {
                type uint32 {
                  range "0..65535";
                }
                default "0";
                description
                  "UTRAN Registration Area (URA)
                   {{bibref|3GPP-TS.23.401}}.
                
                   Indicates to the UE which {{param}} it shall
                   use in case of overlapping URAs.
                
                   {{bibref|3GPP-TS.25.331|Section 10.3.2.6}}";
              }
              leaf PCPICHScramblingCode {
                type uint32 {
                  range "0..511";
                }
                default "0";
                description
                  "Primary CPICH scrambling code.";
              }
              leaf PCPICHTxPower {
                type int32 {
                  range "-100..500";
                }
                default "0";
                description
                  "Primary CPICH Tx power in {{units}}.
                
                   Actual values of the power are -10.0 {{units}}
                   to 50.0 {{units}} in steps of 0.1 dB.  The
                   value of {{param}} divided by 10 yields the
                   actual value of the power.
                
                   {{bibref|3GPP-TS.32.642|Section 6.3.11}}
                   {{bibref|3GPP-TS.25.433|Section 2.2.33}}";
              }
              leaf CollocatedInterFreqCell {
                type uint32 {
                  range "0..268435455";
                }
                description
                  "Provides identity of collocated inter-frequency
                   Cell.  Needed for pathloss estimation, in case
                   the femto environment masks intra-frequency
                   neighbor.
                
                   Cell Identity.
                   {{bibref|3GPP-TS.25.331|Section 10.3.2.2}}";
              }
              leaf MaxTxPower {
                type int32 {
                  range "-300..600";
                }
                default "0";
                description
                  "Cell Max Tx Power.  Parameter needed in HNB power
                   calibration, for protection of neighbour
                   cells.  Actual values of the power are -30.0
                   dBm to 60.0 dBm
                
                   in steps of 0.1 dB.  The value of MaxTxPower
                
                   divided by 10 yields the actual value of the
                   power.
                
                   C.f {{bibref|3GPP-TS.32.642|Section 6.3.11}}
                   {{bibref|3GPP-TS.25.104|Section 6.2.1}}";
              }
              leaf MaxDPCHtxPower {
                type int32 {
                  range "-400..500";
                }
                default "0";
                description
                  "Maximum DL DPCH Tx Power per UE configured in the
                   cell (for CS UEs).
                
                   Parameter may be used by FAP to protect the DL
                   budget allocated to neighbouring UEs served by
                   neighbour cells.
                
                   C.f (max 10 dB below max Tx power)
                
                   {{bibref|3GPP-TS.32.642|Section 6.3.11}}
                   {{bibref|3GPP-TS.25.104|Section 6.2.1}}
                
                   Actual values of the power are -40.0 dBm to
                   50.0 dBm
                
                   in steps of 0.1 dB.  The value of
                   MaxDPCHtxPower
                
                   divided by 10 yields the actual value of the
                   power.";
              }
            }

            list InterFreqCell {
              key "PCPICHScramblingCode UARFCNDL";
              description
                "Table containing the inter-frequency cell list
                 provided by the ACS.  The table contents MAY be
                 added/deleted/modified during operation, in
                 which case these changes shall be reflected in
                 the broadcast information as soon as possible.";
              leaf Enable {
                type boolean;
                default "false";
                description
                  "Enables or disables this entry.";
              }
              leaf MustInclude {
                type boolean;
                default "false";
                description
                  "Indicates whether this instance of the neighbor
                   shall be included or excluded in the FAP's NL
                   configuration.";
              }
              leaf PLMNID {
                type string {
                  length "0..6";
                }
                default "";
                description
                  "PLMN ID consists of Mobile Country Code (MCC) and
                   Mobile Network Code (MNC)
                   {{bibref|3GPP-TS.23.003}},
                   {{bibref|3GPP-TS.24.008}}.
                
                   Mobile Country Code consists of three digits
                   and uniquely identifies the country of
                   domicile of the subscriber.
                
                   Mobile Network Code consists of two or three
                   digits and identifies the Home PLMN within a
                   country.
                
                   For a 2-digit MNC the total string length of
                   {{param}} is 5.";
              }
              leaf RNCID {
                type uint32 {
                  range "0..65535";
                }
                default "0";
                description
                  "RNC-ID of an intra-freq neighbor cell.  It
                   uniquely identifies an RNC within a PLMN.
                
                   Normally, RNC-ID consists of 12 bits (i.e.  a
                   range of [0:4095]).  However, if the value is
                   larger than 4095, then Extended RNC-ID (range
                   of [4096:65535]) is used in RANAP.
                
                   The RNC-ID and Extended RNC-ID are combined
                   into a single parameter here as there is no
                   explicit need to have them separated.
                
                   {{bibref|3GPP-TS.25.413|Section 9.2.1.39}}";
              }
              leaf CID {
                type uint32 {
                  range "1..65535";
                }
                description
                  "Cell Identifier (C-id) that identifies a cell
                   within an RNS.  This Cell Identifier together
                   with the controlling RNC (RNC-ID) constitutes
                   the UTRAN Cell ID (UC-ID) and is used to
                   identify a cell uniquely within UTRAN.  C-ID
                   is either 12-bit or 16-bit value.
                   {{bibref|3GPP-TS.25.401|Section 6.1.5}}.";
              }
              leaf LAC {
                type uint32 {
                  range "0..65535";
                }
                default "0";
                description
                  "Location Area Code (LAC).  The concatenation of
                   PLMN ID (MCC+MNC) and LAC uniquely identifies
                   the Location Area ID (LAI).
                
                   {{bibref|3GPP-TS.23.003|Section 4.1}}
                   {{bibref|3GPP-TS.25.413|Section 9.2.3.6}}";
              }
              leaf RAC {
                type uint32 {
                  range "0..255";
                }
                default "0";
                description
                  "Routing Area Code (RAC).  The concatenation of
                   PLMN ID (MCC+MNC), LAC, and RAC uniquely
                   identifies the Routing Area ID (RAI).
                
                   {{bibref|3GPP-TS.23.003|Section 4.2}}
                   {{bibref|3GPP-TS.25.413|Section 9.2.3.7}}";
              }
              leaf URA {
                type uint32 {
                  range "0..65535";
                }
                default "0";
                description
                  "UTRAN Registration Area (URA)
                   {{bibref|3GPP-TS.23.401}}.
                
                   Indicates to the UE which {{param}} it shall
                   use in case of overlapping URAs.
                
                   {{bibref|3GPP-TS.25.331|Section 10.3.2.6}}";
              }
              leaf UARFCNUL {
                type uint32 {
                  range "0..16383";
                }
                description
                  "The UL UTRA Absolute Radio Frequency Channel
                   Number (UARFCN) in an FDD mode cell.
                   {{bibref|3GPP-TS.25.433}}";
              }
              leaf UARFCNDL {
                type uint32 {
                  range "0..16383";
                }
                description
                  "The DL UTRA Absolute Radio Frequency Channel
                   Number (UARFCN) in an FDD mode cell.
                   {{bibref|3GPP-TS.25.433}}";
              }
              leaf PCPICHScramblingCode {
                type uint32 {
                  range "0..511";
                }
                default "0";
                description
                  "Primary CPICH scrambling code.";
              }
              leaf PCPICHTxPower {
                type int32 {
                  range "-100..500";
                }
                default "0";
                description
                  "Primary CPICH Tx power in {{units}}.
                
                   Actual values of the power are -10.0 {{units}}
                   to 50.0 {{units}} in steps of 0.1 dB.  The
                   value of {{param}} divided by 10 yields the
                   actual value of the power.
                
                   {{bibref|3GPP-TS.32.642|Section 6.3.11}}
                   {{bibref|3GPP-TS.25.433|Section 2.2.33}}";
              }
            }

            container InterRATCell {
              description
                "The inter-RAT cell lists separated by technology.
                 {{bibref|3GPP-TS.25.331|Section 10.3.7.23}}";
              leaf MaxGSMEntries {
                type uint32;
                config false;
                description
                  "The maximum number of entries in the
                   {{object|.CellConfig.UMTS.RAN.NeighborList.InterRATCell.GSM.{i}.}}
                   table.";
              }

              list GSM {
                key "BCCHARFCN";
                description
                  "Table containing the inter-RAT cell list for GSM
                   provided by the ACS.  The table contents MAY
                   be added/deleted/modified during operation, in
                   which case these changes shall be reflected in
                   the broadcast information as soon as possible.";
                leaf Enable {
                  type boolean;
                  default "false";
                  description
                    "Enables or disables this entry.";
                }
                leaf MustInclude {
                  type boolean;
                  default "false";
                  description
                    "Indicates whether this instance of the neighbor
                     shall be included or excluded in the FAP's
                     NL configuration.";
                }
                leaf PLMNID {
                  type string {
                    length "0..6";
                  }
                  default "";
                  description
                    "PLMN ID consists of Mobile Country Code (MCC)
                     and Mobile Network Code (MNC)
                     {{bibref|3GPP-TS.23.003}},
                     {{bibref|3GPP-TS.24.008}}.
                  
                     Mobile Country Code consists of three digits
                     and uniquely identifies the country of
                     domicile of the subscriber.
                  
                     Mobile Network Code consists of two or three
                     digits and identifies the Home PLMN within a
                     country.
                  
                     For a 2-digit MNC the total string length of
                     {{param}} is 5.";
                }
                leaf LAC {
                  type uint32 {
                    range "0..65535";
                  }
                  default "0";
                  description
                    "Location Area Code (LAC).  The concatenation of
                     PLMN ID (MCC+MNC) and LAC uniquely
                     identifies the Location Area ID (LAI).
                  
                     {{bibref|3GPP-TS.23.003|Section 4.1}}
                     {{bibref|3GPP-TS.25.413|Section 9.2.3.6}}";
                }
                leaf BSIC {
                  type uint32 {
                    range "0..255";
                  }
                  description
                    "BSIC of the cell per {{bibref|3GPP-TS.23.003}},
                     consisting of:
                  
                     :Bit 7:6 - not used (\"00\")
                  
                     :Bit 5:3 - NCC (PLMN Color Code)
                  
                     :Bit 2:0 - BCC (BS color code)
                  
                     For example, if NCC is 7 and BCC is 2 you
                     would have 00111010 (binary) or 0x3A (hex),
                     and the value of this parameter would be 58.";
                }
                leaf CI {
                  type uint32 {
                    range "0..65535";
                  }
                  description
                    "Cell ID of the cell per
                     {{bibref|3GPP-TS.23.003|Section 4.3.1}}.";
                }
                leaf BandIndicator {
                  type enumeration {
                    enum "GSM 850";
                    enum "GSM 900";
                    enum "DCS 1800";
                    enum "PCS 1900";
                  }
                  description
                    "Indicates how to interpret the BCCH ARFCN.
                     {{enum}}";
                }
                leaf BCCHARFCN {
                  type uint32 {
                    range "0..1023";
                  }
                  description
                    "ARFCN of this cell.";
                }
              }
            }
          }

          container NeighborListInUse {
            config false;
            description
              "This object contains parameters relating to the
               neighbor list used by the FAP based on its
               self-configuration capability and
               {{object|.CellConfig.UMTS.RAN.NeighborList.}}
               configuration of adding and excluding cells.";
            leaf MaxIntraFreqCellEntries {
              type uint32;
              description
                "The maximum number of entries in the
                 {{object|.CellConfig.UMTS.RAN.NeighborList.IntraFreqCell.{i}.}}
                 table.";
            }
            leaf MaxInterFreqCellEntries {
              type uint32;
              description
                "The maximum number of entries in the
                 {{object|.CellConfig.UMTS.RAN.NeighborList.InterFreqCell.{i}.}}
                 table.";
            }

            list IntraFreqCell {
              key "PCPICHScramblingCode";
              description
                "Table containing the intra-frequency cell list.";
              leaf PLMNID {
                type string {
                  length "0..6";
                }
                description
                  "PLMN ID consists of Mobile Country Code (MCC) and
                   Mobile Network Code (MNC)
                   {{bibref|3GPP-TS.23.003}},
                   {{bibref|3GPP-TS.24.008}}.
                
                   Mobile Country Code consists of three digits
                   and uniquely identifies the country of
                   domicile of the subscriber.
                
                   Mobile Network Code consists of two or three
                   digits and identifies the Home PLMN within a
                   country.
                
                   For a 2-digit MNC the total string length of
                   {{param}} is 5.";
              }
              leaf RNCID {
                type uint32 {
                  range "0..65535";
                }
                description
                  "RNC-ID of an intra-freq neighbor cell.  It
                   uniquely identifies an RNC within a PLMN.
                
                   Normally, RNC-ID consists of 12 bits (i.e.  a
                   range of [0:4095]).  However, if the value is
                   larger than 4095, then Extended RNC-ID (range
                   of [4096:65535]) is used in RANAP.
                
                   The RNC-ID and Extended RNC-ID are combined
                   into a single parameter here as there is no
                   explicit need to have them separated.
                
                   {{bibref|3GPP-TS.25.413|Section 9.2.1.39}}";
              }
              leaf CID {
                type uint32 {
                  range "0..65535";
                }
                description
                  "C-ID of the intra-freq neighbour cell
                   {{bibref|3GPP-TS.25.401|Section 6.1.5}}.
                
                   If {{param|RNCID}} is larger than 4095, then
                   {{param}} will be 12 bits (i.e.  a range of
                   [0:4095]), else {{param}} is 16 bits long
                   (i.e.  range of [4096:65535]).
                
                   This is needed to facilitate Femto to Macro
                   handover.
                
                   Used in {{bibref|3GPP-TS.25.413|Section
                   9.2.1.28}} as part of Target Cell ID.";
              }
              leaf LAC {
                type uint32 {
                  range "0..65535";
                }
                description
                  "Location Area Code (LAC).  The concatenation of
                   PLMN ID (MCC+MNC) and LAC uniquely identifies
                   the Location Area ID (LAI).
                
                   {{bibref|3GPP-TS.23.003|Section 4.1}}
                   {{bibref|3GPP-TS.25.413|Section 9.2.3.6}}";
              }
              leaf RAC {
                type uint32 {
                  range "0..255";
                }
                description
                  "Routing Area Code (RAC).  The concatenation of
                   PLMN ID (MCC+MNC), LAC, and RAC uniquely
                   identifies the Routing Area ID (RAI).
                
                   {{bibref|3GPP-TS.23.003|Section 4.2}}
                   {{bibref|3GPP-TS.25.413|Section 9.2.3.7}}";
              }
              leaf URA {
                type uint32 {
                  range "0..65535";
                }
                description
                  "UTRAN Registration Area (URA)
                   {{bibref|3GPP-TS.23.401}}.
                
                   Indicates to the UE which {{param}} it shall
                   use in case of overlapping URAs.
                
                   {{bibref|3GPP-TS.25.331|Section 10.3.2.6}}";
              }
              leaf PCPICHScramblingCode {
                type uint32 {
                  range "0..511";
                }
                description
                  "Primary CPICH scrambling code.";
              }
            }

            list InterFreqCell {
              key "PCPICHScramblingCode UARFCNDL";
              description
                "Table containing the inter-frequency cell list.";
              leaf PLMNID {
                type string {
                  length "0..6";
                }
                description
                  "PLMN ID consists of Mobile Country Code (MCC) and
                   Mobile Network Code (MNC)
                   {{bibref|3GPP-TS.23.003}},
                   {{bibref|3GPP-TS.24.008}}.
                
                   Mobile Country Code consists of three digits
                   and uniquely identifies the country of
                   domicile of the subscriber.
                
                   Mobile Network Code consists of two or three
                   digits and identifies the Home PLMN within a
                   country.
                
                   For a 2-digit MNC the total string length of
                   {{param}} is 5.";
              }
              leaf RNCID {
                type uint32 {
                  range "0..65535";
                }
                description
                  "RNC-ID of an intra-freq neighbor cell.  It
                   uniquely identifies an RNC within a PLMN.
                
                   Normally, RNC-ID consists of 12 bits (i.e.  a
                   range of [0:4095]).  However, if the value is
                   larger than 4095, then Extended RNC-ID (range
                   of [4096:65535]) is used in RANAP.
                
                   The RNC-ID and Extended RNC-ID are combined
                   into a single parameter here as there is no
                   explicit need to have them separated.
                
                   {{bibref|3GPP-TS.25.413|Section 9.2.1.39}}";
              }
              leaf CID {
                type uint32 {
                  range "0..65535";
                }
                description
                  "C-ID of the intra-freq neighbour cell
                   {{bibref|3GPP-TS.25.401|Section 6.1.5}}.
                
                   If {{param|RNCID}} is larger than 4095, then
                   {{param}} will be 12 bits (i.e.  a range of
                   [0:4095]), else {{param}} is 16 bits long
                   (i.e.  range of [4096:65535]).
                
                   This is needed to facilitate Femto to Macro
                   handover.
                
                   Used in {{bibref|3GPP-TS.25.413|Section
                   9.2.1.28}} as part of Target Cell ID.";
              }
              leaf LAC {
                type uint32 {
                  range "0..65535";
                }
                description
                  "Location Area Code (LAC).  The concatenation of
                   PLMN ID (MCC+MNC) and LAC uniquely identifies
                   the Location Area ID (LAI).
                
                   {{bibref|3GPP-TS.23.003|Section 4.1}}
                   {{bibref|3GPP-TS.25.413|Section 9.2.3.6}}";
              }
              leaf RAC {
                type uint32 {
                  range "0..255";
                }
                description
                  "Routing Area Code (RAC).  The concatenation of
                   PLMN ID (MCC+MNC), LAC, and RAC uniquely
                   identifies the Routing Area ID (RAI).
                
                   {{bibref|3GPP-TS.23.003|Section 4.2}}
                   {{bibref|3GPP-TS.25.413|Section 9.2.3.7}}";
              }
              leaf URA {
                type uint32 {
                  range "0..65535";
                }
                description
                  "UTRAN Registration Area (URA)
                   {{bibref|3GPP-TS.23.401}}.
                
                   Indicates to the UE which {{param}} it shall
                   use in case of overlapping URAs.
                
                   {{bibref|3GPP-TS.25.331|Section 10.3.2.6}}";
              }
              leaf UARFCNUL {
                type uint32 {
                  range "0..16383";
                }
                description
                  "The UL UTRA Absolute Radio Frequency Channel
                   Number (UARFCN) in an FDD mode cell.
                   {{bibref|3GPP-TS.25.433}}";
              }
              leaf UARFCNDL {
                type uint32 {
                  range "0..16383";
                }
                description
                  "The DL UTRA Absolute Radio Frequency Channel
                   Number (UARFCN) in an FDD mode cell.
                   {{bibref|3GPP-TS.25.433}}";
              }
              leaf PCPICHScramblingCode {
                type uint32 {
                  range "0..511";
                }
                description
                  "Primary CPICH scrambling code.";
              }
            }

            container InterRATCell {
              description
                "The inter-RAT cell lists separated by technology.
                 {{bibref|3GPP-TS.25.331|Section 10.3.7.23}}";
              leaf MaxGSMEntries {
                type uint32;
                description
                  "The maximum number of entries in the
                   {{object|.CellConfig.UMTS.RAN.NeighborList.InterRATCell.GSM.{i}.}}
                   table.";
              }

              list GSM {
                key "BCCHARFCN";
                description
                  "Table containing the inter-RAT cell list for GSM.";
                leaf PLMNID {
                  type string {
                    length "0..6";
                  }
                  description
                    "PLMN ID consists of Mobile Country Code (MCC)
                     and Mobile Network Code (MNC)
                     {{bibref|3GPP-TS.23.003}},
                     {{bibref|3GPP-TS.24.008}}.
                  
                     Mobile Country Code consists of three digits
                     and uniquely identifies the country of
                     domicile of the subscriber.
                  
                     Mobile Network Code consists of two or three
                     digits and identifies the Home PLMN within a
                     country.
                  
                     For a 2-digit MNC the total string length of
                     {{param}} is 5.";
                }
                leaf LAC {
                  type uint32 {
                    range "0..65535";
                  }
                  description
                    "Location Area Code (LAC).  The concatenation of
                     PLMN ID (MCC+MNC) and LAC uniquely
                     identifies the Location Area ID (LAI).
                  
                     {{bibref|3GPP-TS.23.003|Section 4.1}}
                     {{bibref|3GPP-TS.25.413|Section 9.2.3.6}}";
                }
                leaf BSIC {
                  type uint32 {
                    range "0..255";
                  }
                  description
                    "BSIC of the cell per {{bibref|3GPP-TS.23.003}},
                     consisting of:
                  
                     :Bit 7:6 - not used (\"00\")
                  
                     :Bit 5:3 - NCC (PLMN Color Code)
                  
                     :Bit 2:0 - BCC (BS color code)
                  
                     For example, if NCC is 7 and BCC is 2 you
                     would have 00111010 (binary) or 0x3A (hex),
                     and the value of this parameter would be 58.";
                }
                leaf CI {
                  type uint32 {
                    range "0..65535";
                  }
                  description
                    "Cell ID of the cell per
                     {{bibref|3GPP-TS.23.003|Section 4.3.1}}.";
                }
                leaf BandIndicator {
                  type enumeration {
                    enum "GSM 850";
                    enum "GSM 900";
                    enum "DCS 1800";
                    enum "PCS 1900";
                  }
                  description
                    "Indicates how to interpret the BCCH ARFCN.
                     {{enum}}";
                }
                leaf BCCHARFCN {
                  type uint32 {
                    range "0..1023";
                  }
                  description
                    "ARFCN of this cell.";
                }
              }
            }
          }

          container RRC {
            config false;
            description
              "This object provides monitoring of the RRC in the
               HNB.";

            container Stats {
              description
                "This object provides the RRC statistics as defined
                 in {{bibref|3GPP-TS.32.452}}.";
              leaf AttConnEstab {
                type string;
                description
                  "This measurement provides the number of RRC
                   connection establishment attempts by cause.
                
                   {{list| where each item is defined as the
                   \"cause name=measurement value\"}} The total
                   of all the measurements is provided using the
                   cause name= \"sum\".";
              }
              leaf FailConnEstab {
                type string;
                description
                  "This measurement provides the number of RRC
                   establishment failures by cause.
                
                   {{list| where each item is defined as the
                   \"cause name=measurement value\"}} The total
                   of all the measurements is provided using the
                   cause name= \"sum\".";
              }
              leaf SuccConnEstab {
                type string;
                description
                  "This measurement provides the number of
                   successful RRC establishments by cause.
                
                   {{list| where each item is defined as the
                   \"cause name=measurement value\"}} The total
                   of all the measurements is provided using the
                   cause name= \"sum\".";
              }
            }
          }
        }

        container RAB {
          config false;
          description
            "This object contains parameters relating to Radio
             Access layers {{bibref|3GPP-TS.32.405}}";
          leaf RABSuccEstabCS {
            type uint32;
            description
              "The number of successfully established RABs (with or
               without queueing) for CS domain.";
          }
          leaf RABFailEstabCS {
            type uint32;
            description
              "The number of RAB establishment failures for CS
               domain.";
          }
          leaf RABSuccEstabPS {
            type uint32;
            description
              "The number of successfully established RABs for PS
               domain.";
          }
          leaf RABFailEstabPS {
            type uint32;
            description
              "The number of RABs failed to establish for PS domain.";
          }
          leaf RABCSSetupTimeMean {
            type uint32;
            description
              "The mean time in {{units}} for a FAP to establish a
               RAB CS connection.
            
               This measurement is obtained by accumulating the
               time intervals for each successful RAB
               establishment between the receipt by the FAP of a
               RANAP \"RAB ASSIGNMENT REQUEST\" message to
               establish a RAB for CS domain, and the first
               corresponding (based on RAB ID) transmission by
               the FAP of a RANAP \"RAB ASSIGNMENT RESPONSE\"
               message for successfully established RABs over a
               granularity period (Sample Interval
               {{bibref|3GPP-TS.32.582|Section 6.3.2}}).
            
               This end value of the time will then be divided by
               the number of successfully established RABs
               observed in the granularity period to give the
               arithmetic mean.  The accumulator SHALL be
               reinitialized at the beginning of each granularity
               period.";
          }
          leaf RABCSSetupTimeMax {
            type uint32;
            description
              "The maximum time in {{units}} for a FAP to establish
               a RAB CS connection.
            
               This measurement is obtained by monitoring the
               time intervals for each successful RAB
               establishment between the receipt by the FAP of a
               RANAP \"RAB ASSIGNMENT REQUEST\" message to
               establish a RAB for CS domain, and the first
               corresponding (based on RAB ID) transmission by
               the FAP of a RANAP \"RAB ASSIGNMENT RESPONSE\"
               message for successfully established RABs.
            
               The high tide mark of this time will be stored in
               a gauge; the gauge SHALL be reinitialized at the
               beginning of each granularity period (Sample
               Interval {{bibref|3GPP-TS.32.582|Section 6.3.2}}).";
          }
          leaf RABPSSetupTimeMean {
            type uint32;
            description
              "The mean time in {{units}} for a FAP to establish a
               RAB PS connection.
            
               This measurement is obtained by accumulating the
               time intervals for each successful RAB
               establishment between the receipt by the FAP of a
               RANAP \"RAB ASSIGNMENT REQUEST\" message to
               establish a RAB for PS domain, and the first
               corresponding (based on RAB ID) transmission by
               the FAP of a RANAP \"RAB ASSIGNMENT RESPONSE\"
               message for successfully established RABs over a
               granularity period (Sample Interval
               {{bibref|3GPP-TS.32.582|Section 6.3.2}}).
            
               This end value of the time will then be divided by
               the number of successfully established RABs
               observed in the granularity period to give the
               arithmetic mean.  The accumulator SHALL be
               reinitialized at the beginning of each granularity
               period.";
          }
          leaf RABPSSetupTimeMax {
            type uint32;
            description
              "The maximum time in {{units}} for a FAP to establish
               a RAB PS connection.
            
               This measurement is obtained by monitoring the
               time intervals for each successful RAB
               establishment between the receipt by the FAP of a
               RANAP \"RAB ASSIGNMENT REQUEST\" message to
               establish a RAB for PS domain, and the first
               corresponding (based on RAB ID) transmission by
               the FAP of a RANAP \"RAB ASSIGNMENT RESPONSE\"
               message for successfully established RABs.
            
               The high tide mark of this time will be stored in
               a gauge; the gauge SHALL be reinitialized at the
               beginning of each granularity period (Sample
               Interval {{bibref|3GPP-TS.32.582|Section 6.3.2}}).";
          }
          leaf FailHO {
            type uint32;
            description
              "The number of failed Handovers.";
          }
          leaf SuccHO {
            type uint32;
            description
              "The number of successful Handovers.";
          }
        }
      }

      container LTE {
        description
          "This object contains parameters relating to configuring
           the LTE FAP.";

        list Tunnel {
          key "TunnelRef";
          description
            "This object contains a table of all tunnel instances
             configured for the LTE FAP.";
          leaf Enable {
            type boolean;
            default "false";
            description
              "Enables or disables this entry.";
          }
          leaf TunnelRef {
            type string {
              length "0..256";
            }
            description
              "This is the reference to an IPsec tunnel instance
               used by the LTE FAP.
            
               For all root data models, which use the tunnel
               definition provided in {{bibref|TR-262}}
               (InternetGatewayDevice:1 {{bibref|TR-098}} and
               Device:1 {{bibref|TR-181i1}}) the {{param}} MUST
               point to a row in the 'FAP.Tunnel.IKESA.{i}.'
               table, defined in {{bibref|TR-262}}.
            
               If the root data model used is Device:2
               {{bibref|TR-181i2}} than the {{param}} MUST point
               to IPsec tunnel instance defined in
               {{bibref|TR-181i2}}.
            
               If the referenced object is deleted, the parameter
               value MUST be set to an empty string.
            
               In case of a multiple-radio-technology FAP
               product, each radio technology can have its own
               tunnels or share common tunnels.  In the former
               case, {{param}} can contain a unique instance
               number.  In the latter case, {{param}} under all
               radio technologies can have the same instance
               number.";
          }
          leaf PLMNID {
            type string {
              length "0..256";
            }
            default "";
            description
              "{{list}} Optional list of PLMM IDs associated with
               the tunnel, which can be used for selecting the
               tunnel.
            
               Each PLMN ID consists of Mobile Country Code (MCC)
               and Mobile Network Code (MNC)
               {{bibref|3GPP-TS.23.003}},
               {{bibref|3GPP-TS.24.008}}.  Mobile Country Code
               consists of three digits and uniquely identifies
               the country of domicile of the subscriber.  Mobile
               Network Code consists of two or three digits and
               identifies the Home PLMN within a country.  For a
               2-digit MNC the total string length of {{param}}
               is 5.";
          }
        }

        container EPC {
          description
            "This object contains parameters relating to configuring
             LTE EPC.";
          leaf AllowedCipheringAlgorithmList {
            type enumeration {
              enum "EEA0";
              enum "128-EEA1";
              enum "128-EEA2";
            }
            description
              "{{list}} Each item is a ciphering algorithm allowed
               to be used for RRC and UP confidentiality
               protection as defined in
               {{bibref|3GPP-TS.33.401}}.  If the list contains
               more than 1 item, it is in the order of the
               preferred algorithm to be used.  {{enum}}";
          }
          leaf AllowedIntegrityProtectionAlgorithmList {
            type enumeration {
              enum "128-EIA1";
              enum "128-EIA2";
            }
            description
              "{{list}} Each item is a integrity protection
               algorithm allowed to be used for RRC as defined in
               {{bibref|3GPP-TS.33.401}}.  If the list contains
               more than 1 item, it is in the order of the
               preferred algorithm to be used.  {{enum}}";
          }
          leaf TAC {
            type uint32 {
              range "0..65535";
            }
            description
              "TAC (Tracking Area Code) for LTE FAP as specified in
               SystemInformationBlockType1 message in
               {{bibref|3GPP-TS.36.331|Section 6.2.2}}.";
          }
          leaf EAID {
            type uint32 {
              range "0..16777216";
            }
            description
              "Emergency Area ID that uniquely identifies the area
               of emergency for Earthquake and Tsunami Warning
               Services (ETWS).  Corresponds to Emergency Area ID
               in {{bibref|3GPP-TS.36.413|Section 9.2.1.47}}.";
          }
          leaf MaxPLMNListEntries {
            type uint32;
            config false;
            description
              "The maximum number of entries available in the
               {{object|.CellConfig.LTE.EPC.PLMNList.{i}.}}
               table.";
          }
          leaf MaxQoSEntries {
            type uint32;
            config false;
            description
              "The maximum number of entries in the
               {{object|.CellConfig.LTE.EPC.QoS.{i}.}} table.";
          }

          list PLMNList {
            key "PLMNID";
            min-elements 1;
            max-elements 6;
            description
              "This object contains parameters relating to list of
               PLMN identity specific to LTE EPC definition,
               called PLMN-IdentityList, as specified in
               SystemInformationBlockType1 message in
               {{bibref|3GPP-TS.36.331|Section 6.2.2}}.  Each
               instance in this object is a PLMN-IdentityInfo
               which consists of plmn-Identity and
               cellReservedForOperatorUse IEs.  At minimum 1 item
               MUST be present in this list, and maximum of 6
               items.";
            leaf Enable {
              type boolean;
              default "false";
              description
                "Enables or disables this entry.";
            }
            leaf IsPrimary {
              type boolean;
              default "false";
              description
                "Indicates whether this {{param|PLMNID}} is a
                 primary PLMN or not.  If there is more than one
                 instance in
                 {{object|.CellConfig.LTE.EPC.PLMNList.{i}.}}
                 table, then ACS MUST set this {{param}} set to
                 {{true}} in only one instance.";
            }
            leaf PLMNID {
              type string {
                length "0..6";
              }
              default "";
              description
                "PLMN ID consists of Mobile Country Code (MCC) and
                 Mobile Network Code (MNC)
                 {{bibref|3GPP-TS.23.003}},
                 {{bibref|3GPP-TS.24.008}}.
              
                 Mobile Country Code consists of three digits and
                 uniquely identifies the country of domicile of
                 the subscriber.  Mobile Network Code consists of
                 two or three digits and identifies the Home PLMN
                 within a country.  For a 2-digit MNC the total
                 string length of {{param}} is 5.";
            }
            leaf CellReservedForOperatorUse {
              type boolean;
              default "false";
              description
                "Indicates whether the cell is reserved for operator
                 use or not.  If {{true}}, it is reserved.  If
                 {{false}}, it is not reserved.  Corresponds to
                 \"reserved\" \"notReserved\" respectively as
                 defined in PLMN-IdentityInfo in
                 {{bibref|3GPP-TS.36.331|Section 6.2.2}}.";
            }
          }

          list QoS {
            key "QCI";
            description
              "This object contains parameters relating to
               configuring QoS in LTE EPC.";
            leaf Enable {
              type boolean;
              default "false";
              description
                "Enables or disables this entry.";
            }
            leaf QCI {
              type uint32 {
                range "1..20";
              }
              default "1";
              description
                "QoS class identity as defined in
                 {{bibref|3GPP-TS.23.203|Section 6.1.7.2}}.";
            }
            leaf Type {
              type enumeration {
                enum "GBR";
                enum "Non-GBR";
              }
              default "Non-GBR";
              description
                "Defines the type of the QoS class as defined in
                 {{bibref|3GPP-TS.23.203|Section 6.1.7.2}}.";
            }
            leaf Priority {
              type uint32 {
                range "1..20";
              }
              default "1";
              description
                "Priority of the QoS class as defined in
                 {{bibref|3GPP-TS.23.203|Section 6.1.7.2}}.";
            }
            leaf PacketDelayBudget {
              type uint32 {
                range "50 | 100 | 150 | 200 | 300 | 400 | 500 | 600 | 700 | 800 | 900 | 1000 | 1500 | 2000";
              }
              default "50";
              description
                "Defines the Packet delay budget, specified in
                 {{units}}, as defined in
                 {{bibref|3GPP-TS.23.203|Section 6.1.7.2}}.";
            }
          }

          container HO {
            config false;
            description
              "This object provides monitoring of the Handover (HO)
               properties in the HeNB.";

            container Stats {
              description
                "This object provides the HO statistics as defined
                 in {{bibref|3GPP-TS.32.453}}.";
              leaf ToeNBAtt {
                type string;
                description
                  "This measurement provides the number of attempted
                   outbound handover to HeNB by handover cause.
                
                   {{list| where each item is defined as the
                   \"cause name=measurement value\"}} The total
                   of all the measurements is provided using the
                   name= \"sum\".";
              }
              leaf ToeNBSucc {
                type string;
                description
                  "This measurement provides the number of
                   successful outbound handover to HeNB by
                   handover cause.
                
                   {{list| where each item is defined as the
                   \"cause name=measurement value\"}} The total
                   of all the measurements is provided using the
                   name= \"sum\".";
              }
              leaf ToeNBFail {
                type string;
                description
                  "This measurement provides the number of failed
                   outbound handover to HeNB by handover cause.
                
                   {{list| where each item is defined as the
                   \"cause name=measurement value\"}} The total
                   of all the measurements is provided using the
                   name= \"sum\".";
              }
              leaf FromeNBAtt {
                type string;
                description
                  "This measurement provides the number of attempted
                   inbound handover from HeNB by handover cause.
                
                   {{list| where each item is defined as the
                   \"cause name=measurement value\"}} The total
                   of all the measurements is provided using the
                   name= \"sum\".";
              }
              leaf FromeNBSucc {
                type string;
                description
                  "This measurement provides the number of
                   successful inbound handover from HeNB by
                   handover cause.
                
                   {{list| where each item is defined as the
                   \"cause name=measurement value\"}} The total
                   of all the measurements is provided using the
                   name= \"sum\".";
              }
              leaf FromeNBFail {
                type string;
                description
                  "This measurement provides the number of failed
                   inbound handover from HeNB by handover cause.
                
                   {{list| where each item is defined as the
                   \"cause name=measurement value\"}} The total
                   of all the measurements is provided using the
                   name= \"sum\".";
              }
              leaf ToUtranAtt {
                type string;
                description
                  "This measurement provides the number of attempted
                   outbound handover to Utran by handover cause.
                
                   {{list| where each item is defined as the
                   \"cause name=measurement value\"}} The total
                   of all the measurements is provided using the
                   name= \"sum\".";
              }
              leaf ToUtranSucc {
                type string;
                description
                  "This measurement provides the number of
                   successful outbound handover to Utran by
                   handover cause.
                
                   {{list| where each item is defined as the
                   \"cause name=measurement value\"}} The total
                   of all the measurements is provided using the
                   name= \"sum\".";
              }
              leaf ToUtranFail {
                type string;
                description
                  "This measurement provides the number of failed
                   outbound handover to Utran by handover cause.
                
                   {{list| where each item is defined as the
                   \"cause name=measurement value\"}} The total
                   of all the measurements is provided using the
                   name= \"sum\".";
              }
              leaf ToGeranAtt {
                type string;
                description
                  "This measurement provides the number of attempted
                   outbound handover to Geran by handover cause.
                
                   {{list| where each item is defined as the
                   \"cause name=measurement value\"}} The total
                   of all the measurements is provided using the
                   name= \"sum\".";
              }
              leaf ToGeranSucc {
                type string;
                description
                  "This measurement provides the number of
                   successful outbound handover to Geran by
                   handover cause.
                
                   {{list| where each item is defined as the
                   \"cause name=measurement value\"}} The total
                   of all the measurements is provided using the
                   name= \"sum\".";
              }
              leaf ToGeranFail {
                type string;
                description
                  "This measurement provides the number of failed
                   outbound handover to Geran by handover cause.
                
                   {{list| where each item is defined as the
                   \"cause name=measurement value\"}} The total
                   of all the measurements is provided using the
                   name= \"sum\".";
              }
            }
          }
        }

        container RAN {
          description
            "This object contains parameters relating to the LTE RAN
             level configuration.";

          container Common {
            description
              "This object contains parameters relating to the
               common configuration in LTE RAN.";
            leaf CellIdentity {
              type uint32 {
                range "0..268435455";
              }
              description
                "Cell Identity as specified in
                 {{bibref|3GPP-TS.36.331|Section 6.3.4}}.";
            }
          }

          container S1AP {
            description
              "This object contains parameters relating to the S1AP
               configuration.";
            leaf TRelocPrep {
              type string;
              description
                "{{list}} Each item is a maximum time for the
                 Handover Preparation procedure in the source LTE
                 FAP, specified in seconds, with a numeric range
                 between 0 and 300 inclusive.  Only values in
                 multiple of 5 are valid; use of other values
                 within the defined range MUST be rejected by the
                 CPE.  In case there is more than one item in the
                 list, the first item contains the most preferred
                 value.  The value of {{param}} divided by 10
                 yields the actual value.
              
                 The timer is started when the LTE FAP sends the
                 HANDOVER REQUIRED message.  Upon reception of
                 the HANDOVER COMMAND message the LTE FAP shall
                 stop the timer.  Corresponds to parameter
                 TS1RELOCprep defined in
                 {{bibref|3GPP-TS.36.413|Section 8.4.1.2}}.
              
                 The multiplicity of the {{param}} values can
                 also be expressed by defining a range using
                 \"..\" (two periods) between two values.  In
                 this case, the combination of two values defines
                 the lower-bound and upper-bound of the range
                 inclusive.  If this notation is used, then the
                 list contains at least 2 items:
                 \"<preferred-value>,<lower-bound>..<upper-bound>\".
              
                 If the LTE FAP supports self-configuration
                 capability for {{param}} and more than one item
                 is configured, then the LTE FAP is expected to
                 select one from the list and overwrite this
                 parameter containing only the one selected.  If
                 the LTE FAP does not support self-configuration
                 capability for {{param}} and more than one item
                 is configured, then the LTE FAP accepts the
                 first value and ignore the rest.  If only one
                 item is configured regardless of the
                 self-configuration capability of LTE FAP, LTE
                 FAP accepts the value as an explicit
                 configuration by the ACS.";
            }
            leaf TRelocOverall {
              type string;
              description
                "{{list}} Each item is a maximum time for the
                 protection of the overall handover procedure in
                 the source LTE FAP, specified in seconds, with a
                 numeric range between 0 and 300 inclusive.  Only
                 values in multiple of 5 are valid; use of other
                 values within the defined range MUST be rejected
                 by the CPE.  In case there is more than one item
                 in the list, the first item contains the most
                 preferred value.  The value of {{param}} divided
                 by 10 yields the actual value.
              
                 The timer is started reception of the HANDOVER
                 COMMAND message.  Corresponds to parameter
                 TS1RELOCOverall defined in
                 {{bibref|3GPP-TS.36.413|Section 8.4.1.2}}.
              
                 The multiplicity of the {{param}} values can
                 also be expressed by defining a range using
                 \"..\" (two periods) between two values.  In
                 this case, the combination of two values defines
                 the lower-bound and upper-bound of the range
                 inclusive.  If this notation is used, then the
                 list contains at least 2 items:
                 \"<preferred-value>,<lower-bound>..<upper-bound>\".
              
                 If LTE FAP supports self-configuration
                 capability for {{param}} and more than one item
                 is configured, then LTE FAP is expected to
                 select one from the list and overwrite this
                 parameter containing only the one selected.  If
                 LTE FAP does not support self-configuration
                 capability for {{param}} and more than one item
                 is configured, then LTE FAP accepts the first
                 value and ignore the rest.  If only one item is
                 configured regardless of the self-configuration
                 capability of LTE FAP, LTE FAP accepts the value
                 as an explicit configuration by the ACS.";
            }
          }

          container S1U {
            description
              "This object contains parameters relating to the S1-U
               configuration.";
            leaf GTPUEchoInterval {
              type uint32 {
                range "0 | 60..max";
              }
              description
                "Defines the interval in {{units}} between each
                 GTP-U Echo Request that LTE FAP sends to the
                 GTP-U peer, as specified in
                 {{bibref|3GPP-TS.29.281|Section 7.2.1}}.  If the
                 value of {{param}} is equal to 0, then this
                 functionality is supressed and thus LTE FAP does
                 not send GTP-U Echo Request.  If there is no
                 GTP-U path in use, then no Echo Request is sent
                 regardless of the value of {{param}}.";
            }
          }

          container RF {
            description
              "This object contains parameters relating to the RF,
               see {{bibref|3GPP-TS.32.592|Section 6.1.7.1}}.";
            leaf EARFCNDL {
              type uint32 {
                range "0..65535";
              }
              description
                "{{list}} Each item is an E-UTRA Absolute Radio
                 Frequency Channel Number in the downlink
                 direction.  In case there is more than one item
                 in the list, the first item contains the most
                 preferred value.  Corresponds to parameter NDL
                 specified in {{bibref|3GPP-TS.36.104|Table
                 5.7.3.1}}.
              
                 If LTE FAP supports self-configuration
                 capability for {{param}} and more than one item
                 is configured, then LTE FAP is expected to
                 select one from the list and overwrite this
                 parameter containing only the one selected.  If
                 LTE FAP does not support self-configuration
                 capability for {{param}} and more than one item
                 is configured, then LTE FAP accepts the first
                 value and ignore the rest.  If only one item is
                 configured regardless of the self-configuration
                 capability of LTE FAP, LTE FAP accepts the value
                 as an explicit configuration by the ACS.";
            }
            leaf EARFCNUL {
              type uint32 {
                range "0..65535";
              }
              description
                "{{list}} Each item is an E-UTRA Absolute Radio
                 Frequency Channel Number in the uplink
                 direction.  In case there is more than one item
                 in the list, the first item contains the most
                 preferred value.  Corresponds to parameter NUL
                 specified in {{bibref|3GPP-TS.36.104|Table
                 5.7.3.1}}.
              
                 If LTE FAP supports self-configuration
                 capability for {{param}} and more than one item
                 is configured, then LTE FAP is expected to
                 select one from the list and overwrite this
                 parameter containing only the one selected.  If
                 LTE FAP does not support self-configuration
                 capability for {{param}} and more than one item
                 is configured, then LTE FAP accepts the first
                 value and ignore the rest.  If only one item is
                 configured regardless of the self-configuration
                 capability of LTE FAP, LTE FAP accepts the value
                 as an explicit configuration by the ACS.";
            }
            leaf FreqBandIndicator {
              type uint32 {
                range "1..40";
              }
              description
                "Frequency band indicator.  Corresponds to parameter
                 freqBandIndicator in SIB1 in
                 {{bibref|3GPP-TS.36.331|Section 6.2.2}}.";
            }
            leaf DLBandwidth {
              type uint32 {
                range "6 | 15 | 25 | 50 | 75 | 100";
              }
              description
                "{{list}} Each item is a downlink transmission
                 bandwidth, specified in number of Resource
                 Blocks.  In case there is more than one item in
                 the list, the first item contains the most
                 preferred value.  Corresponds to parameter
                 dl_Bandwidth in MIB (Master Information Block)
                 in {{bibref|3GPP-TS.36.331|Section 6.2.2}}.  and
                 to parameter NRB in
                 {{bibref|3GPP-TS.36.101|Table 5.6-1}}.
              
                 If LTE FAP supports self-configuration
                 capability for {{param}} and more than one item
                 is configured, then LTE FAP is expected to
                 select one from the list and overwrite this
                 parameter containing only the one selected.  If
                 LTE FAP does not support self-configuration
                 capability for {{param}} and more than one item
                 is configured, then LTE FAP accepts the first
                 value and ignore the rest.  If only one item is
                 configured regardless of the self-configuration
                 capability of LTE FAP, LTE FAP accepts the value
                 as an explicit configuration by the ACS.";
            }
            leaf ULBandwidth {
              type uint32 {
                range "6 | 15 | 25 | 50 | 75 | 100";
              }
              description
                "{{list}} Each item is an uplink transmission
                 bandwidth, specified in number of Resource
                 Blocks.  In case there is more than one item in
                 the list, the first item contains the most
                 preferred value.  Corresponds to parameter
                 ul_Bandwidth in SIB2 in
                 {{bibref|3GPP-TS.36.331|Section 6.3.1}}.  and to
                 parameter NRB in {{bibref|3GPP-TS.36.101|Table
                 5.6-1}}.
              
                 If LTE FAP supports self-configuration
                 capability for {{param}} and more than one item
                 is configured, then LTE FAP is expected to
                 select one from the list and overwrite this
                 parameter containing only the one selected.  If
                 LTE FAP does not support self-configuration
                 capability for {{param}} and more than one item
                 is configured, then LTE FAP accepts the first
                 value and ignore the rest.  If only one item is
                 configured regardless of the self-configuration
                 capability of LTE FAP, LTE FAP accepts the value
                 as an explicit configuration by the ACS.";
            }
            leaf ReferenceSignalPower {
              type string;
              description
                "{{list}} Each item is a downlink reference-signal
                 transmit power, specified in dBm, with a numeric
                 range between -60 and 50 inclusive.  In case
                 there is more than one item in the list, the
                 first item contains the most preferred value.
                 Defined as the linear average over the power
                 contributions (in W) of all resource elements
                 that carry cell-specific reference signals
                 within the operating system bandwidth.
                 Corresponds to parameter referenceSignalPower in
                 PDSCH-Config IE in
                 {{bibref|3GPP-TS.36.331|Section 6.3.2}}.
              
                 The multiplicity of the {{param}} values can
                 also be expressed by defining a range using
                 \"..\" (two periods) between two values.  In
                 this case, the combination of two values defines
                 the lower-bound and upper-bound of the range
                 inclusive.  If this notation is used, then the
                 list contains at least 2 items:
                 \"<preferred-value>,<lower-bound>..<upper-bound>\".
              
                 If LTE FAP supports self-configuration
                 capability for {{param}} and more than one item
                 is configured, then LTE FAP is expected to
                 select one from the list and overwrite this
                 parameter containing only the one selected.  If
                 LTE FAP does not support self-configuration
                 capability for {{param}} and more than one item
                 is configured, then LTE FAP accepts the first
                 value and ignore the rest.  If only one item is
                 configured regardless of the self-configuration
                 capability of LTE FAP, LTE FAP accepts the value
                 as an explicit configuration by the ACS.";
            }
            leaf PhyCellID {
              type string;
              description
                "{{list}} Each item is a physical cell ID with a
                 numeric range between 0 and 503 inclusive.
                 Represents the list of physical cell identities
                 LTE FAP to choose from.  In case there is more
                 than one item in the list, the first item
                 contains the most preferred value.  As specified
                 in {{bibref|3GPP-TS.36.211|Section 6.11}}.
              
                 The multiplicity of the {{param}} values can
                 also be expressed by defining a range using
                 \"..\" (two periods) between two values.  In
                 this case, the combination of two values defines
                 the lower-bound and upper-bound of the range
                 inclusive.  If this notation is used, then the
                 list contains at least 2 items:
                 \"<preferred-value>,<lower-bound>..<upper-bound>\".
              
                 If LTE FAP supports self-configuration
                 capability for {{param}} and more than one item
                 is configured, then LTE FAP is expected to
                 select one from the list and overwrite this
                 parameter containing only the one selected.  If
                 LTE FAP does not support self-configuration
                 capability for {{param}} and more than one item
                 is configured, then accepts the first value and
                 ignore the rest.  If only one item is configured
                 regardless of the self-configuration capability
                 of , accepts the value as an explicit
                 configuration by the ACS.";
            }
            leaf PSCHPowerOffset {
              type string;
              description
                "{{list}} Each item is a power offset, specified in
                 dB, of the Primary Synchronization Channel with
                 respect to the ReferenceSignalPower, with a
                 numeric range between -350 and 150 inclusive.
                 In case there is more than one item in the list,
                 the first item contains the most preferred
                 value.  The value of {{param}} divided by 10
                 yields the actual value.
              
                 The multiplicity of the {{param}} values can
                 also be expressed by defining a range using
                 \"..\" (two periods) between two values.  In
                 this case, the combination of two values defines
                 the lower-bound and upper-bound of the range
                 inclusive.  If this notation is used, then the
                 list contains at least 2 items:
                 \"<preferred-value>,<lower-bound>..<upper-bound>\".
              
                 If supports self-configuration capability for
                 {{param}} and more than one item is configured,
                 then is expected to select one from the list and
                 overwrite this parameter containing only the one
                 selected.  If does not support
                 self-configuration capability for {{param}} and
                 more than one item is configured, then accepts
                 the first value and ignore the rest.  If only
                 one item is configured regardless of the
                 self-configuration capability of , accepts the
                 value as an explicit configuration by the ACS.";
            }
            leaf SSCHPowerOffset {
              type string;
              description
                "{{list}} Each item is a power offset, specified in
                 dB, of the Secondary Synchronization Channel
                 with respect to the ReferenceSignalPower, with a
                 numeric range between -350 and 150 inclusive.
                 In case there is more than one item in the list,
                 the first item contains the most preferred
                 value.  The value of {{param}} divided by 10
                 yields the actual value.
              
                 The multiplicity of the {{param}} values can
                 also be expressed by defining a range using
                 \"..\" (two periods) between two values.  In
                 this case, the combination of two values defines
                 the lower-bound and upper-bound of the range
                 inclusive.  If this notation is used, then the
                 list contains at least 2 items:
                 \"<preferred-value>,<lower-bound>..<upper-bound>\".
              
                 If supports self-configuration capability for
                 {{param}} and more than one item is configured,
                 then is expected to select one from the list and
                 overwrite this parameter containing only the one
                 selected.  If does not support
                 self-configuration capability for {{param}} and
                 more than one item is configured, then accepts
                 the first value and ignore the rest.  If only
                 one item is configured regardless of the
                 self-configuration capability of , accepts the
                 value as an explicit configuration by the ACS.";
            }
            leaf PBCHPowerOffset {
              type string;
              description
                "{{list}} Each item is a power offset, specified in
                 dB, of the Physical Broadcast Channel with
                 respect to the ReferenceSignalPower, with a
                 numeric range between -350 and 150 inclusive.
                 In case there is more than one item in the list,
                 the first item contains the most preferred
                 value.  The value of {{param}} divided by 10
                 yields the actual value.
              
                 The multiplicity of the {{param}} values can
                 also be expressed by defining a range using
                 \"..\" (two periods) between two values.  In
                 this case, the combination of two values defines
                 the lower-bound and upper-bound of the range
                 inclusive.  If this notation is used, then the
                 list contains at least 2 items:
                 \"<preferred-value>,<lower-bound>..<upper-bound>\".
              
                 If supports self-configuration capability for
                 {{param}} and more than one item is configured,
                 then is expected to select one from the list and
                 overwrite this parameter containing only the one
                 selected.  If does not support
                 self-configuration capability for {{param}} and
                 more than one item is configured, then accepts
                 the first value and ignore the rest.  If only
                 one item is configured regardless of the
                 self-configuration capability of , accepts the
                 value as an explicit configuration by the ACS.";
            }
          }

          container PHY {
            description
              "This object contains parameters relating to the
               physical layer level configuration.";

            container AntennaInfo {
              config false;
              description
                "This object contains parameters relating to the
                 antenna configuration (see
                 {{bibref|3GPP-TS.32.592|Section 6.1.1.1}}).";
              leaf AntennaPortsCount {
                type uint32 {
                  range "1 | 2 | 4";
                }
                description
                  "Defines the number of cell specific antenna ports
                   according to {{bibref|3GPP-TS.36.211|Section
                   6.2.1}}.  A UE in IDLE mode acquires the
                   information about the number of transmit
                   antenna ports according to
                   {{bibref|3GPP-TS.36.212|Section 5.3.1.1}}.
                   Corresponds to antennaPortsCount IE specified
                   in {{bibref|3GPP-TS.36.331|Section 6.3.2}}.";
              }
            }

            container PDSCH {
              description
                "This object contains parameters relating to the
                 PDSCH (Physical Downlink Shared Channel)
                 configuration (see
                 {{bibref|3GPP-TS.32.592|Section 6.1.1.2}}).";
              leaf Pb {
                type string;
                description
                  "{{list}} Each item is a Eb/Ea value with a
                   numeric range between 0 and 3 inclusive.  In
                   case there is more than one item in the list,
                   the first item contains the most preferred
                   value.  The value of this parameter is the
                   same for all UEs in the cell.  Eb repsents
                   EPRE of PDSCH REs type B, i.e.  REs in OFDM
                   symbols that include reference symbols, as
                   specified in {{bibref|3GPP-TS.36.213|Section
                   5.2}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf Pa {
                type int32 {
                  range "-600 | -477 | -300 | -177 | 0 | 100 | 200 | 300";
                }
                description
                  "{{list}} Each item is a Ea/Ers value.  In case
                   there is more than one item in the list, the
                   first item contains the most preferred value.
                   Ea represents EPRE of PDSCH REs type A, i.e.
                   REs in OFDM symbols that do not include
                   reference symbols.  Ers represents EPRE of
                   reference symbols REs.  Specified in
                   {{bibref|3GPP-TS.36.213|Section 5.2}}.  Actual
                   values of range are -6.00 to 3.00dB.  The
                   value of each item in {{param}} divided by 100
                   yields the actual value.
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
            }

            container SRS {
              description
                "This object contains parameters relating to the UL
                 SRS (Sounding Reference Signal) configuration
                 (see {{bibref|3GPP-TS.32.592|Section 6.1.1.3}}).";
              leaf SRSEnabled {
                type boolean;
                description
                  "Indicates whether UL SRS (Sounding RS) is enabled
                   or not.
                
                   If {{true}}, UL Sounding RS is enabled.  If
                   {{false}}, UL Sounding RS is disabled.
                
                   Corresponds to SoundingRS-UL-ConfigCommonIE
                   defined in {{bibref|3GPP-TS.36.331|Section
                   6.3.2}}.";
              }
              leaf SRSBandwidthConfig {
                type string;
                description
                  "{{list}} Each item is a index into tables of cell
                   specific SRS Bandwidth Configuration, with a
                   numeric range between 0 and 7 inclusive.  In
                   case there is more than one item in the list,
                   the first item contains the most preferred
                   value.  SRS Bandwidth Configuration tables are
                   specified in {{bibref|3GPP-TS.36.211|Table
                   5.5.3.2-1, 5.5.3.2-2, 5.5.3.2-3 and 5.5.3.2–
                   4}}.  Corresponds to srs-BandwidthConfig IE
                   specified in {{bibref|3GPP-TS.36.331|Section
                   6.3.2}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf SRSMaxUpPTS {
                type boolean;
                description
                  "Defines whether reconfiguration of SRS applies to
                   UpPTS or not.
                
                   If {{true}}, SRS applies to UpPTS.  If
                   {{false}}, SRS does not apply to UpPTS.
                
                   Corresponds to srs-MaxUpPts specified in
                   {{bibref|3GPP-TS.36.331|Section 6.3.2}} and
                   srsMaxUpPts specified in
                   {{bibref|3GPP-TS.36.211|Section 5.5.3.2}}.
                
                   This parameter is applicable to TDD mode only.";
              }
              leaf AckNackSRSSimultaneousTransmission {
                type boolean;
                description
                  "Defines whether a UE can simultaneously transmit
                   SRS and HARQ ACK/NACK or not.
                
                   If {{true}}, simultaneous transmission is
                   allowed.  If {{false}}, simultaneous
                   transmission is not allowed.
                
                   Corresponds to
                   ackNackSRS-SimultaneousTransmission specfied
                   in {{bibref|3GPP-TS.36.331|Section 6.3.2}} and
                   Simultaneous-AN-and-SRS specified in
                   {{bibref|3GPP-TS.36.213|Section 8.2}}.";
              }
            }

            container PRACH {
              description
                "This object contains parameters relating to the
                 PRACH (Physical Random Access Channel)
                 configuration (see
                 {{bibref|3GPP-TS.32.592|Section 6.1.1.4}}).";
              leaf RootSequenceIndex {
                type string;
                description
                  "{{list}} Each item is a Logical root sequence
                   index with a numeric range between 0 and 837
                   inclusive.  In case there is more than one
                   item in the list, the first item contains the
                   most preferred value.  Logical root sequence
                   index is used to determine 64 physical RACH
                   preamble sequences available in the cell.
                   Corresponds to RACH_ROOT_SEQUENCE parameter
                   defined in {{bibref|3GPP-TS.36.331|Section
                   6.3.2}} and {{bibref|3GPP-TS.36.211|Section
                   5.7.2}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf ConfigurationIndex {
                type string;
                description
                  "{{list}} Each item is an index to the table
                   defining PRACH resources within the frame with
                   a numeric range between 0 and 63 inclusive.
                   In case there is more than one item in the
                   list, the first item contains the most
                   preferred value.  Corresponds to
                   PRACH-Configuration-Index parameter defined in
                   {{bibref|3GPP-TS.36.331|Section 6.3.2}} and
                   {{bibref|3GPP-TS.36.211|Section 5.7.1}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf HighSpeedFlag {
                type boolean;
                description
                  "Indicates whether restricted set or unrestricted
                   set of preambles is used.
                
                   If {{true}}, indicates restricted set.  If
                   {{false}}, indicates unrestricted set.
                
                   Corresponds to highSpeedFlag parameter defined
                   in {{bibref|3GPP-TS.36.331|Section 6.3.2}} and
                   high-speed-flag parameter defined in
                   {{bibref|3GPP-TS.36.211|Section 5.7.2}}.";
              }
              leaf ZeroCorrelationZoneConfig {
                type string;
                description
                  "{{list}} Each item is a value used for preamble
                   sequence generation with a numeric range
                   between 0 and 15 inclusive.  In case there is
                   more than one item in the list, the first item
                   contains the most preferred value.  Each item
                   corresponds to zeroCorrelationZoneConfig
                   parameter defined in
                   {{bibref|3GPP-TS.36.331|Section 6.3.2}} and to
                   NCS parameter defined in
                   {{bibref|3GPP-TS.36.211|Section 5.7.2}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf FreqOffset {
                type string;
                description
                  "{{list}} Each item represents the first available
                   physical resource block number for PRACH.  In
                   case there is more than one item in the list,
                   the first item contains the most preferred
                   value.  Corresponds to prach-FreqOffset
                   parameter defined in
                   {{bibref|3GPP-TS.36.331|Section 6.3.2}} and
                   nPRBoffsetRA parameter defined
                   {{bibref|3GPP-TS.36.211|Section 5.7.1}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
            }

            container PUCCH {
              description
                "This object contains parameters relating to the
                 PUCCH (Physical Uplink Control Channel)
                 configuration.  (see
                 {{bibref|3GPP-TS.32.592|Section 6.1.1.5}})";
              leaf DeltaPUCCHShift {
                type enumeration {
                  enum "ds1";
                  enum "ds2";
                  enum "ds3";
                }
                description
                  "Defines the cyclic shift used for PUCCH formats
                   1/1a/1b in a resource block used for a mix of
                   formats 1/1a/1b and 2/2a/2b.
                
                   It is an integer multiple of deltaPUCCHShift
                   within the range of {0, 1, ., 7} .
                
                   Corresponds to deltaPUCCH-Shift parameter
                   defined in {{bibref|3GPP-TS.36.331|Section
                   6.3.2}} and Delta-shiftPUCCH parameter defined
                   {{bibref|3GPP-TS.36.211|Section 5.4}}.";
              }
              leaf NRBCQI {
                type string;
                description
                  "{{list}} Each item is a value that defines the
                   bandwidth in terms of resource blocks
                   available for use by PUCCH formats 2/2a/2b
                   transmission in each slot, with a numeric
                   range between 0 and 98 inclusive.  In case
                   there is more than one item in the list, the
                   first item contains the most preferred value.
                   Corresponds to nRB-CQI parameter defined in
                   {{bibref|3GPP-TS.36.331|Section 6.3.2}} and
                   NRB(2) parameter defined
                   {{bibref|3GPP-TS.36.211|Section 5.4}}.
                
                   The multiplicity of the {{param}} values can
                   also be expressed by defining a range using
                   \"..\" (two periods) between two values.  In
                   this case, the combination of two values
                   defines the lower-bound and upper-bound of the
                   range inclusive.If this notation is used, then
                   the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf NCSAN {
                type uint32 {
                  range "0..7";
                }
                config false;
                description
                  "Defines the number of cyclic shift used for PUCCH
                   formats 1/1a/1b in a resource block used for a
                   mix of formats 1/1a/1b and 2/2a/2b.
                
                   The value is an integer multiple of
                   deltaPUCCHShift within the range of {0, 1, .,
                   7}.
                
                   Corresponds to nCS-AN parameter defined in
                   {{bibref|3GPP-TS.36.331|Section 6.3.2}} and
                   NRB(1) parameter defined
                   {{bibref|3GPP-TS.36.211|Section 5.4}}.";
              }
              leaf N1PUCCHAN {
                type string;
                description
                  "{{list}} Each item is a value that determines
                   resources used for transmission of PUCCH
                   format 1/1a/1b and 2/2a/2b, with a numeric
                   range between 0 and 2047 inclusive.  In case
                   there is more than one item in the list, the
                   first item contains the most preferred value.
                   Corresponds to n1PUCCH-AN parameter defined in
                   {{bibref|3GPP-TS.36.331|Section 6.3.2}} and
                   NPUCCH(1) parameter defined
                   {{bibref|3GPP-TS.36.213|Section 10.1}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf CQIPUCCHResourceIndex {
                type string;
                description
                  "{{list}} Each item is a value that indicates the
                   position of PUCCH, with a numeric range
                   between 0 and 1185 inclusive.  In case there
                   is more than one item in the list, the first
                   item contains the most preferred value.  .
                   Corresponds to the cqi-PUCCH-ResourceIndex IE
                   specified in {{bibref|3GPP-TS.36.331|Section
                   6.3.2}}.  and to parameter nPUCCH(2) specified
                   in {{bibref|3GPP-TS.36.213|Section 7.2}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf K {
                type uint32 {
                  range "1..4";
                }
                config false;
                description
                  "Sub-band size for sub-band reporting mode
                   expressed in units of physical {{units}}, see
                   {{bibref|3GPP-TS.36.213|Section 7.2.2}}.
                
                   This parameter corresponds to the K IE
                   specified in {{bibref|3GPP-TS.36.331|Section
                   6.3.2}}.";
              }
            }

            container PUSCH {
              description
                "This object contains parameters relating to the
                 PUSCH (Physical Uplink Shared Channel)
                 configuration (see
                 {{bibref|3GPP-TS.32.592|Section 6.1.1.6}}).";
              leaf NSB {
                type uint32 {
                  range "1..4";
                }
                description
                  "Defines the number of sub-bands.  This parameter
                   corresponds to n-SB parameter specified in
                   {{bibref|3GPP-TS.36.331|Section 6.3.2}} and
                   NSB parameter specified in
                   {{bibref|3GPP-TS.36.211|Section 5.3.4}}.";
              }
              leaf HoppingMode {
                type enumeration {
                  enum "InterSubFrame";
                  enum "IntraAndInterSubFrame";
                }
                description
                  "Indicates if hopping is \"inter-subframe\" or
                   \"intra and inter-subframe\".  Corresponds to
                   hoppingMode parameter specified in
                   {{bibref|3GPP-TS.36.331|Section 6.3.2}} and
                   Hopping-mode parameter specified in
                   {{bibref|3GPP-TS.36.211|Section 5.3.4}}.";
              }
              leaf HoppingOffset {
                type string;
                description
                  "{{list}} Each item is a value to compute the set
                   of physical resource blocks to be used for
                   transmission on PUSCH if uplink frequency
                   hopping mode is enabled, with a numeric range
                   between 0 and 98 inclusive.  In case there is
                   more than one item in the list, the first item
                   contains the most preferred value.  This
                   parameter corresponds to pusch-HoppingOffset
                   parameter specified in
                   {{bibref|3GPP-TS.36.331|Section 6.3.2}} and
                   NRBHO parameter specified in
                   {{bibref|3GPP-TS.36.211|Section 5.3.4}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf Enable64QAM {
                type boolean;
                config false;
                description
                  "Indicates whether 64QAM is allowed or not.  If
                   {{true}}, 64QAM is allowed.  If {{false}},
                   64QAM is not allowed.
                
                   Corresponds to enable64QAM parameter specified
                   in {{bibref|3GPP-TS.36.331|Section 6.3.2}}.";
              }

              container ULRS {
                description
                  "This object contains parameters relating to the
                   ULRS (Uplink Reference Signal) of PUSCH
                   (Physical Uplink Shared Channel) configuration
                   (see {{bibref|3GPP-TS.32.592|Section
                   6.1.1.6.1}}).";
                leaf GroupHoppingEnabled {
                  type boolean;
                  description
                    "Indicates whether group hopping is enabled or
                     not.  If {{true}}, group hopping is enabled.
                     If {{false}}, group hopping is not enabled.
                  
                     Corresponds to groupHoppingEnabled parameter
                     specified in {{bibref|3GPP-TS.36.331|Section
                     6.3.2}}.and in
                     {{bibref|3GPP-TS.36.211|Section 5.5.1.3}}.";
                }
                leaf GroupAssignmentPUSCH {
                  type uint32 {
                    range "0..29";
                  }
                  config false;
                  description
                    "Corresponds to parameter groupAssignmentPUSCH
                     specified in {{bibref|3GPP-TS.36.331|Section
                     6.3.2}}.";
                }
                leaf SequenceHoppingEnabled {
                  type boolean;
                  description
                    "Indicates whether sequence hopping is enabled
                     or not.  If {{true}}, sequence hopping is
                     enabled.  If {{false}}, sequence hopping is
                     not enabled.
                  
                     Corresponds to sequenceHoppingEnabled
                     parameter specified in
                     {{bibref|3GPP-TS.36.331|Section 6.3.2}}.and
                     in {{bibref|3GPP-TS.36.211|Section
                     5.5.1.4}}.";
                }
                leaf CyclicShift {
                  type uint32 {
                    range "0..7";
                  }
                  config false;
                  description
                    "Corresponds to parameter cyclcShift specified
                     in {{bibref|3GPP-TS.36.331|Section 6.3.2}}.";
                }
              }
            }

            container ULPowerControl {
              description
                "This object contains parameters relating to the
                 uplink power control configuration (see
                 {{bibref|3GPP-TS.32.592|Section 6.1.1.7}}).";
              leaf P0NominalPUSCH {
                type string;
                description
                  "{{list}} Each item is a value to compute the UL
                   UE transmit power for transmission on PUSCH
                   for semi-persistant grants, with a numeric
                   range between -126 and 24 inclusive.  In case
                   there is more than one item in the list, the
                   first item contains the most preferred value.
                   Corresponds to p0-NominalPUSCH parameter
                   specified in {{bibref|3GPP-TS.36.331|Section
                   6.3.2}} and PO_NOMINAL_PUSCH(0) parameter
                   specified in {{bibref|3GPP-TS.36.211|Section
                   5.1.1.1}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf Alpha {
                type string;
                description
                  "{{list}} Each item is a value used to compute the
                   UL UE transmit power for transmission on
                   PUSCH, from the list of 0, 4, 5, 6, 7, 8, 9,
                   100.  In case there is more than one item in
                   the list, the first item contains the most
                   preferred value.  Actual values of range are
                   from 0.00 to 1.00.  The value of {{param}}
                   divided by 100 yields the actual value.
                   Corresponds to alpha parameter specified in
                   {{bibref|3GPP-TS.36.331|Section 6.3.2}} and to
                   α parameter specified in
                   {{bibref|3GPP-TS.36.211|Section 5.1.1.1}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf P0NominalPUCCH {
                type string;
                description
                  "{{list}} Each item is a value to compute the UL
                   UE transmit power for transmission on PUCCH,
                   with a numeric range between -126 and 24
                   inclusive.  In case there is more than one
                   item in the list, the first item contains the
                   most preferred value.  Corresponds to
                   p0-NominalPUCCH parameter specified in
                   {{bibref|3GPP-TS.36.331|Section 6.3.2}} and
                   PO_NOMINAL_PUCCH parameter specified in
                   {{bibref|3GPP-TS.36.211|Section 5.1.2.1}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf DeltaFPUCCHFormat1 {
                type int32 {
                  range "-2 | 0 | 2";
                }
                config false;
                description
                  "Defines deltaF-PUCCH-Format1 to derive the UE
                   transmit power.
                
                   Corresponds to parameter ?F_PUCCH(1) in
                   {{units}} as specified in
                   {{bibref|3GPP-TS.36.331|Section 6.3.2}} and in
                   {{bibref|3GPP-TS.36.213|Section 5.1.2}}.";
              }
              leaf DeltaFPUCCHFormat1b {
                type uint32 {
                  range "1 | 3 | 5";
                }
                config false;
                description
                  "Defines deltaF-PUCCH-Format1b to derive the UE
                   transmit power.
                
                   Corresponds to parameter ?F_PUCCH(1b) in
                   {{units}} dB as specified in
                   {{bibref|3GPP-TS.36.331|Section 6.3.2}} and in
                   {{bibref|3GPP-TS.36.213|Section 5.1.2}}.";
              }
              leaf DeltaFPUCCHFormat2 {
                type int32 {
                  range "-2 | 0..2";
                }
                config false;
                description
                  "Defines deltaF-PUCCH-Format2 to derive the UE
                   transmit power.
                
                   Corresponds to parameter ?F_PUCCH(2) in
                   {{units}} as specified in
                   {{bibref|3GPP-TS.36.331|Section 6.3.2}} and in
                   {{bibref|3GPP-TS.36.213|Section 5.1.2}}.";
              }
              leaf DeltaFPUCCHFormat2a {
                type int32 {
                  range "-2 | 0 | 2";
                }
                config false;
                description
                  "Defines deltaF-PUCCH-Format2a to derive the UE
                   transmit power.
                
                   Corresponds to parameter ?F_PUCCH(2a) in
                   {{units}} as specified in
                   {{bibref|3GPP-TS.36.331|Section 6.3.2}} and in
                   {{bibref|3GPP-TS.36.213|Section 5.1.2}}.";
              }
              leaf DeltaFPUCCHFormat2b {
                type int32 {
                  range "-2 | 0 | 2";
                }
                config false;
                description
                  "Defines deltaF-PUCCH-Format2b to derive the UE
                   transmit power.
                
                   Corresponds to parameter ?F_PUCCH(2b) in
                   {{units}} as specified in
                   {{bibref|3GPP-TS.36.331|Section 6.3.2}} and in
                   {{bibref|3GPP-TS.36.213|Section 5.1.2}}.";
              }
              leaf DeltaPreambleMsg3 {
                type int32 {
                  range "-1..6";
                }
                config false;
                description
                  "Defines the parameter in {{units}} used to
                   compute the UL UE transmit power for
                   transmission of random access response grant.
                
                   This parameter corresponds to
                   deltaPreambleMsg3 parameter specified in
                   {{bibref|3GPP-TS.36.331|Section 6.3.2}} and to
                   ?PREAMBLE_Msg3 parameter specified in
                   {{bibref|3GPP-TS.36.213|Section 5.1.1.1}}.
                   Actual value is 2x the value of this
                   parameter.";
              }
            }

            container MBSFN {
              description
                "This object contains parameters relating to the
                 MBSFN (Multimedia Broadcast multicast service
                 Single Frequency Network) configuration (see
                 {{bibref|3GPP-TS.32.592|Section 6.1.1.8}}).";
              leaf NeighCellConfig {
                type uint32 {
                  range "0..3";
                }
                description
                  "Defines the information related to MBSFN and TDD
                   UL/DL configuration of neighbour cells.
                   Corresponds to NeighCellConfig IE specified in
                   {{bibref|3GPP-TS.36.331|Section 6.3.6}}.
                
                   Value 0: Not all neighbour cells have the same
                   MBSFN sub-frame allocation as serving cell.
                
                   Value 1: No MBSFN sub-frames are present in
                   all neighbour cells.
                
                   Value 2: The MBSFN sub-frame allocations of
                   all neighbour cells are identical to or
                   subsets of that in the serving cell.
                
                   Value 3: Different UL/DL allocation in
                   neighbouring cells for TDD compared to the
                   serving cell.";
              }
              leaf MaxSFConfigListEntries {
                type uint32;
                config false;
                description
                  "The maximum number of entries in the
                   {{object|.CellConfig.LTE.RAN.PHY.MBSFN.SFConfigList.{i}.}}
                   table.";
              }

              list SFConfigList {
                key "RadioFrameAllocationPeriod RadioframeAllocationOffset RadioFrameAllocationSize";
                description
                  "This object contains parameters relating to the
                   sub-frame that are reserved for MBSFN
                   (Multimedia Broadcast multicast service Single
                   Frequency Network) in downlink direction.  For
                   FDD mode, only one entry can exist in this
                   table.  For TDD mode, at most one entry can
                   exist with a given value of stratumID (see
                   {{bibref|3GPP-TS.32.592|Section 6.1.1.8}}).";
                leaf Enable {
                  type boolean;
                  default "false";
                  description
                    "Enables or disables this entry.";
                }
                leaf SyncStratumID {
                  type uint32 {
                    range "1..8";
                  }
                  description
                    "This parameter is applicable to TDD mode only.
                     Defines the synchronization stratum level to
                     which the MBSFN configuration applies.";
                }
                leaf RadioFrameAllocationPeriod {
                  type uint32 {
                    range "1..2 | 4 | 8 | 16 | 32";
                  }
                  description
                    "Defines the period where MBSFN sub-frames occur
                     in the radio frames.  Radio frames contain
                     MBSFN sub-frame when the following condition
                     is met: ((SFN mod {{param}}) =
                     {{param|RadioframeAllocationOffset}}).  The
                     value of 1 and 2 are only meaningful when
                     the value of
                     {{param|RadioFrameAllocationSize}} parameter
                     is 1.
                  
                     Corresponds to radioFrameAllocationPeriod IE
                     specified in {{bibref|3GPP-TS.36.331|Section
                     6.3.1}}.";
                }
                leaf RadioframeAllocationOffset {
                  type uint32 {
                    range "0..7";
                  }
                  description
                    "Defines the offset where MBSFN sub-frames occur
                     in the radio frames.  Radio frames contain
                     MBSFN sub-frame when the following condition
                     is met: ((SFN mod
                     {{param|RadioFrameAllocationPeriod}}) =
                     {{param}}).  Corresponds to
                     radioFrameAllocationOffset IE specified in
                     {{bibref|3GPP-TS.36.331|Section 6.3.1}}.";
                }
                leaf RadioFrameAllocationSize {
                  type uint32 {
                    range "1 | 4";
                  }
                  description
                    "Defines the number of connsecutive frames that
                     the MBSFN allocation pertains to defined by
                     the combination of
                     {{param|RadioFrameAllocationPeriod}} and
                     {{param|RadioframeAllocationOffset}}
                     parameters.";
                }
                leaf SubFrameAllocations {
                  type uint32 {
                    range "0 | 1";
                  }
                  description
                    "{{list}} The value of \"1\" indicates the
                     position of sub-frames that is allocated to
                     MBSFN within the radio frame.  First item
                     defines the MBSFN allocation for sub-frame
                     #1, second item for #2, third item for #3,
                     fourth item for #6, fifth item for #7, sixth
                     item for #8.  If the value of
                     {{param|RadioFrameAllocationSize}} is 4,
                     then this pattern repeats in the sequence of
                     the four radio frames.
                  
                     The actual size of this parameter depends on
                     the value of
                     {{param|RadioFrameAllocationSize}}
                     parameter.  If the value of
                     {{param|RadioFrameAllocationSize}} is 1,
                     then the size of this parameter is 6; if the
                     size {{param|RadioFrameAllocationSize}} is
                     4, then the size of this parameter is 24.
                  
                     Corresponds to subframeAllocation IE
                     specified in {{bibref|3GPP-TS.36.331|Section
                     6.3.1}}.";
                }
              }
            }

            container PRS {
              description
                "This object contains parameters relating to the PRS
                 (Positioning Reference Signal) configuration
                 (see {{bibref|3GPP-TS.32.592|Section 6.1.1.9}}).";
              leaf NumPRSResourceBlocks {
                type uint32;
                description
                  "Defines the number of RBs ({{units}}) used for
                   PRS.  Corresponds to the parameter NRBPRS in
                   {{bibref|3GPP-TS.36.211|Section 6.10.4.1}}.";
              }
              leaf PRSConfigurationIndex {
                type uint32 {
                  range "0..4095";
                }
                description
                  "Corresponds to the PRS configuration index
                   defined as parameter IPRS in
                   {{bibref|3GPP-TS.36.211|Section 6.10.4.3 and
                   Table 6.10.4.3.-1}}.";
              }
              leaf NumConsecutivePRSSubfames {
                type uint32 {
                  range "1..2 | 4 | 6";
                }
                description
                  "Defines the number of consecutive positioning
                   sub-frames.  Corresponds to the parameter NPRS
                   in {{bibref|3GPP-TS.36.211|Section 6.10.4.3}}.";
              }
            }

            container TDDFrame {
              description
                "This object is applicable to TDD mode only.  This
                 object contains parameters relating to the TDD
                 frame structure configuration (see
                 {{bibref|3GPP-TS.32.592|Section 6.1.1.10}}).";
              leaf SubFrameAssignment {
                type uint32 {
                  range "0..6";
                }
                description
                  "Defines the DL/UL sub-frame configuration.
                   Corresponds to subframAssignment specified in
                   {{bibref|3GPP-TS.36.331|Section 6.3.2}} and
                   {{bibref|3GPP-TS.36.211|Table 4.2.2}}.";
              }
              leaf SpecialSubframePatterns {
                type uint32 {
                  range "0..8";
                }
                description
                  "Defines the configuration of the special
                   sub-frame that contains the guard period
                   between the downlink and uplink transmissions.
                   Corresponds to the specialSubframePatterns
                   specified in {{bibref|3GPP-TS.36.331|Section
                   6.3.2}} and {{bibref|3GPP-TS.36.211|Table
                   4.2.1}}.";
              }
            }
          }

          container MAC {
            description
              "This object contains parameters relating to the MAC
               (Medium Access Control) configuration.";

            container RACH {
              description
                "This object contains parameters relating to the
                 RACH (Random Access Channel) configuration (see
                 {{bibref|3GPP-TS.32.592|Section 6.1.2.1}}).";
              leaf NumberOfRaPreambles {
                type uint32 {
                  range "4..64";
                }
                description
                  "{{list}} Each item is a number of non-dedicated
                   random access preambles.  Only values in
                   multiple of 4 are valid (i.e.  4, 8, 12,
                   16,...64); use of other values within the
                   defined range MUST be rejected by the CPE.  In
                   case there is more than one item in the list,
                   the first item contains the most preferred
                   value.  Corresponds to parameter
                   numberOfRA-Preambles specified in
                   {{bibref|3GPP-TS.36.331|Section 6.3.2}} and in
                   {{bibref|3GPP-TS.36.321|Section 5.1.1}}.
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf SizeOfRaGroupA {
                type uint32 {
                  range "4..60";
                }
                description
                  "{{list}} Each item is a number of non-dedicated
                   random access preambles in Random Acces
                   Preambles group A.  Only values in multiple of
                   4 are valid (i.e.  4, 8, 12, 16,...60); use of
                   other values within the defined range MUST be
                   rejected by the CPE.  In case there is more
                   than one item in the list, the first item
                   contains the most preferred value.
                   Corresponds to parameter
                   sizeOfRA-PreamblesGroupA specified in
                   {{bibref|3GPP-TS.36.331|Section 6.3.2}} and in
                   {{bibref|3GPP-TS.36.321|Section 5.1.1}}.
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf MessageSizeGroupA {
                type uint32 {
                  range "56 | 144 | 208 | 256";
                }
                description
                  "{{list}} Each item is a threshold for preamble
                   selection, specified in bits.  In case there
                   is more than one item in the list, the first
                   item contains the most preferred value.
                   Defined in {{bibref|3GPP-TS.36.321|Section
                   5.1.2}}.  Corresponds to parameter
                   messageSizeGroupA specified in
                   {{bibref|3GPP-TS.36.331|Section 6.3.2}}.
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf MessagePowerOffsetGroupB {
                type int32 {
                  range "-1 | 5 | 8 | 10 | 12 | 15 | 18";
                }
                description
                  "{{list}} Each item is a threshold for preamble
                   selection, specified in dB.  In case there is
                   more than one item in the list, the first item
                   contains the most preferred value.  Defined in
                   {{bibref|3GPP-TS.36.321|Section 5.1.2}}.
                   Corresponds to parameter
                   messagePowerOffsetGroupB specified in
                   {{bibref|3GPP-TS.36.331|Section 6.3.2}}.
                   Value of -1 indicates \"minusinfinity.\"
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf PowerRampingStep {
                type uint32 {
                  range "0 | 2 | 4 | 6";
                }
                description
                  "{{list}} Each item is a power increase factor
                   between subsequent random access preamble
                   transmissions, specified in dB.  In case there
                   is more than one item in the list, the first
                   item contains the most preferred value.
                   Corresponds to parameter powerRampingStep
                   specified in {{bibref|3GPP-TS.36.331|Section
                   6.3.2}} and in {{bibref|3GPP-TS.36.321|Section
                   5.1.3}}.
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf PreambleInitialReceivedTargetPower {
                type int32 {
                  range "-120..-90";
                }
                description
                  "{{list}} Each item is a value used as the
                   baseline for computation for random access
                   transmission power, specified in dBm.  Also
                   used as a parameter in the criteria for
                   preamble selection.  Only even values are
                   valid (i.e.  -120, -118, -116,...-90); use of
                   other values within the defined range MUST be
                   rejected by the CPE.  In case there is more
                   than one item in the list, the first item
                   contains the most preferred value.
                   Corresponds to parameter
                   preambleInitialReceivedTargetPower specified
                   in {{bibref|3GPP-TS.36.331|Section 6.3.2}} and
                   in {{bibref|3GPP-TS.36.321|Section 5.1.2}}.
                   and section 5.1.3.
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf PreambleTransMax {
                type string;
                description
                  "{{list}} Each item is a maximum number of random
                   access preamble transmissions, from the list
                   of 3, 4, 5, 6, 7, 8, 10, 20, 50, 100, 200.  In
                   case there is more than one item in the list,
                   the first item contains the most preferred
                   value.  Corresponds to parameter
                   preambleTransMax specified in
                   {{bibref|3GPP-TS.36.331|Section 6.3.2}} and in
                   {{bibref|3GPP-TS.36.321|Section 5.1.4 and
                   section 5.1.5}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf ResponseWindowSize {
                type string;
                description
                  "{{list}} Each item is a duration of the random
                   access response window, specified in
                   sub-frames, with a numeric range between 2 and
                   10 inclusive (except value of 9).  In case
                   there is more than one item in the list, the
                   first item contains the most preferred value.
                   Corresponds to parameter ra-ResponseWindowSize
                   specified in {{bibref|3GPP-TS.36.331|Section
                   6.3.2}} and in {{bibref|3GPP-TS.36.321|Section
                   5.1.4}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf ContentionResolutionTimer {
                type uint32 {
                  range "8..64";
                }
                description
                  "{{list}} Each item is a contention resolution
                   timer, specified in sub-frames.  Only values
                   multiple of 8 are valid (i.e.  8, 16,
                   24,...64); use of other values within the
                   defined range MUST be rejected by the CPE.  In
                   case there is more than one item in the list,
                   the first item contains the most preferred
                   value.  Corresponds to parameter
                   mac-ContentionResolutionTimer specified in
                   {{bibref|3GPP-TS.36.331|Section 6.3.2}} and in
                   {{bibref|3GPP-TS.36.321|Section 5.1.5}}.
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf MaxHARQMsg3Tx {
                type string;
                description
                  "{{list}} Each item is a maximum number of Msg3
                   HARQ transmissions by RRC, with a numeric
                   range between 1 and 8 inclusive.  In case
                   there is more than one item in the list, the
                   first item contains the most preferred value.
                   Corresponds to parameter maxHARQ-Msg3Tx
                   specified in {{bibref|3GPP-TS.36.331|Section
                   6.3.2}} and in {{bibref|3GPP-TS.36.321|Section
                   5.4.2.2}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
            }

            container DRX {
              description
                "This object contains parameters relating to the DRX
                 (Discontinuous Reception) configuration (see
                 {{bibref|3GPP-TS.32.592|Section 6.1.2.2}}).";
              leaf DRXEnabled {
                type boolean;
                description
                  "Specifies whether DRX operation is enabled or
                   not.  If {{true}}, DRX operation is enabled.
                   If {{false}}, DRX operation is not enabled.
                
                   Corresponds to drx-Configuration IE defined in
                   {{bibref|3GPP-TS.36.331|Section 6.3.2}}.";
              }
              leaf OnDurationTimer {
                type string;
                description
                  "{{list}} Each item is the DRX cycle during which
                   UE actively monitors PDCCH, specified in
                   number of PDCCH sub-frames, from the list of
                   1, 2, 3, 4, 5, 6, 8, 10, 20, 30, 40, 50, 60,
                   80, 100, 200.  In case there is more than one
                   item in the list, the first item contains the
                   most preferred value.  Corresponds to
                   parameter onDurationTimer specified in
                   {{bibref|3GPP-TS.36.331|Section 6.3.2}} and in
                   {{bibref|3GPP-TS.36.321|Section 5.7}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf DRXInactivityTimer {
                type string;
                description
                  "{{list}} Each item defines the number of inactive
                   consecutive PDCCH sub-frame(s) that will
                   activate short DRX cycle, specified in number
                   of PDCCH sub-frames, from the list of 1, 2, 3,
                   4, 5, 6, 8, 10, 20, 30, 40, 50, 60, 80, 100,
                   200, 300, 500, 750, 1280, 1920, 2560.  In case
                   there is more than one item in the list, the
                   first item contains the most preferred value.
                   Corresponds to parameter drx-InactivityTimer
                   specified in {{bibref|3GPP-TS.36.331|Section
                   6.3.2}} and in {{bibref|3GPP-TS.36.321|Section
                   5.7}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf DRXRetransmissionTimer {
                type uint32 {
                  range "1 | 2 | 4 | 6 | 8 | 16 | 24 | 33";
                }
                description
                  "{{list}} Each item defines the maximum number of
                   consecutive PDCCH sub-frame(s) UE MUST remain
                   active expecting a DL retransmission,
                   specified in number of PDCCH sub-frames.  In
                   case there is more than one item in the list,
                   the first item contains the most preferred
                   value.  The timer is started when a HARQ RTT
                   Timer expires and the data in the soft buffer
                   of the corresponding HARQ process was not
                   successfully decoded.  There is one timer for
                   each active HARQ process.  Corresponds to
                   parameter drx-RetransmissionTimer specified in
                   {{bibref|3GPP-TS.36.331|Section 6.3.2}} and in
                   {{bibref|3GPP-TS.36.321|Section 5.7}}.
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf LongDRXCycle {
                type uint32 {
                  range "10 | 20 | 32 | 40 | 64 | 80 | 128 | 160 | 256 | 320 | 512 | 640 | 1024 | 1280 | 2048 | 2560";
                }
                description
                  "{{list}} Each item is long DRX Cycle value,
                   specified in number of sub-frames.  In case
                   there is more than one item in the list, the
                   first item contains the most preferred value.
                   If shortDRX-Cycle is configured, this value
                   MUST be a multiple of the
                   {{param|ShortDRXCycle}} value.  Corresponds to
                   longDRX-Cycle parameter specified in
                   {{bibref|3GPP-TS.36.321|Section 5.7}} and
                   longDRX-CycleStartOffset specified in
                   {{bibref|3GPP-TS.36.331|Section 6.3.2}}.
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf DRXStartOffset {
                type string;
                description
                  "{{list}} Each item defines the starting frame of
                   the DRX cycle within the long DRX cycle, with
                   a numeric range between 0 and 2559 inclusive.
                   In case there is more than one item in the
                   list, the first item contains the most
                   preferred value.  The valid value range is
                   dependent on {{param|LongDRXCycle}} parameter
                   which defines the upper bound of this range,
                   i.e., range definition is [0:
                   ({{param|LongDRXCycle}}-1)].  Corresponds to
                   drxStartOffset parameter specified in
                   {{bibref|3GPP-TS.36.321|Section 5.7}}.
                
                   Use of values bigger than
                   ({{param|LongDRXCycle}}-1) MUST be rejected by
                   the CPE.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf ShortDRXCycle {
                type uint32 {
                  range "2 | 5 | 8 | 10 | 16 | 20 | 32 | 40 | 64 | 80 | 128 | 160 | 256 | 320 | 512 | 640";
                }
                description
                  "{{list}} Each item is the short DRX Cycle value,
                   specified in number of sub-frames.  In case
                   there is more than one item in the list, the
                   first item contains the most preferred value.
                   If shortDRX-Cycle is configured, the value of
                   {{param|LongDRXCycle}} MUST be a multiple of
                   the {{param}} value.  Corresponds to
                   shortDRX-Cycle parameter specified in
                   {{bibref|3GPP-TS.36.321|Section 5.7}}.
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf DRXShortCycleTimer {
                type string;
                description
                  "{{list}} Each item defined the duration of the
                   short DRX cycle in multiples of
                   {{param|ShortDRXCycle}} parameter, specified
                   in number of sub-frames, with a numeric range
                   between 1 and 16 inclusive.  In case there is
                   more than one item in the list, the first item
                   contains the most preferred value.  Denotes
                   the number of consecutive sub-frame(s)the UE
                   shall follow the short DRX cycle after the DRX
                   Inactivity Timer has expired.  Corresponds to
                   drxShortCycleTimer parameter specified in
                   {{bibref|3GPP-TS.36.321|Section 5.7}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
            }

            container ULSCH {
              config false;
              description
                "This object contains parameters relating to the
                 ULSCH (Uplink Shared Channel) configuration (see
                 {{bibref|3GPP-TS.32.592|Section 6.1.2.3}}).";
              leaf MaxHARQTx {
                type uint32 {
                  range "1..8 | 10 | 12 | 16 | 20 | 24 | 28";
                }
                description
                  "Maximum number of UL HARQ transmissions.
                
                   Corresponds to parameter maxHARQ-Tx specified
                   in {{bibref|3GPP-TS.36.331|Section 6.3.2}} and
                   in {{bibref|3GPP-TS.36.321|Section 5.4.2.2}}.";
              }
              leaf PeriodicBSRTimer {
                type uint32 {
                  range "0 | 5 | 10 | 16 | 20 | 32 | 40 | 64 | 80 | 128 | 160 | 320 | 640 | 1280 | 2560";
                }
                description
                  "Timer for Periodic BSR (Buffer Status Report)
                   reporting, specified in number of {{units}}.
                   UE transmits periodic BSR at the expiration of
                   this timer.
                
                   Corresponds to parameter periodicBSR-Timer
                   specified in {{bibref|3GPP-TS.36.331|Section
                   6.3.2}} and in {{bibref|3GPP-TS.36.321|Section
                   5.4.5}}.  Value of 0 indicates \"infinity.\"";
              }
              leaf RetxBSRTimer {
                type uint32 {
                  range "320 | 640 | 1280 | 2560 | 5120 | 10240";
                }
                description
                  "Timer for Regular BSR reporting, specified in
                   number of {{units}}.  UE transmits a Regular
                   BSR at the expiration of this timer if data is
                   available in the buffer.
                
                   Corresponds to parameter retxBSR-Timer
                   specified in {{bibref|3GPP-TS.36.331|Section
                   6.3.2}} and in {{bibref|3GPP-TS.36.321|Section
                   5.4.5}}.";
              }
              leaf TTIBundling {
                type boolean;
                description
                  "Enables/disables TTI bundling.  If {{true}}, TTI
                   bundling is enabled.  If {{false}}, TTI
                   bundling is disabled.
                
                   Corresponds to parameter ttiBundling specified
                   in {{bibref|3GPP-TS.36.331|Section 6.3.2}} and
                   in {{bibref|3GPP-TS.36.321|Section 5.4.2.1}}.";
              }
            }
          }

          container RLC {
            description
              "This object contains parameters relating to the RLC
               (Radio Link Control) configuration.";

            container SRB1 {
              description
                "This object contains parameters relating to the
                 SRB1 (Signaling Radio Bearer 1) configuration
                 (see {{bibref|3GPP-TS.32.592|Section 6.1.3.1}}).";
              leaf DefaultConfiguration {
                type boolean;
                description
                  "Indicates the whether default RLC configuration
                   for SRB1 is used or not.
                
                   If {{true}}, the default RLC configuration is
                   used as specified in
                   {{bibref|3GPP-TS.36.331|Section 9.2.1.1}}.  In
                   this case, rest of the parameters defined
                   under the current object are ignored by the
                   CPE.
                
                   If {{false}}, rest of the parameters defined
                   under the current object are used by the CPE
                   for RLC configuration.";
              }
              leaf TPollRetransmit {
                type string;
                description
                  "{{list}} Each item is a timer between successive
                   poll transmissions, specified in milliseconds,
                   specified in milliseconds, with a numeric
                   range between 5 and 500 inclusive.  Only the
                   multiple of 5 are valid in the range between 5
                   and 250 inclusive (i.e.  5, 10, 15, 20,...
                   250), and only the multiple of 50 are valid in
                   the range between 300 and 500 inclusive (i.e.,
                   300, 350, 400, 450, 500).  If the value is
                   other than these, the CPE MUST reject the
                   value.  In case there is more than one item in
                   the list, the first item contains the most
                   preferred value.
                
                   This parameter is valid only if
                   {{param|DefaultConfiguration}} paramter under
                   the current object is set to {{false}}.
                   Corresponds to t-PollRetransmit IE specified
                   in {{bibref|3GPP-TS.36.331|Section 6.3.2}} and
                   in {{bibref|3GPP-TS.36.322|Section 5.2.2}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf PollPDU {
                type uint32 {
                  range "0 | 4 | 8 | 16 | 32 | 64 | 128 | 256";
                }
                description
                  "{{list}} Each item is a counter of PDUs between
                   successive poll transmissions, specified in
                   the number of PDUs.  In case there is more
                   than one item in the list, the first item
                   contains the most preferred value.
                
                   This parameter is valid only if
                   {{param|DefaultConfiguration}} paramter under
                   the current object is set to {{false}}.
                   Corresponds to pollPDU IE specified in
                   {{bibref|3GPP-TS.36.331|Section 6.3.2}} and in
                   {{bibref|3GPP-TS.36.322|Section 5.2.2.1}}.
                   Value of 0 indicates \"infinity.\"
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf PollByte {
                type uint32 {
                  range "0 | 25 | 50 | 75 | 100 | 125 | 250 | 375 | 500 | 750 | 1000 | 1250 | 1500 | 2000 | 3000";
                }
                description
                  "{{list}} Each item is a counter of PDU bytes
                   transmitted between successive poll
                   transmissions, specified in kilobytes.  In
                   case there is more than one item in the list,
                   the first item contains the most preferred
                   value.
                
                   This parameter is valid only if
                   {{param|DefaultConfiguration}} paramter under
                   the current object is set to {{false}}.
                   Corresponds to pollByte IE specified in
                   {{bibref|3GPP-TS.36.331|Section 6.3.2}} and in
                   {{bibref|3GPP-TS.36.322|Section 5.2.2.1}}.
                   Value of 0 indicates infinite amount of
                   kilobytes.
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf MaxRetxThreshold {
                type uint32 {
                  range "1..4 | 6 | 8 | 16 | 32";
                }
                description
                  "{{list}} Each item defines the maximum number of
                   transmission retry used by the RLC entity to
                   limit the number of retransmissions of an AMD
                   PDU.  In case there is more than one item in
                   the list, the first item contains the most
                   preferred value.
                
                   This parameter is valid only if
                   {{param|DefaultConfiguration}} paramter under
                   the current object is set to {{false}}.
                   Corresponds to maxRetxThreshold IE specified
                   in {{bibref|3GPP-TS.36.331|Section 6.3.2}} and
                   in {{bibref|3GPP-TS.36.322|Section 5.2.1}}.
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf TReordering {
                type string;
                description
                  "{{list}} Each item defines a timer used by the
                   receiving side of an RLC entity in order to
                   detect loss of RLC PDUs at lower layer,
                   specified in milliseconds, with a numeric
                   range between 0 and 200 inclusive.  Only the
                   multiple of 5 are valid in the range between 0
                   and 100 inclusive (i.e.  0, 5, 10,
                   15,...,100), and only the multiple of 10 are
                   valid in the range between 110 and 200
                   inclusive (110, 120, 130,...,200).  If the
                   value is other than these, the CPE MUST reject
                   the value.  In case there is more than one
                   item in the list, the first item contains the
                   most preferred value.
                
                   This parameter is valid only if
                   {{param|DefaultConfiguration}} paramter under
                   the current object is set to {{false}}.
                   Corresponds to t-Reordering IE specified in
                   {{bibref|3GPP-TS.36.331|Section 6.3.2}} and in
                   {{bibref|3GPP-TS.36.322|Section 5.1.2.2.  and
                   5.1.3.2}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf TStatusProhibit {
                type string;
                description
                  "{{list}} Each item defines a timer used by the
                   receiving side of an AM RLC entity in order to
                   prohibit transmission of a STATUS PDU,
                   specified in milliseconds, with a numeric
                   range between 0 and 500 inclusive.  Only the
                   multiple of 5 are valid in the range between 0
                   and 250 inclusive (i.e.  0, 5, 10,
                   15,...,250), and only the multiple of 50 are
                   valid in the range between 300 and 500
                   inclusive (i.e.  300, 350, 400, 450, 500).  If
                   the value is other than these, the CPE MUST
                   reject the value.  In case there is more than
                   one item in the list, the first item contains
                   the most preferred value.
                
                   This parameter is valid only if
                   {{param|DefaultConfiguration}} paramter under
                   the current object is set to {{false}}.
                   Corresponds to t-StatusProhibit IE specified
                   in {{bibref|3GPP-TS.36.331|Section 6.3.2}} and
                   in {{bibref|3GPP-TS.36.322|Section 5.2.3}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
            }

            container SRB2 {
              description
                "This object contains parameters relating to the
                 SRB2 (Signaling Radio Bearer 2) configuration
                 (see {{bibref|3GPP-TS.32.592|Section 6.1.3.1}}).";
              leaf DefaultConfiguration {
                type boolean;
                description
                  "Indicates the whether default RLC configuration
                   for SRB1 is used or not.
                
                   If {{true}}, the default RLC configuration is
                   used as specified in
                   {{bibref|3GPP-TS.36.331|Section 9.2.1.1}}.  In
                   this case, rest of the parameters defined
                   under the current object are ignored by the
                   CPE.
                
                   If {{false}}, rest of the parameters defined
                   under the current object are used by the CPE
                   for RLC configuration.";
              }
              leaf TPollRetransmit {
                type string;
                description
                  "{{list}} Each item is a timer between successive
                   poll transmissions, specified in milliseconds,
                   with a numeric range between 5 and 500
                   inclusive.  Only the multiple of 5 are valid
                   in the range between 5 and 250 inclusive (i.e.
                   5, 10, 15, 20,...  250), and only the multiple
                   of 50 are valid in the range between 300 and
                   500 inclusive (i.e., 300, 350, 400, 450, 500).
                   If the value is other than these, the CPE MUST
                   reject the value.  In case there is more than
                   one item in the list, the first item contains
                   the most preferred value.
                
                   This parameter is valid only if
                   {{param|DefaultConfiguration}} paramter under
                   the current object is set to {{false}}.
                   Corresponds to t-PollRetransmit IE specified
                   in {{bibref|3GPP-TS.36.331|Section 6.3.2}} and
                   in {{bibref|3GPP-TS.36.322|Section 5.2.2}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf PollPDU {
                type uint32 {
                  range "0 | 4 | 8 | 16 | 32 | 64 | 128 | 256";
                }
                description
                  "{{list}} Each item is a counter of PDUs between
                   successive poll transmissions, specified in
                   the number of PDUs.  In case there is more
                   than one item in the list, the first item
                   contains the most preferred value.
                
                   This parameter is valid only if
                   {{param|DefaultConfiguration}} paramter under
                   the current object is set to {{false}}.
                   Corresponds to pollPDU IE specified in
                   {{bibref|3GPP-TS.36.331|Section 6.3.2}} and in
                   {{bibref|3GPP-TS.36.322|Section 5.2.2.1}}.
                   Value of 0 indicates \"infinity.\"
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf PollByte {
                type uint32 {
                  range "0 | 25 | 50 | 75 | 100 | 125 | 250 | 375 | 500 | 750 | 1000 | 1250 | 1500 | 2000 | 3000";
                }
                description
                  "{{list}} Each item is a counter of PDU bytes
                   transmitted between successive poll
                   transmissions, specified in kilobytes.  In
                   case there is more than one item in the list,
                   the first item contains the most preferred
                   value.
                
                   This parameter is valid only if
                   {{param|DefaultConfiguration}} paramter under
                   the current object is set to {{false}}.
                   Corresponds to pollByte IE specified in
                   {{bibref|3GPP-TS.36.331|Section 6.3.2}} and in
                   {{bibref|3GPP-TS.36.322|Section 5.2.2.1}}.
                   Value of 0 indicates infinite amount of
                   kilobytes.
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf MaxRetxThreshold {
                type uint32 {
                  range "1..4 | 6 | 8 | 16 | 32";
                }
                description
                  "{{list}} Each item defines the maximum number of
                   transmission retry used by the RLC entity to
                   limit the number of retransmissions of an AMD
                   PDU.  In case there is more than one item in
                   the list, the first item contains the most
                   preferred value.
                
                   This parameter is valid only if
                   {{param|DefaultConfiguration}} paramter under
                   the current object is set to {{false}}.
                   Corresponds to maxRetxThreshold IE specified
                   in {{bibref|3GPP-TS.36.331|Section 6.3.2}} and
                   in {{bibref|3GPP-TS.36.322|Section 5.2.1}}.
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf TReordering {
                type string;
                description
                  "{{list}} Each item defines a timer used by the
                   receiving side of an RLC entity in order to
                   detect loss of RLC PDUs at lower layer,
                   specified in milliseconds, with a numeric
                   range between 0 and 200 inclusive.  Only the
                   multiple of 5 are valid in the range between 0
                   and 100 inclusive (i.e.  0, 5, 10,
                   15,...,100), and only the multiple of 10 are
                   valid in the range between 110 and 200
                   inclusive (110, 120, 130,...,200).  If the
                   value is other than these, the CPE MUST reject
                   the value.  In case there is more than one
                   item in the list, the first item contains the
                   most preferred value.
                
                   This parameter is valid only if
                   {{param|DefaultConfiguration}} paramter under
                   the current object is set to {{false}}.
                   Corresponds to t-Reordering IE specified in
                   {{bibref|3GPP-TS.36.331|Section 6.3.2}} and in
                   {{bibref|3GPP-TS.36.322|Section 5.1.2.2.  and
                   5.1.3.2}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
              leaf TStatusProhibit {
                type string;
                description
                  "{{list}} Each item defines a timer used by the
                   receiving side of an AM RLC entity in order to
                   prohibit transmission of a STATUS PDU,
                   specified in milliseconds, with a numeric
                   range between 0 and 500 inclusive.  Only the
                   multiple of 5 are valid in the range between 0
                   and 250 inclusive (i.e.  0, 5, 10,
                   15,...,250), and only the multiple of 50 are
                   valid in the range between 300 and 500
                   inclusive (i.e.  300, 350, 400, 450, 500).  If
                   the value is other than these, the CPE MUST
                   reject the value.  In case there is more than
                   one item in the list, the first item contains
                   the most preferred value.
                
                   This parameter is valid only if
                   {{param|DefaultConfiguration}} paramter under
                   the current object is set to {{false}}.
                   Corresponds to t-StatusProhibit IE specified
                   in {{bibref|3GPP-TS.36.331|Section 6.3.2}} and
                   in {{bibref|3GPP-TS.36.322|Section 5.2.3}}.
                
                   The multiplicity of the {{param}} values can
                   also be expressed by defining a range using
                   \"..\" (two periods) between two values.  In
                   this case, the combination of two values
                   defines the lower-bound and upper-bound of the
                   range inclusive.  If this notation is used,
                   then the list contains at least 2 items:
                   \"<preferred-value>,<lower-bound>..<upper-bound>\".
                
                   If supports self-configuration capability for
                   {{param}} and more than one item is
                   configured, then is expected to select one
                   from the list and overwrite this parameter
                   containing only the one selected.  If does not
                   support self-configuration capability for
                   {{param}} and more than one item is
                   configured, then accepts the first value and
                   ignore the rest.  If only one item is
                   configured regardless of the
                   self-configuration capability of , accepts the
                   value as an explicit configuration by the ACS.";
              }
            }
          }

          container RRCTimers {
            description
              "This object contains parameters relating to the RRC
               timers and constants (see
               {{bibref|3GPP-TS.32.592|Section 6.1.6.1}}) and
               (see {{bibref|3GPP-TS.32.592|Section 6.1.6.2}}).";
            leaf T300 {
              type uint32 {
                range "100 | 200 | 300 | 400 | 600 | 1000 | 1500 | 2000";
              }
              description
                "{{list}} Each item is an interval, in milliseconds,
                 between subsequent transmissions of
                 RRCConnectionRequest.  In case there is more
                 than one item in the list, the first item
                 contains the most preferred value.  Corresponds
                 to parameter t300 specified in
                 UE-TimersAndConstants IE in
                 {{bibref|3GPP-TS.36.331|Section 6.3.6}}.
                 Start/stop/expirary condition is defined in
                 {{bibref|3GPP-TS.36.331|Section 7.3}}.
              
                 If supports self-configuration capability for
                 {{param}} and more than one item is configured,
                 then is expected to select one from the list and
                 overwrite this parameter containing only the one
                 selected.  If does not support
                 self-configuration capability for {{param}} and
                 more than one item is configured, then accepts
                 the first value and ignore the rest.  If only
                 one item is configured regardless of the
                 self-configuration capability of , accepts the
                 value as an explicit configuration by the ACS.";
            }
            leaf T301 {
              type uint32 {
                range "100 | 200 | 300 | 400 | 600 | 1000 | 1500 | 2000";
              }
              description
                "{{list}} Each item is an interval, in milliseconds,
                 between subsequent transmissions of
                 RRCConnectionReestablishmentRequest.  In case
                 there is more than one item in the list, the
                 first item contains the most preferred value.
                 Corresponds to parameter t301 specified in
                 UE-TimersAndConstants IE in
                 {{bibref|3GPP-TS.36.331|Section 6.3.6}}.
                 Start/stop/expirary condition is defined in
                 {{bibref|3GPP-TS.36.331|Section 7.3}}.
              
                 If supports self-configuration capability for
                 {{param}} and more than one item is configured,
                 then is expected to select one from the list and
                 overwrite this parameter containing only the one
                 selected.  If does not support
                 self-configuration capability for {{param}} and
                 more than one item is configured, then accepts
                 the first value and ignore the rest.  If only
                 one item is configured regardless of the
                 self-configuration capability of , accepts the
                 value as an explicit configuration by the ACS.";
            }
            leaf T302 {
              type uint32 {
                range "100 | 200 | 300 | 400 | 600 | 1000 | 1500 | 2000";
              }
              description
                "Time to wait in {{units}} for cell re-selection or
                 RRConnectionSetup after RRCConnectionReject.
                 Start/stop/expirary condition is defined in
                 {{bibref|3GPP-TS.36.331|Section 7.3}}.";
            }
            leaf T304EUTRA {
              type uint32 {
                range "50 | 100 | 150 | 200 | 500 | 1000 | 2000";
              }
              description
                "{{list}} Each item is a HO failure timer, in
                 milliseconds.  In case there is more than one
                 item in the list, the first item contains the
                 most preferred value.  Corresponds to t304
                 defined within IE MobilityControlInfo in
                 RRCConnectionReconfiguration message in
                 {{bibref|3GPP-TS.36.331|Section 5.3.5.4 and
                 Section 6.3.4}}.  Start/stop/expirary condition
                 is defined in {{bibref|3GPP-TS.36.331|Section
                 7.3}}.
              
                 If supports self-configuration capability for
                 {{param}} and more than one item is configured,
                 then is expected to select one from the list and
                 overwrite this parameter containing only the one
                 selected.  If does not support
                 self-configuration capability for {{param}} and
                 more than one item is configured, then accepts
                 the first value and ignore the rest.  If only
                 one item is configured regardless of the
                 self-configuration capability of , accepts the
                 value as an explicit configuration by the ACS.";
            }
            leaf T304IRAT {
              type uint32 {
                range "100 | 200 | 500 | 1000 | 2000 | 4000 | 8000";
              }
              description
                "{{list}} Each item is a HO failure timer, in
                 milliseconds.  In case there is more than one
                 item in the list, the first item contains the
                 most preferred value.  Corresponds to t304
                 defined within IE CellChangeOrder in
                 MobilityFromEUTRACommand message in
                 {{bibref|3GPP-TS.36.331|Section 6.2.2}}.
                 Start/stop/expirary condition is defined in
                 {{bibref|3GPP-TS.36.331|Section 7.3}}.
              
                 If supports self-configuration capability for
                 {{param}} and more than one item is configured,
                 then is expected to select one from the list and
                 overwrite this parameter containing only the one
                 selected.  If does not support
                 self-configuration capability for {{param}} and
                 more than one item is configured, then accepts
                 the first value and ignore the rest.  If only
                 one item is configured regardless of the
                 self-configuration capability of , accepts the
                 value as an explicit configuration by the ACS.";
            }
            leaf T310 {
              type uint32 {
                range "0 | 50 | 100 | 200 | 500 | 1000 | 2000";
              }
              description
                "{{list}} Each item is a RLF declaration timer, in
                 milliseconds.  In case there is more than one
                 item in the list, the first item contains the
                 most preferred value.  Corresponds to parameter
                 t310 specified in RLF-TimersAndConstants IE in
                 {{bibref|3GPP-TS.36.331|Section 6.3.6}}.
                 Start/stop/expirary condition is defined in
                 {{bibref|3GPP-TS.36.331|Section 7.3}}.
              
                 If supports self-configuration capability for
                 {{param}} and more than one item is configured,
                 then is expected to select one from the list and
                 overwrite this parameter containing only the one
                 selected.  If does not support
                 self-configuration capability for {{param}} and
                 more than one item is configured, then accepts
                 the first value and ignore the rest.  If only
                 one item is configured regardless of the
                 self-configuration capability of , accepts the
                 value as an explicit configuration by the ACS.";
            }
            leaf T311 {
              type uint32 {
                range "1000 | 3000 | 5000 | 10000 | 15000 | 20000 | 30000";
              }
              description
                "{{list}} Each item is a RLF recovery timer, in
                 milliseconds.  In case there is more than one
                 item in the list, the first item contains the
                 most preferred value.  Corresponds to parameter
                 t311 specified in RLF-TimersAndConstants IE in
                 {{bibref|3GPP-TS.36.331|Section 6.3.6}}.
                 Start/stop/expirary condition is defined in
                 {{bibref|3GPP-TS.36.331|Section 7.3}}.
              
                 If supports self-configuration capability for
                 {{param}} and more than one item is configured,
                 then is expected to select one from the list and
                 overwrite this parameter containing only the one
                 selected.  If does not support
                 self-configuration capability for {{param}} and
                 more than one item is configured, then accepts
                 the first value and ignore the rest.  If only
                 one item is configured regardless of the
                 self-configuration capability of , accepts the
                 value as an explicit configuration by the ACS.";
            }
            leaf T320 {
              type uint32 {
                range "5 | 10 | 20 | 30 | 60 | 120 | 180";
              }
              description
                "Time in {{units}} after RRCConnection Release in
                 which cell re-selection priority info supplied
                 in RRCConnectionRelease MUST be observed.
                 Start/stop/expirary condition is defined in
                 {{bibref|3GPP-TS.36.331|Section 7.3}}.
              
                 Corresponds to parameter t320 specified in
                 RRCConnectionRelease message in
                 {{bibref|3GPP-TS.36.331|Section 6.2.2}}.  S";
            }
            leaf N310 {
              type uint32 {
                range "1..4 | 6 | 8 | 10 | 20";
              }
              description
                "Number of consecutive \"out-of-sync\" indications
                 received from lower layers that triggers timer
                 T310.
              
                 Corresponds to parameter n310 specified in
                 UE-TimersAndConstants IE in
                 {{bibref|3GPP-TS.36.331|Section 6.3.6 and
                 Section 7.3}}.";
            }
            leaf N311 {
              type uint32 {
                range "1..6 | 8 | 10";
              }
              description
                "Number of consecutive \"in-sync\" indications
                 received from lower layers that stops timer
                 T310.
              
                 Corresponds to parameter n311 specified in
                 UE-TimersAndConstants IE in
                 {{bibref|3GPP-TS.36.331|Section 6.3.6 and
                 Section 7.3}}.";
            }
          }

          container CellRestriction {
            description
              "This object contains parameters relating to the cell
               restriction configuration.";
            leaf CellBarred {
              type boolean;
              description
                "Indicates whether the is barred or not.  If
                 {{true}}, the cell is barred.  If {{false}}, the
                 cell is not barred.
              
                 Corresponds to parameter CellBarred specified in
                 SIB1 in {{bibref|3GPP-TS.36.331|Section 6.2.2}}.";
            }
            leaf CellReservedForOperatorUse {
              type boolean;
              description
                "Indicates whether the is reserved for operator's
                 use or not.  If {{true}}, the cell is reserved
                 for operator use.  If {{false}}, the cell is not
                 reserved for operator use.
              
                 Corresponds to parameter
                 cellReservedForOperatorUse specified in SIB1 in
                 {{bibref|3GPP-TS.36.331|Section 6.2.2}}.";
            }
            leaf BarringForEmergency {
              type boolean;
              description
                "Indicates whether the is barred for Access Class 10
                 or not.
              
                 If {{true}}, the cell is barred for Access Class
                 10.
              
                 If {{false}}, the cell is not barred for Access
                 Class 10.
              
                 Corresponds to parameter ac-BarringForEmergency
                 specified in SIB2 in
                 {{bibref|3GPP-TS.36.331|Section 6.3.1}}.";
            }
          }

          container Mobility {
            description
              "This object contains parameters relating to the UE's
               mobility configuration.  It covers both idle mode
               and connected mode.";

            container IdleMode {
              description
                "This object contains parameters relating to the
                 UE's mobility while it is in idle mode (cell
                 (re-)selection).  Parameters under this object
                 determines the content in the SIB (System
                 Information Block) that is broadcast by LTE .";

              container Common {
                description
                  "This object contains parameters relating to the
                   idle mode mobility configuration that is
                   common to all cell re-selection scenarios
                   (intra/inter-freq, inter-RAT to UTRA (UMTS),
                   GERAN (GSM) and CDMA2000) (see
                   {{bibref|3GPP-TS.32.592|Section 6.1.5.1.1}}).";
                leaf Qhyst {
                  type string;
                  description
                    "{{list}} Each item is a hysteresis value
                     applied to serving cell for evaluating cell
                     ranking criteria specified in dB, with a
                     numeric range between 0 and 24 inclusive.
                     For the value greater than 6, only even
                     numbers are valid.  If the value is other
                     than these, the CPE MUST reject the value.
                     In case there is more than one item in the
                     list, the first item contains the most
                     preferred value.  Corresponds to parameter
                     q-Hyst specified in SIB3 in
                     {{bibref|3GPP-TS.36.331|Section 6.3.1}} and
                     in {{bibref|3GPP-TS.36.304|Section
                     5.2.4.7}}.
                  
                     The multiplicity of the {{param}} values can
                     also be expressed by defining a range using
                     \"..\" (two periods) between two values.  In
                     this case, the combination of two values
                     defines the lower-bound and upper-bound of
                     the range inclusive.  If this notation is
                     used, then the list contains at least 2
                     items:
                     \"<preferred-value>,<lower-bound>..<upper-bound>\".
                  
                     If supports self-configuration capability
                     for {{param}} and more than one item is
                     configured, then is expected to select one
                     from the list and overwrite this parameter
                     containing only the one selected.  If does
                     not support self-configuration capability
                     for {{param}} and more than one item is
                     configured, then accepts the first value and
                     ignore the rest.  If only one item is
                     configured regardless of the
                     self-configuration capability of , accepts
                     the value as an explicit configuration by
                     the ACS.";
                }
                leaf QHystSFMedium {
                  type int32 {
                    range "-6 | -4 | -2 | 0";
                  }
                  description
                    "Speed-dependent scaling factor for Qhyst in
                     Medium-mobility state, specified in
                     {{units}}.
                  
                     Corresponds to parameter q-HystSF:sf-Medium
                     specified in SIB3 in
                     {{bibref|3GPP-TS.36.331|Section 6.3.1}} and
                     in {{bibref|3GPP-TS.36.304|Section
                     5.2.4.3}}.";
                }
                leaf QHystSFHigh {
                  type int32 {
                    range "-6 | -4 | -2 | 0";
                  }
                  description
                    "Speed-dependent scaling factor for Qhyst in
                     High-mobility state, specified in {{units}}.
                  
                     Corresponds to parameter q-HystSF:sf-High
                     specified in SIB3 in
                     {{bibref|3GPP-TS.36.331|Section 6.3.1}} and
                     in {{bibref|3GPP-TS.36.304|Section
                     5.2.4.3}}.";
                }
                leaf TEvaluation {
                  type uint32 {
                    range "30 | 60 | 120 | 180 | 240";
                  }
                  description
                    "Duration for evaluating allowed amount of cell
                     re-selection(s) required to enter mobility
                     states, specified in {{units}}.
                  
                     Corresponds to parameter t-Evaluation
                     specified in SIB3 in
                     {{bibref|3GPP-TS.36.331|Section 6.3.4}} and
                     to parameter TCRmax specified in
                     {{bibref|3GPP-TS.36.304|Section 5.2.4.3}}.";
                }
                leaf THystNormal {
                  type uint32 {
                    range "30 | 60 | 120 | 180 | 240";
                  }
                  description
                    "Additional duration for evaluating criteria to
                     enter normal mobility state, specified in
                     {{units}}.  Specifies the additional time
                     period for evaluating criteria to enter
                     Normal-mobility state.
                  
                     Corresponds to parameter t-HystNormal
                     specified in SIB3 in
                     {{bibref|3GPP-TS.36.331|Section 6.3.4}} and
                     to parameter TCRmaxHyst specified in
                     {{bibref|3GPP-TS.36.304|Section 5.2.4.3}}.";
                }
                leaf NCellChangeMedium {
                  type uint32 {
                    range "1..16";
                  }
                  description
                    "Defines the number of cell re-selections within
                     TEvaluation to enter Medium-mobility state.
                  
                     Corresponds to parameter n-cellChangeMedium
                     specified in SIB3 in
                     {{bibref|3GPP-TS.36.331|Section 6.3.4}} and
                     to parameter NCR_M specified in
                     {{bibref|3GPP-TS.36.304|Section 5.2.4.3}}.";
                }
                leaf NCellChangeHigh {
                  type uint32 {
                    range "1..16";
                  }
                  description
                    "Defines the number of cell re-selections within
                     TEvaluation to enter High-mobility state.
                  
                     Corresponds to parameter n-cellChangeHigh
                     specified in SIB3 in
                     {{bibref|3GPP-TS.36.331|Section 6.3.4}} and
                     to parameter NCR_H specified in
                     {{bibref|3GPP-TS.36.304|Section 5.2.4.3}}.";
                }
              }

              container IntraFreq {
                description
                  "This object contains parameters relating to the
                   idle mode mobility configuration for
                   intra-freq re-selection scenario (see
                   {{bibref|3GPP-TS.32.592|Section 6.1.5.1.2}}).";
                leaf QRxLevMinSIB1 {
                  type string;
                  description
                    "{{list}} Each item is a required minimum
                     received RSRP level of a E-UTRA cell for
                     cell selection, specified in dBm, with a
                     numeric range between -70 and -22 inclusive.
                     In case there is more than one item in the
                     list, the first item contains the most
                     preferred value.  The value of ({{param}} *
                     2) yields the actual value.  Corresponds to
                     parameter q-rxLevMin in SIB1 in
                     {{bibref|3GPP-TS.36.331|Section 6.2.2}} and
                     in {{bibref|3GPP-TS.36.304|Section
                     5.2.3.2}}.
                  
                     The multiplicity of the {{param}} values can
                     also be expressed by defining a range using
                     \"..\" (two periods) between two values.  In
                     this case, the combination of two values
                     defines the lower-bound and upper-bound of
                     the range inclusive.  If this notation is
                     used, then the list contains at least 2
                     items:
                     \"<preferred-value>,<lower-bound>..<upper-bound>\".
                  
                     If supports self-configuration capability
                     for {{param}} and more than one item is
                     configured, then is expected to select one
                     from the list and overwrite this parameter
                     containing only the one selected.  If does
                     not support self-configuration capability
                     for {{param}} and more than one item is
                     configured, then accepts the first value and
                     ignore the rest.  If only one item is
                     configured regardless of the
                     self-configuration capability of , accepts
                     the value as an explicit configuration by
                     the ACS.";
                }
                leaf QRxLevMinSIB3 {
                  type string;
                  description
                    "{{list}} Each item is a required minimum
                     received RSRP level for intra-frequency
                     E-UTRA cell re-selection, specified in dBm,
                     with a numeric range between -70 and -22
                     inclusive.  In case there is more than one
                     item in the list, the first item contains
                     the most preferred value.  The value of
                     ({{param}} * 2) yields the actual value.
                     Corresponds to parameter q-rxLevMin in SIB3
                     in {{bibref|3GPP-TS.36.331|Section 6.3.1}}
                     and in {{bibref|3GPP-TS.36.304|Section
                     5.2.3.2}}.
                  
                     The multiplicity of the {{param}} values can
                     also be expressed by defining a range using
                     \"..\" (two periods) between two values.  In
                     this case, the combination of two values
                     defines the lower-bound and upper-bound of
                     the range inclusive.  If this notation is
                     used, then the list contains at least 2
                     items:
                     \"<preferred-value>,<lower-bound>..<upper-bound>\".
                  
                     If supports self-configuration capability
                     for {{param}} and more than one item is
                     configured, then is expected to select one
                     from the list and overwrite this parameter
                     containing only the one selected.  If does
                     not support self-configuration capability
                     for {{param}} and more than one item is
                     configured, then accepts the first value and
                     ignore the rest.  If only one item is
                     configured regardless of the
                     self-configuration capability of , accepts
                     the value as an explicit configuration by
                     the ACS.";
                }
                leaf QRxLevMinOffset {
                  type uint32 {
                    range "1..8";
                  }
                  description
                    "Defines offset with respect to QrxLevMin,
                     specified in {{units}}.  This offset is
                     taken into account in the computation of
                     Srxlev for cell selection evaluation of
                     cells detected during a periodic search for
                     a higher priority PLMN while camped normally
                     in a VPLMN.  The value of ({{param}} * 2)
                     yields the actual value.
                  
                     Corresponds to parameter q-rxLevMinOffset in
                     SIB1 specified in
                     {{bibref|3GPP-TS.36.331|Section 6.2.2}} and
                     in {{bibref|3GPP-TS.36.304|Section
                     5.2.3.2}}.";
                }
                leaf SIntraSearch {
                  type string;
                  description
                    "{{list}} Each item is a threshold for
                     intra-frequency measurements, specified in
                     dB, with a numeric range between 0 and 31
                     inclusive.  In case there is more than one
                     item in the list, the first item contains
                     the most preferred value.  The value of
                     ({{param}} * 2) yields the actual value.
                     Corresponds to parameter s-IntraSearch
                     specified in SIB3 in
                     {{bibref|3GPP-TS.36.331|Section 6.3.1}} and
                     in {{bibref|3GPP-TS.36.304|Section
                     5.2.4.7}}.
                  
                     The multiplicity of the {{param}} values can
                     also be expressed by defining a range using
                     \"..\" (two periods) between two values.  In
                     this case, the combination of two values
                     defines the lower-bound and upper-bound of
                     the range inclusive.  If this notation is
                     used, then the list contains at least 2
                     items:
                     \"<preferred-value>,<lower-bound>..<upper-bound>\".
                  
                     If supports self-configuration capability
                     for {{param}} and more than one item is
                     configured, then is expected to select one
                     from the list and overwrite this parameter
                     containing only the one selected.  If does
                     not support self-configuration capability
                     for {{param}} and more than one item is
                     configured, then accepts the first value and
                     ignore the rest.  If only one item is
                     configured regardless of the
                     self-configuration capability of , accepts
                     the value as an explicit configuration by
                     the ACS.";
                }
                leaf TReselectionEUTRA {
                  type string;
                  description
                    "{{list}} Each item is a cell re-selection timer
                     for intra-frequency E-UTRA cell
                     re-selection, specified in seconds, with a
                     numeric range between 0 and 7 inclusive.  In
                     case there is more than one item in the
                     list, the first item contains the most
                     preferred value.  Corresponds to parameter
                     t-ReselectionEUTRA specified in SIB3 in
                     {{bibref|3GPP-TS.36.331|Section 6.3.1}} and
                     in {{bibref|3GPP-TS.36.304|Section
                     5.2.4.7}}.
                  
                     The multiplicity of the {{param}} values can
                     also be expressed by defining a range using
                     \"..\" (two periods) between two values.  In
                     this case, the combination of two values
                     defines the lower-bound and upper-bound of
                     the range inclusive.  If this notation is
                     used, then the list contains at least 2
                     items:
                     \"<preferred-value>,<lower-bound>..<upper-bound>\".
                  
                     If supports self-configuration capability
                     for {{param}} and more than one item is
                     configured, then is expected to select one
                     from the list and overwrite this parameter
                     containing only the one selected.  If does
                     not support self-configuration capability
                     for {{param}} and more than one item is
                     configured, then accepts the first value and
                     ignore the rest.  If only one item is
                     configured regardless of the
                     self-configuration capability of , accepts
                     the value as an explicit configuration by
                     the ACS.";
                }
                leaf SNonIntraSearch {
                  type string;
                  description
                    "{{list}} Each item is a threshold for
                     inter-frequency and inter-RAT measurements
                     with lower or equal priority, specified in
                     dB, with a numeric range between 0 and 31
                     inclusive.  In case there is more than one
                     item in the list, the first item contains
                     the most preferred value.  The value of
                     ({{param}} * 2) yields the actual value.
                     Corresponds to parameter s-NonIntraSearch
                     specified in SIB3 in
                     {{bibref|3GPP-TS.36.331|Section 6.3.1}} and
                     in {{bibref|3GPP-TS.36.304|Section
                     5.2.4.7}}.
                  
                     The multiplicity of the {{param}} values can
                     also be expressed by defining a range using
                     \"..\" (two periods) between two values.  In
                     this case, the combination of two values
                     defines the lower-bound and upper-bound of
                     the range inclusive.  If this notation is
                     used, then the list contains at least 2
                     items:
                     \"<preferred-value>,<lower-bound>..<upper-bound>\".
                  
                     If supports self-configuration capability
                     for {{param}} and more than one item is
                     configured, then is expected to select one
                     from the list and overwrite this parameter
                     containing only the one selected.  If does
                     not support self-configuration capability
                     for {{param}} and more than one item is
                     configured, then accepts the first value and
                     ignore the rest.  If only one item is
                     configured regardless of the
                     self-configuration capability of , accepts
                     the value as an explicit configuration by
                     the ACS.";
                }
                leaf CellReselectionPriority {
                  type uint32 {
                    range "0..7";
                  }
                  description
                    "Absolute priority of the E-UTRAN serving
                     carrier frequency used in the
                     inter-frequency and inter-RAT cell
                     re-selection procedure.
                  
                     Corresponds to parameter
                     CellReselectionPriority specified in SIB3 in
                     {{bibref|3GPP-TS.36.331|Section 6.3.1}} and
                     in {{bibref|3GPP-TS.36.304|Section
                     5.2.4.7}}.";
                }
                leaf PMax {
                  type int32 {
                    range "-30..33";
                  }
                  description
                    "Used to limit the allowed UE uplink
                     transmission power on the serving frequency,
                     specified in {{units}}.  It is used to
                     calculate the parameter Pcompensation
                     defined in {{bibref|3GPP-TS.36.304|Section
                     5.2.3.2}}.
                  
                     Corresponds to parameter p-Max specified in
                     SIB1 and SIB3 in
                     {{bibref|3GPP-TS.36.331|Section 6.3.1 and
                     Section 6.3.4}}.";
                }
                leaf ThreshServingLow {
                  type uint32 {
                    range "0..31";
                  }
                  description
                    "Threshold for serving frequency used in
                     evaluation of re-selection towards lower
                     priority E-UTRAN frequency or inter-RAT,
                     specified in {{units}}.  The value of
                     ({{param}} * 2) yields the actual value.
                  
                     Corresponds to parameter threshServingLow
                     specified in SIB3 in
                     {{bibref|3GPP-TS.36.331|Section 6.3.1}} and
                     in {{bibref|3GPP-TS.36.304|Section
                     5.2.4.7}}.";
                }
                leaf TReselectionEUTRASFMedium {
                  type uint32 {
                    range "25 | 50 | 75 | 100";
                  }
                  description
                    "Scaling factor for intra-frequency
                     TreselectionEUTRA in Medium-mobility state.
                     The value of {{param}} divided by 100 yields
                     the actual SF value.
                  
                     Corresponds to parameter
                     t-ReselectionEUTRA-SF:sf-Medium specified in
                     SIB3 in {{bibref|3GPP-TS.36.331|Section
                     6.3.1}} and in
                     {{bibref|3GPP-TS.36.304|Section 5.2.4.3}}.";
                }
                leaf TReselectionEUTRASFHigh {
                  type uint32 {
                    range "25 | 50 | 75 | 100";
                  }
                  description
                    "Scaling factor for intra-frequency
                     TreselectionEUTRA in High-mobility state.
                     The value of {{param}} divided by 100 yields
                     the actual SF value.
                  
                     Corresponds to parameter
                     t-ReselectionEUTRA-SF:sf-High specified in
                     SIB3 in {{bibref|3GPP-TS.36.331|Section
                     6.3.1}} and in
                     {{bibref|3GPP-TS.36.304|Section 5.2.4.3}}.";
                }
              }

              container InterFreq {
                description
                  "This object contains parameters relating to the
                   idle mode mobility configuration for
                   inter-freq re-selection scenario .";
                leaf MaxCarrierEntries {
                  type uint32;
                  config false;
                  description
                    "The maximum number of entries in the
                     {{object|.CellConfig.LTE.RAN.Mobility.IdleMode.InterFreq.Carrier.{i}.}}
                     table.";
                }

                list Carrier {
                  key "EUTRACarrierARFCN";
                  description
                    "This object contains parameters relating to the
                     carrier information for inter-freq
                     re-selection scenario (see
                     {{bibref|3GPP-TS.32.592|Section
                     6.1.5.1.3}}).";
                  leaf Enable {
                    type boolean;
                    default "false";
                    description
                      "Enables or disables this entry.";
                  }
                  leaf EUTRACarrierARFCN {
                    type uint32 {
                      range "0..65535";
                    }
                    default "0";
                    description
                      "Indicates the ARFCN of this frequency
                       carrier.  Corresponds to parameter
                       dl-CarrierFreq in SIB5 in
                       {{bibref|3GPP-TS.36.331|Section 6.3.1}}.";
                  }
                  leaf QRxLevMinSIB5 {
                    type string;
                    default "0";
                    description
                      "{{list}} Each item is a required minimum
                       received RSRP level on this E-UTRA
                       frequency carrier, spcified in dBm, with a
                       numeric range between -70 and -22
                       inclusive.  In case there is more than one
                       item in the list, the first item contains
                       the most preferred value.  The value of
                       ({{param}} * 2) yields the actual value.
                       Corresponds to parameter q-rxLevMin in
                       SIB5 in {{bibref|3GPP-TS.36.331|Section
                       6.3.1}} and in
                       {{bibref|3GPP-TS.36.304|Section 5.2.3.2}}.
                    
                       The multiplicity of the {{param}} values
                       can also be expressed by defining a range
                       using \"..\" (two periods) between two
                       values.  In this case, the combination of
                       two values defines the lower-bound and
                       upper-bound of the range inclusive.  If
                       this notation is used, then the list
                       contains at least 2 items:
                       \"<preferred-value>,<lower-bound>..<upper-bound>\".
                    
                       If supports self-configuration capability
                       for {{param}} and more than one item is
                       configured, then is expected to select one
                       from the list and overwrite this parameter
                       containing only the one selected.  If does
                       not support self-configuration capability
                       for {{param}} and more than one item is
                       configured, then accepts the first value
                       and ignore the rest.  If only one item is
                       configured regardless of the
                       self-configuration capability of , accepts
                       the value as an explicit configuration by
                       the ACS.";
                  }
                  leaf QOffsetFreq {
                    type string;
                    default "0";
                    description
                      "{{list}} Each item is an offset applicable
                       between serving and this frequency
                       carrier, specified in dBm, with a numeric
                       range between -24 and 24 inclusive.  For
                       values less than or equal to -6, or values
                       greater than or equal to 6, only the even
                       values are valid.  If the value is other
                       than these, the CPE MUST reject the value.
                       In case there is more than one item in the
                       list, the first item contains the most
                       preferred value.  The value of ({{param}}
                       * 2) yields the actual value.  Corresponds
                       to parameter q-OffsetFreq in SIB5
                       specified in
                       {{bibref|3GPP-TS.36.331|Section 6.3.1}}
                       and in {{bibref|3GPP-TS.36.304|Section
                       5.4.2.6}}.
                    
                       The multiplicity of the {{param}} values
                       can also be expressed by defining a range
                       using \"..\" (two periods) between two
                       values.  In this case, the combination of
                       two values defines the lower-bound and
                       upper-bound of the range inclusive.  If
                       this notation is used, then the list
                       contains at least 2 items:
                       \"<preferred-value>,<lower-bound>..<upper-bound>\".
                    
                       If supports self-configuration capability
                       for {{param}} and more than one item is
                       configured, then is expected to select one
                       from the list and overwrite this parameter
                       containing only the one selected.  If does
                       not support self-configuration capability
                       for {{param}} and more than one item is
                       configured, then accepts the first value
                       and ignore the rest.  If only one item is
                       configured regardless of the
                       self-configuration capability of , accepts
                       the value as an explicit configuration by
                       the ACS.";
                  }
                  leaf TReselectionEUTRA {
                    type string;
                    default "0";
                    description
                      "{{list}} Each item is a cell re-selection
                       timer for inter-frequency cell
                       re-selection to this E-UTRA frequency
                       carrier, specified in seconds, with a
                       numeric range between 0 and 7 inclusive.
                       In case there is more than one item in the
                       list, the first item contains the most
                       preferred value.  Corresponds to parameter
                       t-ReselectionEUTRA specified in SIB5 in
                       {{bibref|3GPP-TS.36.331|Section 6.3.1}}
                       and in {{bibref|3GPP-TS.36.304|Section
                       5.2.4.7}}.
                    
                       The multiplicity of the {{param}} values
                       can also be expressed by defining a range
                       using \"..\" (two periods) between two
                       values.  In this case, the combination of
                       two values defines the lower-bound and
                       upper-bound of the range inclusive.  If
                       this notation is used, then the list
                       contains at least 2 items:
                       \"<preferred-value>,<lower-bound>..<upper-bound>\".
                    
                       If supports self-configuration capability
                       for {{param}} and more than one item is
                       configured, then is expected to select one
                       from the list and overwrite this parameter
                       containing only the one selected.  If does
                       not support self-configuration capability
                       for {{param}} and more than one item is
                       configured, then accepts the first value
                       and ignore the rest.  If only one item is
                       configured regardless of the
                       self-configuration capability of , accepts
                       the value as an explicit configuration by
                       the ACS.";
                  }
                  leaf CellReselectionPriority {
                    type uint32 {
                      range "0..7";
                    }
                    default "0";
                    description
                      "Absolute priority of this E-UTRA frequency
                       carrier, as used by the inter-frequency
                       cell re-selection procedure.
                    
                       Corresponds to parameter
                       CellReselectionPriority specified in SIB5
                       in {{bibref|3GPP-TS.36.331|Section 6.3.1}}
                       and in {{bibref|3GPP-TS.36.304|Section
                       5.2.4.7}}.";
                  }
                  leaf ThreshXHigh {
                    type uint32 {
                      range "0..31";
                    }
                    default "0";
                    description
                      "Threshold used when re-selecting from a lower
                       priority E-UTRAN frequency, specified in
                       {{units}}.  The value of ({{param}} * 2)
                       yields the actual value.
                    
                       Corresponds to parameter threshX-High
                       specified in SIB5 in
                       {{bibref|3GPP-TS.36.331|Section 6.3.1}}
                       and in {{bibref|3GPP-TS.36.304|Section
                       5.2.4.5}}.";
                  }
                  leaf ThreshXLow {
                    type uint32 {
                      range "0..31";
                    }
                    default "0";
                    description
                      "Threshold used when re-selecting from a
                       higher priority E-UTRAN frequency,
                       specified in {{units}}.  The value of
                       ({{param}} * 2) yields the actual value.
                    
                       Corresponds to parameter threshX-Low
                       specified in SIB5 in
                       {{bibref|3GPP-TS.36.331|Section 6.3.1}}
                       and in {{bibref|3GPP-TS.36.304|Section
                       5.2.4.5}}.";
                  }
                  leaf PMax {
                    type int32 {
                      range "-30..33";
                    }
                    default "0";
                    description
                      "Used to limit the allowed UE uplink
                       transmission power on this carrier
                       frequency, specified in {{units}}.  It is
                       used to calculate the parameter
                       Pcompensation defined in
                       {{bibref|3GPP-TS.36.304|Section 5.2.3.2}}.
                    
                       Corresponds to parameter p-Max specified
                       in SIB5 in {{bibref|3GPP-TS.36.331|Section
                       6.3.1}}.";
                  }
                  leaf TReselectionEUTRASFMedium {
                    type uint32 {
                      range "25 | 50 | 75 | 100";
                    }
                    default "25";
                    description
                      "Scaling factor for TreselectionEUTRA for
                       inter-frequency re-selection to this
                       frequency carrier in Medium-mobility
                       state.  The value of {{param}} divided by
                       100 yields the actual SF value.
                    
                       Corresponds to parameter
                       t-ReselectionEUTRA-SF:sf-Medium specified
                       in SIB5 in {{bibref|3GPP-TS.36.331|Section
                       6.3.1}} and in
                       {{bibref|3GPP-TS.36.304|Section 5.2.4.3}}.";
                  }
                  leaf TReselectionEUTRASFHigh {
                    type uint32 {
                      range "25 | 50 | 75 | 100";
                    }
                    default "25";
                    description
                      "Scaling factor for TreselectionEUTRA for
                       inter-frequency re-selection to this
                       frequency carrier in High-mobility state.
                       The value of {{param}} divided by 100
                       yields the actual SF value.
                    
                       Corresponds to parameter
                       t-ReselectionEUTRA-SF:sf-High specified in
                       SIB5 in {{bibref|3GPP-TS.36.331|Section
                       6.3.1}} and in
                       {{bibref|3GPP-TS.36.304|Section 5.2.4.3}}.";
                  }
                }
              }

              container IRAT {
                description
                  "This object contains parameters relating to the
                   idle mode mobility configuration for inter-RAT
                   (Radio Access Technology) re-selection
                   scenario.";

                container UTRA {
                  description
                    "This object contains parameters relating to the
                     idle mode mobility configuration for
                     inter-RAT (Radio Access Technology)
                     re-selection, specifically for re-selection
                     to UTRA (UMTS) scenario (see
                     {{bibref|3GPP-TS.32.592|Section
                     6.1.5.1.4}}).";
                  leaf TReselectionUTRA {
                    type string;
                    description
                      "{{list}} Each item is a cell re-selection
                       timer for re-selection to a UTRA frequency
                       carrier, specified in seconds, with a
                       numeric range between 0 and 7 inclusive.
                       In case there is more than one item in the
                       list, the first item contains the most
                       preferred value.  Corresponds to parameter
                       t-ReselectionUTRA specified in SIB6 in
                       {{bibref|3GPP-TS.36.331|Section 6.3.1}}
                       and in {{bibref|3GPP-TS.36.304|Section
                       5.2.4.7}}.
                    
                       The multiplicity of the {{param}} values
                       can also be expressed by defining a range
                       using \"..\" (two periods) between two
                       values.  In this case, the combination of
                       two values defines the lower-bound and
                       upper-bound of the range inclusive.  If
                       this notation is used, then the list
                       contains at least 2 items:
                       \"<preferred-value>,<lower-bound>..<upper-bound>\".
                    
                       If supports self-configuration capability
                       for {{param}} and more than one item is
                       configured, then is expected to select one
                       from the list and overwrite this parameter
                       containing only the one selected.  If does
                       not support self-configuration capability
                       for {{param}} and more than one item is
                       configured, then accepts the first value
                       and ignore the rest.  If only one item is
                       configured regardless of the
                       self-configuration capability of , accepts
                       the value as an explicit configuration by
                       the ACS.";
                  }
                  leaf TReselectionUTRASFMedium {
                    type uint32 {
                      range "25 | 50 | 75 | 100";
                    }
                    description
                      "Scaling factor for TreselectionUTRA for
                       inter-RAT re-selection to UTRA in
                       Medium-mobility state.  The value of
                       {{param}} divided by 100 yields the actual
                       SF value.
                    
                       Corresponds to parameter
                       t-ReselectionUTRA-SF:sf-Medium specified
                       in SIB6 in {{bibref|3GPP-TS.36.331|Section
                       6.3.1}} and in
                       {{bibref|3GPP-TS.36.304|Section 5.2.4.3}}.";
                  }
                  leaf TReselectionUTRASFHigh {
                    type uint32 {
                      range "25 | 50 | 75 | 100";
                    }
                    description
                      "Scaling factor for TreselectionEUTRA for
                       inter-frequency re-selection to this
                       frequency carrier in High-mobility state.
                       The value of {{param}} divided by 100
                       yields the actual SF value.
                    
                       Corresponds to parameter
                       t-ReselectionUTRA-SF:sf-High specified in
                       SIB6 in {{bibref|3GPP-TS.36.331|Section
                       6.3.1}} and in
                       {{bibref|3GPP-TS.36.304|Section 5.2.4.3}}.";
                  }
                  leaf MaxUTRANFDDFreqEntries {
                    type uint32;
                    config false;
                    description
                      "The maximum number of entries in the
                       {{object|.CellConfig.LTE.RAN.Mobility.IdleMode.IRAT.UTRA.UTRANFDDFreq.{i}.}}
                       table.";
                  }

                  list UTRANFDDFreq {
                    key "UTRACarrierARFCN";
                    description
                      "This object contains parameters relating to
                       the channel frequncy related information
                       of UTRA (UMTS) system (see
                       {{bibref|3GPP-TS.32.592|Section 6.1.5.1.5,
                       6.1.5.1.6}}).";
                    leaf Enable {
                      type boolean;
                      default "false";
                      description
                        "Enables or disables this entry.";
                    }
                    leaf UTRACarrierARFCN {
                      type uint32 {
                        range "0..16383";
                      }
                      default "0";
                      description
                        "Indicates the ARFCN of the frequency
                         carrier.  Corresponds to parameter
                         CarrierFreq in SIB6 in
                         {{bibref|3GPP-TS.36.331|Section 6.3.1}}.";
                    }
                    leaf QRxLevMin {
                      type string;
                      default "-60";
                      description
                        "{{list}} Each item is a required minimum
                         received RSCP level on this UTRA
                         frequency carrier, specified in dBm,
                         with a numeric range between -60 and -13
                         inclusive.  In case there is more than
                         one item in the list, the first item
                         contains the most preferred value.  The
                         value of ({{param}} * 2 + 1) yields the
                         actual value.  Corresponds to parameter
                         q-RxLevMin in SIB6 in
                         {{bibref|3GPP-TS.36.331|Section 6.3.1}}
                         and in {{bibref|3GPP-TS.25.304|Section
                         5.2.3.1.2}}.
                      
                         The multiplicity of the {{param}} values
                         can also be expressed by defining a
                         range using \"..\" (two periods) between
                         two values.  In this case, the
                         combination of two values defines the
                         lower-bound and upper-bound of the range
                         inclusive.  If this notation is used,
                         then the list contains at least 2 items:
                         \"<preferred-value>,<lower-bound>..<upper-bound>\".
                      
                         If supports self-configuration
                         capability for {{param}} and more than
                         one item is configured, then is expected
                         to select one from the list and
                         overwrite this parameter containing only
                         the one selected.  If does not support
                         self-configuration capability for
                         {{param}} and more than one item is
                         configured, then accepts the first value
                         and ignore the rest.  If only one item
                         is configured regardless of the
                         self-configuration capability of ,
                         accepts the value as an explicit
                         configuration by the ACS.";
                    }
                    leaf QQualMin {
                      type string;
                      default "0";
                      description
                        "{{list}} Each item is a required minimum
                         received Ec/Io level on this UTRA FDD
                         carrier, specified in dB, with a numeric
                         range between -24 and 0 inclusive.  In
                         case there is more than one item in the
                         list, the first item contains the most
                         preferred value.  Corresponds to
                         parameter q-QualMin in SIB6 in
                         {{bibref|3GPP-TS.36.331|Section 6.3.1}}
                         and in {{bibref|3GPP-TS.25.304|Section
                         5.2.3.1.2}}.
                      
                         The multiplicity of the {{param}} values
                         can also be expressed by defining a
                         range using \"..\" (two periods) between
                         two values.  In this case, the
                         combination of two values defines the
                         lower-bound and upper-bound of the range
                         inclusive.  If this notation is used,
                         then the list contains at least 2 items:
                         \"<preferred-value>,<lower-bound>..<upper-bound>\".
                      
                         If supports self-configuration
                         capability for {{param}} and more than
                         one item is configured, then is expected
                         to select one from the list and
                         overwrite this parameter containing only
                         the one selected.  If does not support
                         self-configuration capability for
                         {{param}} and more than one item is
                         configured, then accepts the first value
                         and ignore the rest.  If only one item
                         is configured regardless of the
                         self-configuration capability of ,
                         accepts the value as an explicit
                         configuration by the ACS.";
                    }
                    leaf CellReselectionPriority {
                      type uint32 {
                        range "0..7";
                      }
                      default "0";
                      description
                        "Absolute priority of this UTRA FDD
                         frequency carrier, as used by the
                         inter-frequency cell re-selection
                         procedure.  Corresponds to parameter
                         CellReselectionPriority specified in
                         SIB6 in {{bibref|3GPP-TS.36.331|Section
                         6.3.1}} and in
                         {{bibref|3GPP-TS.36.304|Section
                         5.2.4.7}}.";
                    }
                    leaf ThreshXHigh {
                      type uint32 {
                        range "0..31";
                      }
                      default "0";
                      description
                        "Threshold used when re-selecting towards a
                         higher priority UTRA FDD frequency,
                         specified in {{units}}.  The value of
                         ({{param}} * 2) yields the actual value.
                         Corresponds to parameter threshX-High
                         specified in SIB6 in
                         {{bibref|3GPP-TS.36.331|Section 6.3.1}}
                         and in {{bibref|3GPP-TS.36.304|Section
                         5.2.4.5}}.";
                    }
                    leaf ThreshXLow {
                      type uint32 {
                        range "0..31";
                      }
                      default "0";
                      description
                        "Threshold used when re-selecting towards a
                         lower priority UTRA FDD frequency,
                         specified in {{units}}.  The value of
                         ({{param}} * 2) yields the actual value.
                         Corresponds to parameter threshX-Low
                         specified in SIB6 in
                         {{bibref|3GPP-TS.36.331|Section 6.3.1}}
                         and in {{bibref|3GPP-TS.36.304|Section
                         5.2.4.5}}.";
                    }
                    leaf PMaxUTRA {
                      type int32 {
                        range "-50..33";
                      }
                      default "0";
                      description
                        "Used to limit the allowed UE uplink
                         transmission power on this UTRA FDD
                         carrier frequency, specified in
                         {{units}}.  It is used to calculate the
                         parameter Pcompensation defined in
                         {{bibref|3GPP-TS.25.304|Section
                         5.2.3.1.2}}.  Corresponds to parameter
                         p-MaxUTRA specified in SIB6 in
                         {{bibref|3GPP-TS.36.331|Section 6.3.1}}.";
                    }
                  }
                }

                container GERAN {
                  description
                    "This object contains parameters relating to the
                     idle mode mobility configuration for
                     inter-RAT (Radio Access Technology)
                     re-selection, specifically for re-selection
                     to GERAN (GSM) scenario (see
                     {{bibref|3GPP-TS.32.592|Section
                     6.1.5.1.6}}).";
                  leaf TReselectionGERAN {
                    type string;
                    description
                      "{{list}} Each item is a cell re-selection
                       timer for re-selection to a GERAN
                       frequency carrier, specified in seconds,
                       with a numeric range between 0 and 7
                       inclusive.  In case there is more than one
                       item in the list, the first item contains
                       the most preferred value.  Corresponds to
                       parameter t-ReselectionGERAN specified in
                       SIB7 in {{bibref|3GPP-TS.36.331|Section
                       6.3.1}} and to TreselectionGERA in
                       {{bibref|3GPP-TS.36.304|Section 5.2.4.7}}.
                    
                       The multiplicity of the {{param}} values
                       can also be expressed by defining a range
                       using \"..\" (two periods) between two
                       values.  In this case, the combination of
                       two values defines the lower-bound and
                       upper-bound of the range inclusive.  If
                       this notation is used, then the list
                       contains at least 2 items:
                       \"<preferred-value>,<lower-bound>..<upper-bound>\".
                    
                       If supports self-configuration capability
                       for {{param}} and more than one item is
                       configured, then is expected to select one
                       from the list and overwrite this parameter
                       containing only the one selected.  If does
                       not support self-configuration capability
                       for {{param}} and more than one item is
                       configured, then accepts the first value
                       and ignore the rest.  If only one item is
                       configured regardless of the
                       self-configuration capability of , accepts
                       the value as an explicit configuration by
                       the ACS.";
                  }
                  leaf TReselectionGERANSFMedium {
                    type uint32 {
                      range "25 | 50 | 75 | 100";
                    }
                    description
                      "Scaling factor for TreselectionGERAN for
                       inter-RAT re-selection to GERAN in
                       Medium-mobility state.  The value of
                       {{param}} divided by 100 yields the actual
                       SF value.
                    
                       Corresponds to parameter
                       t-ReselectionGERAN-SF:sf-Medium specified
                       in SIB7 in {{bibref|3GPP-TS.36.331|Section
                       6.3.1}} and in
                       {{bibref|3GPP-TS.36.304|Section 5.2.4.3}}.";
                  }
                  leaf TReselectionGERANSFHigh {
                    type uint32 {
                      range "25 | 50 | 75 | 100";
                    }
                    description
                      "Scaling factor for TreselectionGERAN for
                       inter-RAT re-selection to GERAN in
                       High-mobility state.  The value of
                       {{param}} divided by 100 yields the actual
                       SF value.
                    
                       Corresponds to parameter
                       t-ReselectionGERAN-SF:sf-High specified in
                       SIB7 in {{bibref|3GPP-TS.36.331|Section
                       6.3.1}} and in
                       {{bibref|3GPP-TS.36.304|Section 5.2.4.3}}.";
                  }
                  leaf MaxGERANFreqGroupEntries {
                    type uint32;
                    config false;
                    description
                      "The maximum number of entries in the
                       {{object|.CellConfig.LTE.RAN.Mobility.IdleMode.IRAT.GERAN.GERANFreqGroup.{i}.}}
                       table.";
                  }

                  list GERANFreqGroup {
                    key "BCCHARFCN";
                    description
                      "This object contains parameters relating to
                       the channel frequncy related information
                       of GERAN (GSM) system (see
                       {{bibref|3GPP-TS.32.592|Section
                       6.1.5.1.7}}).";
                    leaf Enable {
                      type boolean;
                      default "false";
                      description
                        "Enables or disables this entry.";
                    }
                    leaf BandIndicator {
                      type enumeration {
                        enum "GSM850";
                        enum "GSM900";
                        enum "DCS1800";
                        enum "PCS1900";
                      }
                      default "GSM850";
                      description
                        "Indicates how to interpret the BCCH ARFCN.
                         {{enum}}";
                    }
                    leaf BCCHARFCN {
                      type uint32 {
                        range "0..1023";
                      }
                      default "0";
                      description
                        "ARFCN of this cell.";
                    }
                    leaf QRxLevMin {
                      type string;
                      default "0";
                      description
                        "{{list}} Each item is a required minimum
                         received RSSI level on this GERAN
                         frequency carrier for re-selection to
                         this UTRA FDD carrier, specified in dBm,
                         with a numeric range between 0 and 63
                         inclusive.  In case there is more than
                         one item in the list, the first item
                         contains the most preferred value.  The
                         value of ({{param}} * 2 - 115) yields
                         the actual value.  Corresponds to
                         parameter q-rxLevMin in SIB7 in
                         {{bibref|3GPP-TS.36.331|Section 6.3.1}}
                         and to RXLEV_ACCESS_MIN in
                         {{bibref|3GPP-TS.45.008}}.
                      
                         The multiplicity of the {{param}} values
                         can also be expressed by defining a
                         range using \"..\" (two periods) between
                         two values.  In this case, the
                         combination of two values defines the
                         lower-bound and upper-bound of the range
                         inclusive.  If this notation is used,
                         then the list contains at least 2 items:
                         \"<preferred-value>,<lower-bound>..<upper-bound>\".
                      
                         If supports self-configuration
                         capability for {{param}} and more than
                         one item is configured, then is expected
                         to select one from the list and
                         overwrite this parameter containing only
                         the one selected.  If does not support
                         self-configuration capability for
                         {{param}} and more than one item is
                         configured, then accepts the first value
                         and ignore the rest.  If only one item
                         is configured regardless of the
                         self-configuration capability of ,
                         accepts the value as an explicit
                         configuration by the ACS.";
                    }
                    leaf CellReselectionPriority {
                      type uint32 {
                        range "0..7";
                      }
                      default "0";
                      description
                        "Absolute priority of this GERAN frequency
                         group, as used by the inter-frequency
                         cell re-selection procedure.
                      
                         Corresponds to parameter
                         CellReselectionPriority specified in
                         SIB7 in {{bibref|3GPP-TS.36.331|Section
                         6.3.1}} and in
                         {{bibref|3GPP-TS.36.304|Section
                         5.2.4.7}}.";
                    }
                    leaf ThreshXHigh {
                      type uint32 {
                        range "0..31";
                      }
                      default "0";
                      description
                        "Threshold used when re-selecting towards a
                         higher priority GERAN frequency group
                         than current serving E-UTRA frequency,
                         specified in {{units}}.  The value of
                         ({{param}} * 2) yields the actual value.
                      
                         Corresponds to parameter threshX-High
                         specified in SIB7 in
                         {{bibref|3GPP-TS.36.331|Section 6.3.1}}
                         and in {{bibref|3GPP-TS.36.304|Section
                         5.2.4.5}}.";
                    }
                    leaf ThreshXLow {
                      type uint32 {
                        range "0..31";
                      }
                      default "0";
                      description
                        "Threshold used when re-selecting towards a
                         lower priority GERAN frequency group
                         than current serving E-UTRA frequency,
                         specified in {{units}} dB.  The value of
                         ({{param}} * 2) yields the actual value.
                         Corresponds to parameter threshX-Low
                         specified in SIB7 in
                         {{bibref|3GPP-TS.36.331|Section 6.3.1}}
                         and in {{bibref|3GPP-TS.36.304|Section
                         5.2.4.5}}.";
                    }
                  }
                }

                container CDMA2000 {
                  description
                    "This object contains parameters relating to the
                     idle mode mobility configuration for
                     inter-RAT (Radio Access Technology)
                     re-selection, specifically for re-selection
                     to CDMA2000 system scenario (see
                     {{bibref|3GPP-TS.32.592|Section
                     6.1.5.1.8}}).";
                  leaf SearchWindowSize {
                    type string;
                    description
                      "{{list}} Each item is a CDMA2000 parameter
                       affecting the search for neighbouring
                       pilots, with a numeric range between 0 and
                       15 inclusive.  In case there is more than
                       one item in the list, the first item
                       contains the most preferred value.
                       Corresponds to parameter searchWindowSize
                       in SIB8 in {{bibref|3GPP-TS.36.331|Section
                       6.3.1}} and in
                       {{bibref|3GPP2-C.S0005-A|Table
                       2.6.6.2.1-1}} and
                       {{bibref|3GPP2-C.S0024-A|Table
                       8.7.6.2-4}}.
                    
                       The multiplicity of the {{param}} values
                       can also be expressed by defining a range
                       using \"..\" (two periods) between two
                       values.  In this case, the combination of
                       two values defines the lower-bound and
                       upper-bound of the range inclusive.  If
                       this notation is used, then the list
                       contains at least 2 items:
                       \"<preferred-value>,<lower-bound>..<upper-bound>\".
                    
                       If supports self-configuration capability
                       for {{param}} and more than one item is
                       configured, then is expected to select one
                       from the list and overwrite this parameter
                       containing only the one selected.  If does
                       not support self-configuration capability
                       for {{param}} and more than one item is
                       configured, then accepts the first value
                       and ignore the rest.  If only one item is
                       configured regardless of the
                       self-configuration capability of , accepts
                       the value as an explicit configuration by
                       the ACS.";
                  }
                  leaf TReselectionCDMA2000 {
                    type string;
                    description
                      "{{list}} Each item is a cell re-selection
                       timer for a CDMA2000 band, specified in
                       seconds, with a numeric range between 0
                       and 7 inclusive.  In case there is more
                       than one item in the list, the first item
                       contains the most preferred value.
                       Corresponds to parameter
                       t-ReselectionCDMA2000 specified in SIB8 in
                       {{bibref|3GPP-TS.36.331|Section 6.3.1}}
                       and to TreselectionCDMA_HRPD or
                       TreselectionCDMA_1xRTT in
                       {{bibref|3GPP-TS.36.304|Section 5.2.4.7}}.
                    
                       The multiplicity of the {{param}} values
                       can also be expressed by defining a range
                       using \"..\" (two periods) between two
                       values.  In this case, the combination of
                       two values defines the lower-bound and
                       upper-bound of the range inclusive.  If
                       this notation is used, then the list
                       contains at least 2 items:
                       \"<preferred-value>,<lower-bound>..<upper-bound>\".
                    
                       If supports self-configuration capability
                       for {{param}} and more than one item is
                       configured, then is expected to select one
                       from the list and overwrite this parameter
                       containing only the one selected.  If does
                       not support self-configuration capability
                       for {{param}} and more than one item is
                       configured, then accepts the first value
                       and ignore the rest.  If only one item is
                       configured regardless of the
                       self-configuration capability of , accepts
                       the value as an explicit configuration by
                       the ACS.";
                  }
                  leaf TReselectionCDMA2000SFMedium {
                    type uint32 {
                      range "25 | 50 | 75 | 100";
                    }
                    description
                      "Scaling factor for TReselectionCDMA2000 for
                       inter-RAT re-selection to CDMA2000 in
                       Medium-mobility state.  The value of
                       {{param}} divided by 100 yields the actual
                       SF value.  Corresponds to parameter
                       t-ReselectionCDMA2000-SF:sf-Medium
                       specified in SIB8 in
                       {{bibref|3GPP-TS.36.331|Section 6.3.1}}
                       and in {{bibref|3GPP-TS.36.304|Section
                       5.2.4.3}}.";
                  }
                  leaf TReselectionCDMA2000SFHigh {
                    type uint32 {
                      range "25 | 50 | 75 | 100";
                    }
                    description
                      "Scaling factor for TReselectionCDMA2000 for
                       inter-RAT re-selection to CDMA2000 in
                       High-mobility state.  The value of
                       {{param}} divided by 100 yields the actual
                       SF value.  Corresponds to parameter
                       t-ReselectionCDMA2000-SF:sf-High specified
                       in SIB8 in {{bibref|3GPP-TS.36.331|Section
                       6.3.1}} and in
                       {{bibref|3GPP-TS.36.304|Section 5.2.4.3}}.";
                  }
                  leaf MaxCDMA2000BandEntries {
                    type uint32;
                    config false;
                    description
                      "The maximum number of entries in the
                       {{object|.CellConfig.LTE.RAN.Mobility.IdleMode.IRAT.CDMA2000.CDMA2000Band.{i}.}}
                       table.";
                  }

                  list CDMA2000Band {
                    key "BandClass";
                    description
                      "This object contains parameters relating to
                       the channel frequncy related information
                       of CDMA2000 system (see
                       {{bibref|3GPP-TS.32.592|Section
                       6.1.5.1.8}}).";
                    leaf Enable {
                      type boolean;
                      default "false";
                      description
                        "Enables or disables this entry.";
                    }
                    leaf BandClass {
                      type uint32 {
                        range "0..17";
                      }
                      default "0";
                      description
                        "Defines the CDMA2000 band in which the
                         CDMA2000 carrier frequency can be found,
                         specified in {{units}}.  BandClass is
                         defined in 3GPP2 C.S0057-B Table 1.5-1.
                      
                         Corresponds to parameter bandClass
                         specified in SIB8 in
                         {{bibref|3GPP-TS.36.331|Section 6.3.1}}.";
                    }
                    leaf CellReselectionPriority {
                      type uint32 {
                        range "0..7";
                      }
                      default "0";
                      description
                        "Absolute priority of this CDMA2000 band
                         used by the inter-frequency cell
                         re-selection procedure.  Corresponds to
                         parameter CellReselectionPriority
                         specified in SIB8 in
                         {{bibref|3GPP-TS.36.331|Section 6.3.1}}
                         and in {{bibref|3GPP-TS.36.304|Section
                         5.2.4.7}}.";
                    }
                    leaf ThreshXHigh {
                      type uint32 {
                        range "0..63";
                      }
                      default "0";
                      description
                        "Threshold used when re-selecting towards a
                         higher priority CDMA2000 band than
                         current serving E-UTRA frequency,
                         specified in {{units}}.  The value of
                         ({{param}} * 2) yields the actual value.
                         Corresponds to parameter threshX-High
                         specified in SIB8 in
                         {{bibref|3GPP-TS.36.331|Section 6.3.1}}
                         and in {{bibref|3GPP-TS.36.304|Section
                         5.2.4.5}}.";
                    }
                    leaf ThreshXLow {
                      type uint32 {
                        range "0..63";
                      }
                      default "0";
                      description
                        "Threshold used when re-selecting towards a
                         lower priority CDMA2000 band than
                         current serving E-UTRA frequency,
                         specified in {{units}}.  The value of
                         ({{param}} * 2) yields the actual value.
                         Corresponds to parameter threshX-Low
                         specified in SIB8 in
                         {{bibref|3GPP-TS.36.331|Section 6.3.1}}
                         and in {{bibref|3GPP-TS.36.304|Section
                         5.2.4.5}}.";
                    }
                  }
                }
              }
            }

            container ConnMode {
              description
                "This object contains parameters relating to the
                 UE's mobility while it is in connected mode
                 (handover).  Parameters under this object
                 determines the content in the SIB (System
                 Information Block) that is broadcast by LTE .";

              container EUTRA {
                description
                  "This object contains parameters relating to the
                   connected mode mobility (handover)
                   configuration within LTE system (see
                   {{bibref|3GPP-TS.32.592|Section 6.1.5.2.1}}).";
                leaf FilterCoefficientRSRP {
                  type string;
                  description
                    "{{list}} Each item is a filtering coefficient
                     used for RSRP measurements, with a numeric
                     range between 0 and 19 inclusive.  For
                     values greater than 9, only odd values are
                     valid.  If the value is other than these,
                     the CPE MUST reject the value.  In case
                     there is more than one item in the list, the
                     first item contains the most preferred
                     value.  Corresponds to filterCoefficientRSRP
                     parameter specified in QuantityConfigEUTRA
                     IE in {{bibref|3GPP-TS.36.331|Section
                     6.3.5}}.
                  
                     The multiplicity of the {{param}} values can
                     also be expressed by defining a range using
                     \"..\" (two periods) between two values.  In
                     this case, the combination of two values
                     defines the lower-bound and upper-bound of
                     the range inclusive.  If this notation is
                     used, then the list contains at least 2
                     items:
                     \"<preferred-value>,<lower-bound>..<upper-bound>\".
                  
                     If supports self-configuration capability
                     for {{param}} and more than one item is
                     configured, then is expected to select one
                     from the list and overwrite this parameter
                     containing only the one selected.  If does
                     not support self-configuration capability
                     for {{param}} and more than one item is
                     configured, then accepts the first value and
                     ignore the rest.  If only one item is
                     configured regardless of the
                     self-configuration capability of , accepts
                     the value as an explicit configuration by
                     the ACS.";
                }
                leaf FilterCoefficientRSRQ {
                  type string;
                  description
                    "{{list}} Each item is a filtering coefficient
                     used for RSRQ measurements, with a numeric
                     range between 0 and 19 inclusive.  For
                     values greater than 9, only odd values are
                     valid.  If the value is other than these,
                     the CPE MUST reject the value.  In case
                     there is more than one item in the list, the
                     first item contains the most preferred
                     value.  Corresponds to filterCoefficientRSRQ
                     parameter specified in QuantityConfigEUTRA
                     IE in {{bibref|3GPP-TS.36.331|Section
                     6.3.5}}.
                  
                     The multiplicity of the {{param}} values can
                     also be expressed by defining a range using
                     \"..\" (two periods) between two values.  In
                     this case, the combination of two values
                     defines the lower-bound and upper-bound of
                     the range inclusive.  If this notation is
                     used, then the list contains at least 2
                     items:
                     \"<preferred-value>,<lower-bound>..<upper-bound>\".
                  
                     If supports self-configuration capability
                     for {{param}} and more than one item is
                     configured, then is expected to select one
                     from the list and overwrite this parameter
                     containing only the one selected.  If does
                     not support self-configuration capability
                     for {{param}} and more than one item is
                     configured, then accepts the first value and
                     ignore the rest.  If only one item is
                     configured regardless of the
                     self-configuration capability of , accepts
                     the value as an explicit configuration by
                     the ACS.";
                }
                leaf A1ThresholdRSRP {
                  type uint32 {
                    range "0..97";
                  }
                  description
                    "Threshold to be used in EUTRA measurement
                     report triggering condition for event A1.
                     Valid only if {{param|TriggerQuantity}} is
                     {{enum|RSRP|TriggerQuantity}}.  Mapping to
                     actual values is specified in
                     {{bibref|3GPP-TS.36.133|Table 9.1.4-1}}.
                     Corresponds to parameter
                     a1-Threshold:threshold-RSRP specified in
                     ReportConfigEUTRA IE in
                     {{bibref|3GPP-TS.36.331|Section 6.3.5}}.";
                }
                leaf A1ThresholdRSRQ {
                  type uint32 {
                    range "0..34";
                  }
                  description
                    "Threshold to be used in EUTRA measurement
                     report triggering condition for event A1.
                     Valid only if {{param|TriggerQuantity}} is
                     {{enum|RSRQ|TriggerQuantity}}.  Mapping to
                     actual values is specified in 3GPP TS
                     36.133}} table 9.1.7-1.  Corresponds to
                     parameter a1-Threshold:threshold-RSRQ
                     specified in ReportConfigEUTRA IE in
                     {{bibref|3GPP-TS.36.331|Section 6.3.5}}.";
                }
                leaf A2ThresholdRSRP {
                  type uint32 {
                    range "0..97";
                  }
                  description
                    "Threshold to be used in EUTRA measurement
                     report triggering condition for event A2.
                     Valid only if {{param|TriggerQuantity}} is
                     {{enum|RSRP|TriggerQuantity}}.  Mapping to
                     actual values is specified in
                     {{bibref|3GPP-TS.36.133|Table 9.1.4-1}}.
                     Corresponds to parameter
                     a2-Threshold:threshold-RSRP specified in
                     ReportConfigEUTRA IE in
                     {{bibref|3GPP-TS.36.331|Section 6.3.5}}.";
                }
                leaf A2ThresholdRSRQ {
                  type uint32 {
                    range "0..34";
                  }
                  description
                    "Threshold to be used in EUTRA measurement
                     report triggering condition for event A2.
                     Valid only if {{param|TriggerQuantity}} is
                     {{enum|RSRQ|TriggerQuantity}}.  Mapping to
                     actual values is specified in
                     {{bibref|3GPP-TS.36.133|Table 9.1.7-1}}.
                     Corresponds to parameter
                     a2-Threshold:threshold-RSRQ specified in
                     ReportConfigEUTRA IE in
                     {{bibref|3GPP-TS.36.331|Section 6.3.5}}.";
                }
                leaf A3Offset {
                  type string;
                  description
                    "{{list}} Each item is an offset to be used in
                     evaluation of EUTRA measurement report
                     triggering condition for event A3, with a
                     numeric range between -30 and 30 inclusive.
                     In case there is more than one item in the
                     list, the first item contains the most
                     preferred value.  Mapping to actual values
                     is specified in {{bibref|3GPP-TS.36.133}}.
                     Corresponds to parameter a3-Offset specified
                     in ReportConfigEUTRA IE in
                     {{bibref|3GPP-TS.36.331|Section 6.3.5}}.
                  
                     The multiplicity of the {{param}} values can
                     also be expressed by defining a range using
                     \"..\" (two periods) between two values.  In
                     this case, the combination of two values
                     defines the lower-bound and upper-bound of
                     the range inclusive.  If this notation is
                     used, then the list contains at least 2
                     items:
                     \"<preferred-value>,<lower-bound>..<upper-bound>\".
                  
                     If supports self-configuration capability
                     for {{param}} and more than one item is
                     configured, then is expected to select one
                     from the list and overwrite this parameter
                     containing only the one selected.  If does
                     not support self-configuration capability
                     for {{param}} and more than one item is
                     configured, then accepts the first value and
                     ignore the rest.  If only one item is
                     configured regardless of the
                     self-configuration capability of , accepts
                     the value as an explicit configuration by
                     the ACS.";
                }
                leaf ReportOnLeave {
                  type boolean;
                  description
                    "Indicates whether or not the UE shall initiate
                     the measurement reporting procedure when the
                     leaving condition is met for event A3 for a
                     cell in cellsTriggeredList, as specified in
                     {{bibref|3GPP-TS.36.331|Section 5.5.4.1 and
                     Section 6.3.5}}.";
                }
                leaf A4ThresholdRSRP {
                  type uint32 {
                    range "0..97";
                  }
                  description
                    "Threshold to be used in EUTRA measurement
                     report triggering condition for event A4.
                     Valid only if {{param|TriggerQuantity}} is
                     {{enum|RSRP|TriggerQuantity}}.  Mapping to
                     actual values is specified in
                     {{bibref|3GPP-TS.36.133}}.  Corresponds to
                     parameter a4-Threshold:threshold-RSRP
                     specified in ReportConfigEUTRA IE in
                     {{bibref|3GPP-TS.36.331|Section 6.3.5}}.";
                }
                leaf A4ThresholdRSRQ {
                  type uint32 {
                    range "0..34";
                  }
                  description
                    "Threshold to be used in EUTRA measurement
                     report triggering condition for event A4.
                     Valid only if {{param|TriggerQuantity}} is
                     {{enum|RSRQ|TriggerQuantity}}.  Mapping to
                     actual values is specified in
                     {{bibref|3GPP-TS.36.133}}.  Corresponds to
                     parameter a4-Threshold:threshold-RSRQ
                     specified in ReportConfigEUTRA IE in
                     {{bibref|3GPP-TS.36.331|Section 6.3.5}}.";
                }
                leaf A5Threshold1RSRP {
                  type uint32 {
                    range "0..97";
                  }
                  description
                    "Threshold1 to be used in EUTRA measurement
                     report triggering condition for event A5.
                     Valid only if {{param|TriggerQuantity}} is
                     {{enum|RSRP|TriggerQuantity}}.  Mapping to
                     actual values is specified in
                     {{bibref|3GPP-TS.36.133}}.  Corresponds to
                     parameter a5-Threshold1:threshold-RSRP
                     specified in ReportConfigEUTRA IE in
                     {{bibref|3GPP-TS.36.331|Section 6.3.5}}.";
                }
                leaf A5Threshold1RSRQ {
                  type uint32 {
                    range "0..34";
                  }
                  description
                    "Threshold1 to be used in EUTRA measurement
                     report triggering condition for event A5.
                     Valid only if {{param|TriggerQuantity}} is
                     {{enum|RSRQ|TriggerQuantity}}.  Mapping to
                     actual values is specified in
                     {{bibref|3GPP-TS.36.133}}.  Corresponds to
                     parameter a5-Threshold1:threshold-RSRQ
                     specified in ReportConfigEUTRA IE in
                     {{bibref|3GPP-TS.36.331|Section 6.3.5}}.";
                }
                leaf A5Threshold2RSRP {
                  type uint32 {
                    range "0..97";
                  }
                  description
                    "Threshold2 to be used in EUTRA measurement
                     report triggering condition for event A5.
                     Valid only if {{param|TriggerQuantity}} is
                     {{enum|RSRP|TriggerQuantity}}.  Mapping to
                     actual values is specified in
                     {{bibref|3GPP-TS.36.133}}.  Corresponds to
                     parameter a5-Threshold2:threshold-RSRP
                     specified in ReportConfigEUTRA IE in
                     {{bibref|3GPP-TS.36.331|Section 6.3.5}}.";
                }
                leaf A5Threshold2RSRQ {
                  type uint32 {
                    range "0..34";
                  }
                  description
                    "Threshold2 to be used in EUTRA measurement
                     report triggering condition for event A5.
                     Valid only if {{param|TriggerQuantity}} is
                     {{enum|RSRQ|TriggerQuantity}}.  Mapping to
                     actual values is specified in
                     {{bibref|3GPP-TS.36.133}}.  Corresponds to
                     parameter a5-Threshold2:threshold-RSRQ
                     specified in ReportConfigEUTRA IE in
                     {{bibref|3GPP-TS.36.331|Section 6.3.5}}.";
                }
                leaf Hysteresis {
                  type string;
                  description
                    "{{list}} Each item is a hysteresis value
                     applied to entry and leave condition of a
                     report triggering event, with a numeric
                     range between 0 and 30 inclusive.  In case
                     there is more than one item in the list, the
                     first item contains the most preferred
                     value.  Corresponds to parameter hysteresis
                     specified in ReportConfigEUTRA IE in
                     {{bibref|3GPP-TS.36.331|Section 6.3.5}}.
                  
                     The multiplicity of the {{param}} values can
                     also be expressed by defining a range using
                     \"..\" (two periods) between two values.  In
                     this case, the combination of two values
                     defines the lower-bound and upper-bound of
                     the range inclusive.  If this notation is
                     used, then the list contains at least 2
                     items:
                     \"<preferred-value>,<lower-bound>..<upper-bound>\".
                  
                     If supports self-configuration capability
                     for {{param}} and more than one item is
                     configured, then is expected to select one
                     from the list and overwrite this parameter
                     containing only the one selected.  If does
                     not support self-configuration capability
                     for {{param}} and more than one item is
                     configured, then accepts the first value and
                     ignore the rest.  If only one item is
                     configured regardless of the
                     self-configuration capability of , accepts
                     the value as an explicit configuration by
                     the ACS.";
                }
                leaf TimeToTrigger {
                  type uint32 {
                    range "0 | 40 | 64 | 80 | 100 | 128 | 160 | 256 | 320 | 480 | 512 | 640 | 1024 | 1280 | 2560 | 5120";
                  }
                  description
                    "{{list}} Each item is a time period during
                     which measurement report triggering
                     condition needs to be met in order to
                     trigger a measurement report, specified in
                     milliseconds.  In case there is more than
                     one item in the list, the first item
                     contains the most preferred value.
                     Corresponds to parameter timeToTrigger
                     specified in ReportConfigEUTRA IE in
                     {{bibref|3GPP-TS.36.331|Section 6.3.5}}.
                  
                     If supports self-configuration capability
                     for {{param}} and more than one item is
                     configured, then is expected to select one
                     from the list and overwrite this parameter
                     containing only the one selected.  If does
                     not support self-configuration capability
                     for {{param}} and more than one item is
                     configured, then accepts the first value and
                     ignore the rest.  If only one item is
                     configured regardless of the
                     self-configuration capability of , accepts
                     the value as an explicit configuration by
                     the ACS.";
                }
                leaf TriggerQuantity {
                  type enumeration {
                    enum "RSRP";
                    enum "RSRQ";
                  }
                  description
                    "Quantities used to evaluate a measurement
                     report triggering condition.  Corresponds to
                     parameter triggerQuantity specified in
                     ReportConfigEUTRA IE in
                     {{bibref|3GPP-TS.36.331|Section 6.3.5}}.";
                }
                leaf ReportQuantity {
                  type enumeration {
                    enum "SameAsTriggerQuantity";
                    enum "Both";
                  }
                  description
                    "Measrument quantities to be included in the
                     measurement report.  Corresponds to
                     parameter reportQuantity specified in
                     ReportConfigEUTRA IE in
                     {{bibref|3GPP-TS.36.331|Section 6.3.5}}.
                     The value {{enum|Both}} specifies that both
                     the RSRP and RSRQ quantities are to be
                     included in the measurement report.";
                }
                leaf MaxReportCells {
                  type uint32 {
                    range "1..8";
                  }
                  config false;
                  description
                    "Maximum number of cells that can be included in
                     a measurement report.  Corresponds to
                     parameter maxReportCells specified in
                     ReportConfigEUTRA IE in
                     {{bibref|3GPP-TS.36.331|Section 6.3.5}}.";
                }
                leaf ReportInterval {
                  type uint32 {
                    range "120 | 240 | 480 | 640 | 1024 | 2048 | 5120 | 10240 | 60000 | 360000 | 720000 | 1800000 | 3600000";
                  }
                  description
                    "Interval between successive measurement
                     reports, specified in {{units}}.
                     Corresponds to parameter reportInterval
                     specified in ReportConfigEUTRA IE in
                     {{bibref|3GPP-TS.36.331|Section 6.3.5}}.";
                }
                leaf ReportAmount {
                  type uint32 {
                    range "0..2 | 4 | 8 | 16 | 32 | 64";
                  }
                  description
                    "Number of times a measurement report is sent.
                     Corresponds to parameter reportAmount
                     specified in ReportConfigEUTRA IE in
                     {{bibref|3GPP-TS.36.331|Section 6.3.5}}.
                     Value of 0 indicates \"infinity.\"";
                }
              }

              container IRAT {
                description
                  "This object contains parameters relating to the
                   connected mode mobility (handover)
                   configuration that is common to all inter-RAT
                   handover scenarios (UTRA (UMTS), GERAN (GSM)
                   and CDMA2000) (see
                   {{bibref|3GPP-TS.32.592|Section 6.1.5.2.2}}).";
                leaf QoffsettUTRA {
                  type string;
                  description
                    "{{list}} Each item is a UTRA-specific offset to
                     be applied when evaluating triggering
                     conditions for measurement reporting in
                     connected mode, with a numeric range between
                     -15 and 15 inclusive.  In case there is more
                     than one item in the list, the first item
                     contains the most preferred value.
                     Corresponds to parameter offsetFreq included
                     in the IE MeasObjectUTRA specified in
                     {{bibref|3GPP-TS.36.331}}.
                  
                     The multiplicity of the {{param}} values can
                     also be expressed by defining a range using
                     \"..\" (two periods) between two values.  In
                     this case, the combination of two values
                     defines the lower-bound and upper-bound of
                     the range inclusive.  If this notation is
                     used, then the list contains at least 2
                     items:
                     \"<preferred-value>,<lower-bound>..<upper-bound>\".
                  
                     If supports self-configuration capability
                     for {{param}} and more than one item is
                     configured, then is expected to select one
                     from the list and overwrite this parameter
                     containing only the one selected.  If does
                     not support self-configuration capability
                     for {{param}} and more than one item is
                     configured, then accepts the first value and
                     ignore the rest.  If only one item is
                     configured regardless of the
                     self-configuration capability of , accepts
                     the value as an explicit configuration by
                     the ACS.";
                }
                leaf FilterCoefficientUTRA {
                  type string;
                  description
                    "{{list}} Each item is a filtering coefficient
                     used for UTRA measurements, with a numeric
                     range between 0 and 19 inclusive.  For
                     values greater than 9, only odd values are
                     valid.  If the value is other than these,
                     the CPE MUST reject the value.  In case
                     there is more than one item in the list, the
                     first item contains the most preferred
                     value.  Corresponds to filterCoefficient
                     parameter specified in QuantityConfigUTRA IE
                     in {{bibref|3GPP-TS.36.331|Section 6.3.5}}.
                  
                     The multiplicity of the {{param}} values can
                     also be expressed by defining a range using
                     \"..\" (two periods) between two values.  In
                     this case, the combination of two values
                     defines the lower-bound and upper-bound of
                     the range inclusive.  If this notation is
                     used, then the list contains at least 2
                     items:
                     \"<preferred-value>,<lower-bound>..<upper-bound>\".
                  
                     If supports self-configuration capability
                     for {{param}} and more than one item is
                     configured, then is expected to select one
                     from the list and overwrite this parameter
                     containing only the one selected.  If does
                     not support self-configuration capability
                     for {{param}} and more than one item is
                     configured, then accepts the first value and
                     ignore the rest.  If only one item is
                     configured regardless of the
                     self-configuration capability of , accepts
                     the value as an explicit configuration by
                     the ACS.";
                }
                leaf MeasQuantityUTRAFDD {
                  type enumeration {
                    enum "CPICH-RSCP";
                    enum "CPICH-EcN0";
                  }
                  description
                    "Measurement quantity used for UTRA
                     measurements.  Corresponds to
                     measQuantityUTRA-FDD parameter specified in
                     QuantityConfigUTRA IE in
                     {{bibref|3GPP-TS.36.331|Section 6.3.5}}.";
                }
                leaf B1ThresholdUTRARSCP {
                  type int32 {
                    range "-5..91";
                  }
                  description
                    "RSCP threshold to be used in UTRA measurement
                     report triggering condition for event B1.
                     Mapping to actual {{units}} values is
                     specified in 3GPP TS 25.133}}.  Corresponds
                     to parameter b1-ThresholdUTRA:utra-RSCP
                     specified in ReportConfigInterRAT IE in
                     {{bibref|3GPP-TS.36.331|Section 6.3.5}}.";
                }
                leaf B1ThresholdUTRAEcN0 {
                  type uint32 {
                    range "0..49";
                  }
                  description
                    "EcNo threshold to be used in UTRA measurement
                     report triggering condition for event B1.
                     Mapping to actual {{units}} values is
                     specified in 3GPP TS 25.133}}.  Corresponds
                     to parameter b1-ThresholdUTRA:utra-EcNo
                     specified in ReportConfigInterRAT IE in
                     {{bibref|3GPP-TS.36.331|Section 6.3.5}}.";
                }
                leaf QoffsetGERAN {
                  type string;
                  description
                    "{{list}} Each item is a GERAN-specific offset
                     to be applied when evaluating triggering
                     conditions for measurement reporting in
                     connected mode, with a numeric range between
                     -15 and 15 inclusive.  In case there is more
                     than one item in the list, the first item
                     contains the most preferred value.
                     Corresponds to parameter offsetFreq included
                     in the IE MeasObjectGERAN specified in
                     {{bibref|3GPP-TS.36.331}}.
                  
                     The multiplicity of the {{param}} values can
                     also be expressed by defining a range using
                     \"..\" (two periods) between two values.  In
                     this case, the combination of two values
                     defines the lower-bound and upper-bound of
                     the range inclusive.  If this notation is
                     used, then the list contains at least 2
                     items:
                     \"<preferred-value>,<lower-bound>..<upper-bound>\".
                  
                     If supports self-configuration capability
                     for {{param}} and more than one item is
                     configured, then is expected to select one
                     from the list and overwrite this parameter
                     containing only the one selected.  If does
                     not support self-configuration capability
                     for {{param}} and more than one item is
                     configured, then accepts the first value and
                     ignore the rest.  If only one item is
                     configured regardless of the
                     self-configuration capability of , accepts
                     the value as an explicit configuration by
                     the ACS.";
                }
                leaf FilterCoefficientGERAN {
                  type string;
                  description
                    "{{list}} Each item is a filtering coefficient
                     used for GERAN measurements, with a numeric
                     range between 0 and 19 inclusive.  For
                     values greater than 9, only odd values are
                     valid.  If the value is other than these,
                     the CPE MUST reject the value.  In case
                     there is more than one item in the list, the
                     first item contains the most preferred
                     value.  Corresponds to filterCoefficient
                     parameter specified in QuantityConfigGERAN
                     IE in {{bibref|3GPP-TS.36.331|Section
                     6.3.5}}.
                  
                     The multiplicity of the {{param}} values can
                     also be expressed by defining a range using
                     \"..\" (two periods) between two values.  In
                     this case, the combination of two values
                     defines the lower-bound and upper-bound of
                     the range inclusive.  If this notation is
                     used, then the list contains at least 2
                     items:
                     \"<preferred-value>,<lower-bound>..<upper-bound>\".
                  
                     If supports self-configuration capability
                     for {{param}} and more than one item is
                     configured, then is expected to select one
                     from the list and overwrite this parameter
                     containing only the one selected.  If does
                     not support self-configuration capability
                     for {{param}} and more than one item is
                     configured, then accepts the first value and
                     ignore the rest.  If only one item is
                     configured regardless of the
                     self-configuration capability of , accepts
                     the value as an explicit configuration by
                     the ACS.";
                }
                leaf B1ThresholdGERAN {
                  type uint32 {
                    range "0..63";
                  }
                  description
                    "Threshold to be used in GERAN measurement
                     report triggering condition for event B1.
                     Mapping to actual {{units}} values is
                     specified in 3GPP TS 45.008}}.  Corresponds
                     to parameter b1-ThresholdGERAN specified in
                     ReportConfigInterRAT IE in
                     {{bibref|3GPP-TS.36.331|Section 6.3.5}}.";
                }
                leaf QoffsetCDMA2000 {
                  type string;
                  description
                    "{{list}} Each item is a CDMA2000-specific
                     offset to be applied when evaluating
                     triggering conditions for measurement
                     reporting in connected mode, with a numeric
                     range between -15 and 15 inclusive.  In case
                     there is more than one item in the list, the
                     first item contains the most preferred
                     value.  Corresponds to parameter offsetFreq
                     included in the IE MeasObjectCDMA2000
                     specified in {{bibref|3GPP-TS.36.331}}.
                  
                     The multiplicity of the {{param}} values can
                     also be expressed by defining a range using
                     \"..\" (two periods) between two values.  In
                     this case, the combination of two values
                     defines the lower-bound and upper-bound of
                     the range inclusive.  If this notation is
                     used, then the list contains at least 2
                     items:
                     \"<preferred-value>,<lower-bound>..<upper-bound>\".
                  
                     If supports self-configuration capability
                     for {{param}} and more than one item is
                     configured, then is expected to select one
                     from the list and overwrite this parameter
                     containing only the one selected.  If does
                     not support self-configuration capability
                     for {{param}} and more than one item is
                     configured, then accepts the first value and
                     ignore the rest.  If only one item is
                     configured regardless of the
                     self-configuration capability of , accepts
                     the value as an explicit configuration by
                     the ACS.";
                }
                leaf MeasQuantityCDMA2000 {
                  type enumeration {
                    enum "PilotStrength";
                    enum "PilotPnPhaseAndPilotStrength";
                  }
                  description
                    "Measurement quantity used for CDMA2000
                     measurements.  Corresponds to
                     measQuantityCDMA2000 parameter specified in
                     QuantityConfigCDMA2000 IE in
                     {{bibref|3GPP-TS.36.331|Section 6.3.5}}.";
                }
                leaf B1ThresholdCDMA2000 {
                  type uint32 {
                    range "0..63";
                  }
                  description
                    "Threshold to be used in CDMA2000 measurement
                     report triggering condition for event B1.
                     Mapping to actual {{units}} values is
                     specified in {{bibref|3GPP-TS.45.008}}.
                     Corresponds to parameter
                     b1-ThresholdCDMA2000 specified in
                     ReportConfigInterRAT IE in
                     {{bibref|3GPP-TS.36.331|Section 6.3.5}}.";
                }
                leaf B2Threshold2UTRARSCP {
                  type int32 {
                    range "-5..91";
                  }
                  description
                    "RSCP threshold to be used in UTRA measurement
                     report triggering condition for event B2.
                     Mapping to actual {{units}} values is
                     specified in {{bibref|3GPP-TS.25.133}}.
                     Corresponds to parameter
                     b2-Threshold2UTRA:utra-RSCP specified in
                     ReportConfigInterRAT IE in
                     {{bibref|3GPP-TS.36.331|Section 6.3.5}}.";
                }
                leaf B2Threshold2UTRAEcN0 {
                  type uint32 {
                    range "0..49";
                  }
                  description
                    "EcNo threshold to be used in UTRA measurement
                     report triggering condition for event B2.
                     Mapping to actual {{units}} values is
                     specified in 3GPP TS 25.133}}.  Corresponds
                     to parameter b2-Threshold2UTRA:utra-EcNo
                     specified in ReportConfigInterRAT IE in
                     {{bibref|3GPP-TS.36.331|Section 6.3.5}}.";
                }
                leaf B2Threshold2GERAN {
                  type uint32 {
                    range "0..63";
                  }
                  description
                    "Threshold to be used in GERAN measurement
                     report triggering condition for event B2.
                     Mapping to actual {{units}} values is
                     specified in 3GPP TS 45.008}}.  Corresponds
                     to parameter b2-Threshold2GERAN specified in
                     ReportConfigInterRAT IE in
                     {{bibref|3GPP-TS.36.331|Section 6.3.5}}.";
                }
                leaf B2Threshold2CDMA2000 {
                  type uint32 {
                    range "0..63";
                  }
                  description
                    "Threshold to be used in CDMA2000 measurement
                     report triggering condition for event B2.
                     Mapping to actual {{units}} values is
                     specified in 3GPP TS 45.008}}.  Corresponds
                     to parameter b2-Threshold2CDMA2000 specified
                     in ReportConfigInterRAT IE in
                     {{bibref|3GPP-TS.36.331|Section 6.3.5}}.";
                }
                leaf Hysteresis {
                  type string;
                  description
                    "{{list}} Each item is a hysteresis value
                     applied to entry and leave condition of an
                     IRAT report triggering event, with a numeric
                     range between 0 and 30 inclusive.  In case
                     there is more than one item in the list, the
                     first item contains the most preferred
                     value.  Corresponds to parameter hysteresis
                     specified in ReportConfigInterRAT IE in
                     {{bibref|3GPP-TS.36.331|Section 6.3.5}}.
                  
                     The multiplicity of the {{param}} values can
                     also be expressed by defining a range using
                     \"..\" (two periods) between two values.  In
                     this case, the combination of two values
                     defines the lower-bound and upper-bound of
                     the range inclusive.  If this notation is
                     used, then the list contains at least 2
                     items:
                     \"<preferred-value>,<lower-bound>..<upper-bound>\".
                  
                     If supports self-configuration capability
                     for {{param}} and more than one item is
                     configured, then is expected to select one
                     from the list and overwrite this parameter
                     containing only the one selected.  If does
                     not support self-configuration capability
                     for {{param}} and more than one item is
                     configured, then accepts the first value and
                     ignore the rest.  If only one item is
                     configured regardless of the
                     self-configuration capability of , accepts
                     the value as an explicit configuration by
                     the ACS.";
                }
                leaf TimeToTrigger {
                  type uint32 {
                    range "0 | 40 | 64 | 80 | 100 | 128 | 160 | 256 | 320 | 480 | 512 | 640 | 1024 | 1280 | 2560 | 5120";
                  }
                  description
                    "{{list}} Each item is a time period during
                     which IRAT measurement report triggering
                     condition needs to be met in order to
                     trigger IRAT measurement report, specified
                     in milliseconds.  In case there is more than
                     one item in the list, the first item
                     contains the most preferred value..
                     Corresponds to parameter timeToTrigger
                     specified in ReportConfigInterRAT IE in
                     {{bibref|3GPP-TS.36.331|Section 6.3.5}}.
                  
                     If supports self-configuration capability
                     for {{param}} and more than one item is
                     configured, then is expected to select one
                     from the list and overwrite this parameter
                     containing only the one selected.  If does
                     not support self-configuration capability
                     for {{param}} and more than one item is
                     configured, then accepts the first value and
                     ignore the rest.  If only one item is
                     configured regardless of the
                     self-configuration capability of , accepts
                     the value as an explicit configuration by
                     the ACS.";
                }
                leaf MaxReportCells {
                  type uint32 {
                    range "1..8";
                  }
                  config false;
                  description
                    "Maximum number of IRAT cells that can be
                     included in a measurement report.
                     Corresponds to parameter maxReportCells
                     specified in ReportConfigInterRAT IE in
                     {{bibref|3GPP-TS.36.331|Section 6.3.5}}.";
                }
                leaf ReportInterval {
                  type uint32 {
                    range "120 | 240 | 480 | 640 | 1024 | 2048 | 5120 | 10240 | 60000 | 360000 | 720000 | 1800000 | 3600000";
                  }
                  description
                    "Interval between successive IRAT measurement
                     reports, specified in {{units}}.
                     Corresponds to parameter reportInterval
                     specified in ReportConfigInterRAT IE in
                     {{bibref|3GPP-TS.36.331|Section 6.3.5}}.";
                }
                leaf ReportAmount {
                  type uint32 {
                    range "0..2 | 4 | 8 | 16 | 32 | 64";
                  }
                  description
                    "Number of times an IRAT measurement report is
                     sent.  Corresponds to parameter reportAmount
                     specified in ReportConfigInterRAT IE in
                     {{bibref|3GPP-TS.36.331|Section 6.3.5}}.
                     Value of 0 indicates \"infinity.\"";
                }
              }
            }
          }

          container NeighborList {
            description
              "This object contains parameters relating to the
               neighbor list.";
            leaf MaxLTECellEntries {
              type uint32;
              config false;
              description
                "The maximum number of entries in the
                 {{object|.CellConfig.LTE.RAN.NeighborList.LTECell.{i}.}}
                 table.";
            }

            list LTECell {
              key "PLMNID CID";
              description
                "Table containing the E-UTRA (i.e.  intra-RAT) cell
                 list provided by the ACS.  The table contents
                 MAY be added/deleted/modified during operation,
                 in which case these changes shall be reflected
                 in the broadcast information as soon as
                 possible.";
              leaf Enable {
                type boolean;
                default "false";
                description
                  "Enables or disables this entry.";
              }
              leaf MustInclude {
                type boolean;
                default "false";
                description
                  "Indicates whether this instance of the neighbor
                   shall be included or excluded in the FAP's NL
                   configuration.";
              }
              leaf PLMNID {
                type string {
                  length "0..6";
                }
                default "";
                description
                  "PLMN ID consists of Mobile Country Code (MCC) and
                   Mobile Network Code (MNC)
                   {{bibref|3GPP-TS.23.003}},
                   {{bibref|3GPP-TS.24.008}}.
                
                   Mobile Country Code consists of three digits
                   and uniquely identifies the country of
                   domicile of the subscriber.
                
                   Mobile Network Code consists of two or three
                   digits and identifies the Home PLMN within a
                   country.
                
                   For a 2-digit MNC the total string length of
                   {{param}} is 5.";
              }
              leaf CID {
                type uint32 {
                  range "1..268435455";
                }
                default "1";
                description
                  "Cell Identity.  {{bibref|3GPP-TS.36.331|Section
                   6.3.4}}.  Combination of {{param|PLMNID}} and
                   {{param}} constitutes the Cell Global ID
                   (CGI).";
              }
              leaf EUTRACarrierARFCN {
                type uint32 {
                  range "0..65535";
                }
                default "0";
                description
                  "Indicates the ARFCN of this carrier frequency.
                   Corresponds to parameter dl-CarrierFreq in
                   SIB5 in {{bibref|3GPP-TS.36.331|Section
                   6.3.1}}, and and parameter NDL in
                   {{bibref|3GPP-TS.36.101|Section 5.7.3}}.  If
                   the value of {{param}} is the same with the
                   one currently being used by the, then it
                   implies that this neighbor cell is an
                   intra-frequency cell; otherwise, it is an
                   inter-frequency cell.";
              }
              leaf PhyCellID {
                type uint32 {
                  range "0..503";
                }
                default "0";
                description
                  "Physical cell ID, as specified in
                   {{bibref|3GPP-TS.36.211|Section 6.11}}.";
              }
              leaf QOffset {
                type int32 {
                  range "-24..-8 | -6..6 | 8..24";
                }
                default "0";
                description
                  "Indicate a cell-specific offset applicable to a
                   specific neighbouring cell.  It is used for
                   evaluating the cell as a candidate for cell
                   re-selection in idle mode.  Corresponds to
                   parameter q-OffsetCell broadcast in SIB4 for
                   intra-frequency cells and in SIB5 for
                   inter-frequency cells, specified in
                   {{bibref|3GPP-TS.36.331|Section 6.3.1}}.  For
                   the value less than or equal to -8, and bigger
                   than or equal to 8, only even numbers are
                   valid.  If the value is other than these, the
                   CPE MUST reject the value.";
              }
              leaf CIO {
                type int32 {
                  range "-24..-8 | -6..6 | 8..24";
                }
                default "0";
                description
                  "Cell individual offset applicable to a specific
                   neighbouring cell.  It is used for evaluating
                   triggering conditions for measurement
                   reporting in connected mode.  Specified by
                   cellIndividualOffset in MeasObjectEUTRA IE in
                   {{bibref|3GPP-TS.36.331|Section 6.3.5}}.  For
                   the value less than or equal to -8, and bigger
                   than or equal to 8, only even numbers are
                   valid.  If the value is other than these, the
                   CPE MUST reject the value.";
              }
              leaf RSTxPower {
                type int32 {
                  range "-60..50";
                }
                default "0";
                description
                  "The downlink reference-signal transmit power,
                   specified in {{units}}.  Defined as the linear
                   average over the power contributions (in W) of
                   all resource elements that carry cell-specific
                   reference signals within the operating system
                   bandwidth.  Corresponds to parameter
                   referenceSignalPower in SIB4 as a part of
                   PDSCH-Config IE in
                   {{bibref|3GPP-TS.36.331|Section 6.3.2}}.";
              }
              leaf Blacklisted {
                type boolean;
                default "false";
                description
                  "Indicates whether this neighbor cell is allowed
                   for UEs as handover target or not.  If
                   {{true}}, handover is prohibited towards this
                   cell.  If {{false}}, handover is allowed
                   toward this cell.  The {{param}} parameter
                   allows this cell to be prohibited as a
                   handover target, while still allowing this
                   cell to be included in the BCCH SIB4 or 5.";
              }
            }

            container InterRATCell {
              description
                "The inter-RAT cell lists separated by technology.
                 {{bibref|3GPP-TS.36.331|Section 6.3.1 (SIB6, 7,
                 8)}}.";
              leaf MaxUMTSEntries {
                type uint32;
                config false;
                description
                  "The maximum number of entries in the
                   {{object|.CellConfig.LTE.RAN.NeighborList.InterRATCell.UMTS.{i}.}}
                   table.  There can be maximum of 16 UTRAN
                   (UMTS) neighbor cells, as specified by
                   carrierFreqListUTRA-FDD in SIB6 in
                   {{bibref|3GPP-TS.36.331|Section 6.3.1}}.";
              }
              leaf MaxGSMEntries {
                type uint32;
                config false;
                description
                  "The maximum number of entries in the
                   {{object|.CellConfig.LTE.RAN.NeighborList.InterRATCell.GSM.{i}.}}
                   table.  There can be maximum of 16 GERAN (GSM)
                   neighbor cells, as specified by
                   carrierFreqsInfoList in SIB7 in
                   {{bibref|3GPP-TS.36.331|Section 6.3.1}}.";
              }
              leaf MaxCDMA2000Entries {
                type uint32;
                config false;
                description
                  "The maximum number of entries in the
                   {{object|.CellConfig.LTE.RAN.NeighborList.InterRATCell.CDMA2000.{i}.}}
                   table.  There can be maximum of 32
                   bandclasses.  In each bandclass, there can be
                   maximum of 16 CDMA2000 carrier frequencies.
                   In each carrier, there can be maximum of 16
                   CDMA2000 neighbor cells (PN offset).  It is
                   specified by neighCellList in SIB8 in
                   {{bibref|3GPP-TS.36.331|Section 6.3.1}}.";
              }

              list UMTS {
                key "PLMNID CID";
                description
                  "Table containing the inter-RAT cell list for UTRA
                   (UMTS) provided by the ACS.  The table
                   contents MAY be added/deleted/modified during
                   operation, in which case these changes shall
                   be reflected in the broadcast information as
                   soon as possible.";
                leaf Enable {
                  type boolean;
                  default "false";
                  description
                    "Enables or disables this entry.";
                }
                leaf MustInclude {
                  type boolean;
                  default "false";
                  description
                    "Indicates whether this instance of the neighbor
                     shall be included or excluded in the FAP's
                     NL configuration.";
                }
                leaf PLMNID {
                  type string {
                    length "0..6";
                  }
                  default "";
                  description
                    "PLMN ID consists of Mobile Country Code (MCC)
                     and Mobile Network Code (MNC)
                     {{bibref|3GPP-TS.23.003}},
                     {{bibref|3GPP-TS.24.008}}.
                  
                     Mobile Country Code consists of three digits
                     and uniquely identifies the country of
                     domicile of the subscriber.
                  
                     Mobile Network Code consists of two or three
                     digits and identifies the Home PLMN within a
                     country.
                  
                     For a 2-digit MNC the total string length of
                     {{param}} is 5.";
                }
                leaf RNCID {
                  type uint32 {
                    range "0..65535";
                  }
                  default "0";
                  description
                    "RNC-ID of an intra-RAT UMTS neighbor cell.  It
                     uniquely identifies an RNC within a PLMN.
                  
                     Normally, RNC-ID consists of 12 bits (i.e.
                     a range of [0:4095]).  However, if the value
                     is larger than 4095, then Extended RNC-ID
                     (range of [4096:65535]) is used in RANAP.
                  
                     The RNC-ID and Extended RNC-ID are combined
                     into a single parameter here as there is no
                     explicit need to have them separated.
                  
                     {{bibref|3GPP-TS.25.413|Section 9.2.1.39}}";
                }
                leaf CID {
                  type uint32 {
                    range "1..65535";
                  }
                  default "1";
                  description
                    "Cell Identifier (C-id) that identifies a cell
                     within an RNS.  This Cell Identifier
                     together with the controlling RNC (RNC-ID)
                     constitutes the UTRAN Cell ID (UC-ID) and is
                     used to identify a cell uniquely within
                     UTRAN.  C-ID is either 12-bit or 16-bit
                     value.  {{bibref|3GPP-TS.25.401|Section
                     6.1.5}}.";
                }
                leaf LAC {
                  type uint32 {
                    range "0..65535";
                  }
                  default "0";
                  description
                    "Location Area Code (LAC).  The concatenation of
                     PLMN ID (MCC+MNC) and LAC uniquely
                     identifies the Location Area ID (LAI).
                  
                     {{bibref|3GPP-TS.23.003|Section 4.1}}
                     {{bibref|3GPP-TS.25.413|Section 9.2.3.6}}";
                }
                leaf RAC {
                  type uint32 {
                    range "0..255";
                  }
                  default "0";
                  description
                    "Routing Area Code (RAC).  The concatenation of
                     PLMN ID (MCC+MNC), LAC, and RAC uniquely
                     identifies the Routing Area ID (RAI).
                  
                     {{bibref|3GPP-TS.23.003|Section 4.2}}
                     {{bibref|3GPP-TS.25.413|Section 9.2.3.7}}";
                }
                leaf URA {
                  type uint32 {
                    range "0..65535";
                  }
                  default "0";
                  description
                    "UTRAN Registration Area (URA)
                     {{bibref|3GPP-TS.23.401}}.
                  
                     Indicates to the UE which {{param}} it shall
                     use in case of overlapping URAs.
                  
                     {{bibref|3GPP-TS.25.331|Section 10.3.2.6}}";
                }
                leaf UARFCNUL {
                  type uint32 {
                    range "0..16383";
                  }
                  default "0";
                  description
                    "The UL UTRA Absolute Radio Frequency Channel
                     Number (UARFCN) in an FDD mode cell.
                     {{bibref|3GPP-TS.25.433}}";
                }
                leaf UARFCNDL {
                  type uint32 {
                    range "0..16383";
                  }
                  default "0";
                  description
                    "The DL UTRA Absolute Radio Frequency Channel
                     Number (UARFCN) in an FDD mode cell.
                     {{bibref|3GPP-TS.25.433}}";
                }
                leaf PCPICHScramblingCode {
                  type uint32 {
                    range "0..511";
                  }
                  default "0";
                  description
                    "Primary CPICH scrambling code.";
                }
                leaf PCPICHTxPower {
                  type int32 {
                    range "-100..500";
                  }
                  default "0";
                  description
                    "Primary CPICH Tx power in {{units}}.
                  
                     Actual values of the power are -10.0
                     {{units}} to 50.0 {{units}} in steps of 0.1
                     dB.  The value of {{param}} divided by 10
                     yields the actual value of the power.
                  
                     {{bibref|3GPP-TS.32.642|Section 6.3.11}}
                     {{bibref|3GPP-TS.25.433|Section 2.2.33}}";
                }
              }

              list GSM {
                key "PLMNID LAC CI";
                description
                  "Table containing the inter-RAT cell list for
                   GERAN (GSM) provided by the ACS.  The table
                   contents MAY be added/deleted/modified during
                   operation, in which case these changes shall
                   be reflected in the broadcast information as
                   soon as possible.";
                leaf Enable {
                  type boolean;
                  default "false";
                  description
                    "Enables or disables this entry.";
                }
                leaf MustInclude {
                  type boolean;
                  default "false";
                  description
                    "Indicates whether this instance of the neighbor
                     shall be included or excluded in the FAP's
                     NL configuration.";
                }
                leaf PLMNID {
                  type string {
                    length "0..6";
                  }
                  default "";
                  description
                    "PLMN ID consists of Mobile Country Code (MCC)
                     and Mobile Network Code (MNC)
                     {{bibref|3GPP-TS.23.003}},
                     {{bibref|3GPP-TS.24.008}}.
                  
                     Mobile Country Code consists of three digits
                     and uniquely identifies the country of
                     domicile of the subscriber.
                  
                     Mobile Network Code consists of two or three
                     digits and identifies the Home PLMN within a
                     country.
                  
                     For a 2-digit MNC the total string length of
                     {{param}} is 5.";
                }
                leaf LAC {
                  type uint32 {
                    range "0..65535";
                  }
                  default "0";
                  description
                    "Location Area Code (LAC).  The concatenation of
                     PLMN ID (MCC+MNC) and LAC uniquely
                     identifies the Location Area ID (LAI).
                  
                     {{bibref|3GPP-TS.23.003|Section 4.1}}
                     {{bibref|3GPP-TS.25.413|Section 9.2.3.6}}";
                }
                leaf BSIC {
                  type uint32 {
                    range "0..255";
                  }
                  default "0";
                  description
                    "BSIC of the cell per {{bibref|3GPP-TS.23.003}},
                     consisting of:
                  
                     :Bit 7:6 - not used (\"00\")
                  
                     :Bit 5:3 - NCC (PLMN Color Code)
                  
                     :Bit 2:0 - BCC (BS color code)
                  
                     For example, if NCC is 7 and BCC is 2 you
                     would have 00111010 (binary) or 0x3A (hex),
                     and the value of this parameter would be 58.";
                }
                leaf CI {
                  type uint32 {
                    range "0..65535";
                  }
                  default "0";
                  description
                    "Cell ID of the cell per
                     {{bibref|3GPP-TS.23.003|Section 4.3.1}}.";
                }
                leaf BandIndicator {
                  type enumeration {
                    enum "GSM850";
                    enum "GSM900";
                    enum "DCS1800";
                    enum "PCS1900";
                  }
                  default "GSM850";
                  description
                    "Indicates how to interpret the BCCH ARFCN.
                     {{enum}}";
                }
                leaf BCCHARFCN {
                  type uint32 {
                    range "0..1023";
                  }
                  default "0";
                  description
                    "ARFCN of this cell.";
                }
              }

              list CDMA2000 {
                key "CID";
                description
                  "Table containing the inter-RAT cell list for
                   CDMA2000 provided by the ACS.  The table
                   contents MAY be added/deleted/modified during
                   operation, in which case these changes shall
                   be reflected in the broadcast information as
                   soon as possible.";
                leaf Enable {
                  type boolean;
                  default "false";
                  description
                    "Enables or disables this entry.";
                }
                leaf MustInclude {
                  type boolean;
                  default "false";
                  description
                    "Indicates whether this instance of the neighbor
                     shall be included or excluded in the FAP's
                     NL configuration.";
                }
                leaf BandClass {
                  type uint32 {
                    range "0..17";
                  }
                  default "0";
                  description
                    "Defines the CDMA2000 band in which the CDMA2000
                     frequency carrier can be found, specified in
                     bandclass number.  BandClass is defined in
                     {{bibref|3GPP2-C.S0057-B}} Table 1.5-1.
                  
                     Corresponds to parameter bandClass specified
                     in SIB8 in {{bibref|3GPP-TS.36.331|Section
                     6.3.1}}.";
                }
                leaf ARFCN {
                  type uint32 {
                    range "0..2047";
                  }
                  default "0";
                  description
                    "Defines the CDMA2000 frequency carrier within a
                     CDMA2000 band, as specified by
                     ARFCN-ValueCDMA2000 in SIB8 in
                     {{bibref|3GPP-TS.36.331|Section 6.3.1}}, and
                     {{bibref|3GPP2-C.S0002-A}}.";
                }
                leaf PNOffset {
                  type uint32 {
                    range "0..511";
                  }
                  default "0";
                  description
                    "Defines the PN offset that represents the
                     \"Physical cell identity\" in CDMA2000
                     system, as specified by PhysCellIdCDMA2000
                     in SIB8 in {{bibref|3GPP-TS.36.331|Section
                     6.3.1}}.";
                }
                leaf Type {
                  type enumeration {
                    enum "1xRTT";
                    enum "HRPD";
                  }
                  default "1xRTT";
                  description
                    "Indicates the type of the cell.  This parameter
                     determines the length of the CID parameter.";
                }
                leaf CID {
                  type string {
                    length "0..16";
                  }
                  default "0";
                  description
                    "Defines the global cell identity of the cell.
                     For a 1xRTT cell, the cell identity is a
                     binary string 47 bits long.  For a HRPD
                     cell, the cell identity is a binary string
                     128 bits long.  The value of {{param}}
                     parameter is interpreted as 128-bit long
                     unsigned integer.  If {{param|Type}} is
                     {{enum|1xRTT|Type}}, the first 47 bits (6
                     octet) is used and the rest of this
                     {{param}} parameter MUST be ignored by the
                     CPE.  If {{param|Type}} is
                     {{enum|HRPD|Type}}, the entire 16 octet is
                     used as {{param}}.  Corresponds to IE
                     CellGlobalIdCDMA2000 specified in
                     {{bibref|3GPP-TS.36.331|Section 6.3.4}}.";
                }
              }
            }
          }

          container NeighborListInUse {
            config false;
            description
              "This object contains parameters relating to the
               neighbor list used by the FAP based on its
               self-configuration capability and
               {{object|.CellConfig.LTE.RAN.NeighborList.}}
               configuration of adding and excluding cells.";
            leaf MaxLTECellEntries {
              type uint32;
              description
                "The maximum number of entries in the
                 {{object|.CellConfig.LTE.RAN.NeighborListInUse.LTECell.{i}.}}
                 table.";
            }

            list LTECell {
              key "PLMNID CID";
              description
                "Table containing the LTE EUTRA (i.e.  intra-RAT)
                 cell list.";
              leaf PLMNID {
                type string {
                  length "0..6";
                }
                description
                  "PLMN ID consists of Mobile Country Code (MCC) and
                   Mobile Network Code (MNC)
                   {{bibref|3GPP-TS.23.003}},
                   {{bibref|3GPP-TS.24.008}}.
                
                   Mobile Country Code consists of three digits
                   and uniquely identifies the country of
                   domicile of the subscriber.
                
                   Mobile Network Code consists of two or three
                   digits and identifies the Home PLMN within a
                   country.
                
                   For a 2-digit MNC the total string length of
                   {{param}} is 5.";
              }
              leaf CID {
                type uint32 {
                  range "1..268435455";
                }
                description
                  "Cell Identity.  {{bibref|3GPP-TS.36.331|Section
                   6.3.4}}.  Combination of {{param|PLMNID}} and
                   {{param}} constitutes the Cell Global ID
                   (CGI).";
              }
              leaf EUTRACarrierARFCN {
                type uint32 {
                  range "0..65535";
                }
                description
                  "Indicates the ARFCN of this carrier frequency.
                   Corresponds to parameter dl-CarrierFreq in
                   SIB5 in {{bibref|3GPP-TS.36.331|Section
                   6.3.1}}, and and parameter NDL in
                   {{bibref|3GPP-TS.36.101|Section 5.7.3}}.  If
                   the value of {{param}} is the same with the
                   one currently being used by the, then it
                   implies that this neighbor cell is an
                   intra-frequency cell; otherwise, it is an
                   inter-frequency cell.";
              }
              leaf PhyCellID {
                type uint32 {
                  range "0..503";
                }
                description
                  "Physical cell ID, as specified in
                   {{bibref|3GPP-TS.36.211|Section 6.11}}.";
              }
              leaf QOffset {
                type int32 {
                  range "-24..-8 | -6..6 | 8..24";
                }
                description
                  "Indicate a cell-specific offset applicable to a
                   specific neighbouring cell.  It is used for
                   evaluating the cell as a candidate for cell
                   re-selection in idle mode.
                
                   Corresponds to parameter q-OffsetCell
                   broadcast in SIB4 for intra-frequency cells
                   and in SIB5 for inter-frequency cells,
                   specified in {{bibref|3GPP-TS.36.331|Section
                   6.3.1}}.";
              }
              leaf CIO {
                type int32 {
                  range "-24..-8 | -6..6 | 8..24";
                }
                description
                  "Cell individual offset applicable to a specific
                   neighbouring cell.  It is used for evaluating
                   triggering conditions for measurement
                   reporting in connected mode.
                
                   Specified by cellIndividualOffset in
                   MeasObjectEUTRA IE in
                   {{bibref|3GPP-TS.36.331|Section 6.3.5}}.";
              }
              leaf RSTxPower {
                type int32 {
                  range "-60..50";
                }
                description
                  "The downlink reference-signal transmit power,
                   specified in {{units}}.  Defined as the linear
                   average over the power contributions (in W) of
                   all resource elements that carry cell-specific
                   reference signals within the operating system
                   bandwidth.  Corresponds to parameter
                   referenceSignalPower in SIB4 as a part of
                   PDSCH-Config IE in
                   {{bibref|3GPP-TS.36.331|Section 6.3.2}}.";
              }
              leaf Blacklisted {
                type boolean;
                description
                  "Indicates whether this neighbor cell is allowed
                   for UEs as handover target or not.  If
                   {{true}}, handover is prohibited towards this
                   cell.  If {{false}}, handover is allowed
                   toward this cell.  The {{param}} parameter
                   allows this cell to be prohibited as a
                   handover target, while still allowing this
                   cell to be included in the BCCH SIB4 or 5.";
              }
            }

            container InterRATCell {
              description
                "Table containing the inter-RAT cell lists separated
                 by technology.  {{bibref|3GPP-TS.36.331|Section
                 6.3.1 (SIB6, 7, 8)}}.";
              leaf MaxUMTSEntries {
                type uint32;
                description
                  "The maximum number of entries in the
                   {{object|.CellConfig.LTE.RAN.NeighborListInUse.InterRATCell.UMTS.{i}.}}
                   table.  There can be maximum of 16 UTRAN
                   (UMTS) neighbor cells, as specified by
                   carrierFreqListUTRA-FDD in SIB6 in
                   {{bibref|3GPP-TS.36.331|Section 6.3.1}}.";
              }
              leaf MaxGSMEntries {
                type uint32;
                description
                  "The maximum number of entries in the
                   {{object|.CellConfig.LTE.RAN.NeighborListInUse.InterRATCell.GSM.{i}.}}
                   table.  There can be maximum of 16 GERAN (GSM)
                   neighbor cells, as specified by
                   carrierFreqsInfoList in SIB7 in
                   {{bibref|3GPP-TS.36.331|Section 6.3.1}}.";
              }
              leaf MaxCDMA2000Entries {
                type uint32;
                description
                  "The maximum number of entries in the
                   {{object|.CellConfig.LTE.RAN.NeighborListInUse.InterRATCell.CDMA2000.{i}.}}
                   table.  There can be maximum of 32 banclasses.
                   In each bandclass, there can be maximum of 16
                   CDMA2000 carrier frequencies.  In each
                   carrier, there can be maximum of 16 CDMA2000
                   neighbor cells (PN offset).  It is specified
                   by neighCellList in SIB8 in
                   {{bibref|3GPP-TS.36.331|Section 6.3.1}}.";
              }

              list UMTS {
                key "PLMNID CID";
                description
                  "Table containing the inter-RAT cell list for UTRA
                   (UMTS) cell.";
                leaf PLMNID {
                  type string {
                    length "0..6";
                  }
                  description
                    "PLMN ID consists of Mobile Country Code (MCC)
                     and Mobile Network Code (MNC)
                     {{bibref|3GPP-TS.23.003}},
                     {{bibref|3GPP-TS.24.008}}.
                  
                     Mobile Country Code consists of three digits
                     and uniquely identifies the country of
                     domicile of the subscriber.
                  
                     Mobile Network Code consists of two or three
                     digits and identifies the Home PLMN within a
                     country.
                  
                     For a 2-digit MNC the total string length of
                     {{param}} is 5.";
                }
                leaf RNCID {
                  type uint32 {
                    range "0..65535";
                  }
                  description
                    "RNC-ID of an intra-RAT UMTS neighbor cell.  It
                     uniquely identifies an RNC within a PLMN.
                  
                     Normally, RNC-ID consists of 12 bits (i.e.
                     a range of [0:4095]).  However, if the value
                     is larger than 4095, then Extended RNC-ID
                     (range of [4096:65535]) is used in RANAP.
                  
                     The RNC-ID and Extended RNC-ID are combined
                     into a single parameter here as there is no
                     explicit need to have them separated.
                  
                     {{bibref|3GPP-TS.25.413|Section 9.2.1.39}}";
                }
                leaf CID {
                  type uint32 {
                    range "1..65535";
                  }
                  description
                    "Cell Identifier (C-id) that identifies a cell
                     within an RNS.  This Cell Identifier
                     together with the controlling RNC (RNC-ID)
                     constitutes the UTRAN Cell ID (UC-ID) and is
                     used to identify a cell uniquely within
                     UTRAN.  C-ID is either 12-bit or 16-bit
                     value.  {{bibref|3GPP-TS.25.401|Section
                     6.1.5}}.";
                }
                leaf LAC {
                  type uint32 {
                    range "0..65535";
                  }
                  description
                    "Location Area Code (LAC).  The concatenation of
                     PLMN ID (MCC+MNC) and LAC uniquely
                     identifies the Location Area ID (LAI).
                  
                     {{bibref|3GPP-TS.23.003|Section 4.1}}
                     {{bibref|3GPP-TS.25.413|Section 9.2.3.6}}";
                }
                leaf RAC {
                  type uint32 {
                    range "0..255";
                  }
                  description
                    "Routing Area Code (RAC).  The concatenation of
                     PLMN ID (MCC+MNC), LAC, and RAC uniquely
                     identifies the Routing Area ID (RAI).
                  
                     {{bibref|3GPP-TS.23.003|Section 4.2}}
                     {{bibref|3GPP-TS.25.413|Section 9.2.3.7}}";
                }
                leaf URA {
                  type uint32 {
                    range "0..65535";
                  }
                  description
                    "UTRAN Registration Area (URA)
                     {{bibref|3GPP-TS.23.401}}.
                  
                     Indicates to the UE which {{param}} it shall
                     use in case of overlapping URAs.
                  
                     {{bibref|3GPP-TS.25.331|Section 10.3.2.6}}";
                }
                leaf UARFCNUL {
                  type uint32 {
                    range "0..16383";
                  }
                  description
                    "The UL UTRA Absolute Radio Frequency Channel
                     Number (UARFCN) in an FDD mode cell.
                     {{bibref|3GPP-TS.25.433}}";
                }
                leaf UARFCNDL {
                  type uint32 {
                    range "0..16383";
                  }
                  description
                    "The DL UTRA Absolute Radio Frequency Channel
                     Number (UARFCN) in an FDD mode cell.
                     {{bibref|3GPP-TS.25.433}}";
                }
                leaf PCPICHScramblingCode {
                  type uint32 {
                    range "0..511";
                  }
                  description
                    "Primary CPICH scrambling code.";
                }
                leaf PCPICHTxPower {
                  type int32 {
                    range "-100..500";
                  }
                  description
                    "Primary CPICH Tx power in {{units}}.
                  
                     Actual values of the power are -10.0
                     {{units}} to 50.0 {{units}} in steps of 0.1
                     dB.  The value of {{param}} divided by 10
                     yields the actual value of the power.
                  
                     {{bibref|3GPP-TS.32.642|Section 6.3.11}}
                     {{bibref|3GPP-TS.25.433|Section 2.2.33}}";
                }
              }

              list GSM {
                key "PLMNID LAC CI";
                description
                  "Table containing the inter-RAT cell list for
                   GERAN (GSM) cell.";
                leaf PLMNID {
                  type string {
                    length "0..6";
                  }
                  description
                    "PLMN ID consists of Mobile Country Code (MCC)
                     and Mobile Network Code (MNC)
                     {{bibref|3GPP-TS.23.003}},
                     {{bibref|3GPP-TS.24.008}}.
                  
                     Mobile Country Code consists of three digits
                     and uniquely identifies the country of
                     domicile of the subscriber.
                  
                     Mobile Network Code consists of two or three
                     digits and identifies the Home PLMN within a
                     country.
                  
                     For a 2-digit MNC the total string length of
                     {{param}} is 5.";
                }
                leaf LAC {
                  type uint32 {
                    range "0..65535";
                  }
                  description
                    "Location Area Code (LAC).  The concatenation of
                     PLMN ID (MCC+MNC) and LAC uniquely
                     identifies the Location Area ID (LAI).
                  
                     {{bibref|3GPP-TS.23.003|Section 4.1}}
                     {{bibref|3GPP-TS.25.413|Section 9.2.3.6}}";
                }
                leaf BSIC {
                  type uint32 {
                    range "0..255";
                  }
                  description
                    "BSIC of the cell per {{bibref|3GPP-TS.23.003}},
                     consisting of:
                  
                     :Bit 7:6 - not used (\"00\")
                  
                     :Bit 5:3 - NCC (PLMN Color Code)
                  
                     :Bit 2:0 - BCC (BS color code)
                  
                     For example, if NCC is 7 and BCC is 2 you
                     would have 00111010 (binary) or 0x3A (hex),
                     and the value of this parameter would be 58.";
                }
                leaf CI {
                  type uint32 {
                    range "0..65535";
                  }
                  description
                    "Cell ID of the cell per
                     {{bibref|3GPP-TS.23.003|Section 4.3.1}}.";
                }
                leaf BandIndicator {
                  type enumeration {
                    enum "GSM850";
                    enum "GSM900";
                    enum "DCS1800";
                    enum "PCS1900";
                  }
                  description
                    "Indicates how to interpret the BCCH ARFCN.
                     {{enum}}";
                }
                leaf BCCHARFCN {
                  type uint32 {
                    range "0..1023";
                  }
                  description
                    "ARFCN of this cell.";
                }
              }

              list CDMA2000 {
                key "CID";
                description
                  "Table containing the inter-RAT cell list for
                   CDMA2000 cell.";
                leaf BandClass {
                  type uint32 {
                    range "0..17";
                  }
                  description
                    "Defines the CDMA2000 band in which the CDMA2000
                     frequency carrier can be found, specified in
                     bandclass number.  BandClass is defined in
                     {{bibref|3GPP2-C.S0057-B|Table 1.5-1}}.
                  
                     Corresponds to parameter bandClass specified
                     in SIB8 in {{bibref|3GPP-TS.36.331|Section
                     6.3.1}}.";
                }
                leaf ARFCN {
                  type uint32 {
                    range "0..2047";
                  }
                  description
                    "Defines the CDMA2000 frequency carrier within a
                     CDMA2000 band, as specified by
                     ARFCN-ValueCDMA2000 in SIB8 in
                     {{bibref|3GPP-TS.36.331|Section 6.3.1}}, and
                     {{bibref|3GPP2-C.S0002-A}}.";
                }
                leaf PNOffset {
                  type uint32 {
                    range "0..511";
                  }
                  description
                    "Defines the PN offset that represents the
                     \"Physical cell identity\" in CDMA2000
                     system, as specified by PhysCellIdCDMA2000
                     in SIB8 in {{bibref|3GPP-TS.36.331|Section
                     6.3.1}}.";
                }
                leaf Type {
                  type enumeration {
                    enum "1xRTT";
                    enum "HRPD";
                  }
                  description
                    "Indicates the type of the cell.  This parameter
                     determines the length of the CID parameter.";
                }
                leaf CID {
                  type string {
                    length "0..16";
                  }
                  description
                    "Defines the global cell identity of the cell.
                     For a 1xRTT cell, the cell identity is a
                     binary string 47 bits long.  For a HRPD
                     cell, the cell identity is a binary string
                     128 bits long.  The value of {{param}}
                     parameter is interpreted as 128-bit long
                     unsigned integer.  If {{param|Type}} is
                     {{enum|1xRTT|Type}}, the first 47 bits (6
                     octet) is used and the rest of this
                     {{param}} parameter MUST be ignored by the
                     CPE.  If {{param|Type}} is
                     {{enum|HRPD|Type}}, the entire 16 octet is
                     used as {{param}}.  Corresponds to IE
                     CellGlobalIdCDMA2000 specified in
                     {{bibref|3GPP-TS.36.331|Section 6.3.4}}.";
                }
              }
            }
          }

          container CSG {
            config false;
            description
              "This object provides monitoring of Closed Subscriber
               Groups (CSG) in the HeNB.";

            container Stats {
              description
                "This object provides the LTE RAN CSG statistics as
                 defined in {{bibref|3GPP-TS.32.453}}.";
              leaf MeanNbrUsr {
                type uint32;
                description
                  "This measurement provides the mean number of
                   attached CSG UEs in the HeNB.";
              }
              leaf AttInboundMobility {
                type uint32;
                description
                  "This measurement provides the number of attempted
                   inbound mobility for UEs to CSG cells or
                   hybrid cells in RRC_CONNECTED mode.";
              }
              leaf SuccInboundMobility {
                type uint32;
                description
                  "This measurement provides the number of
                   successful inbound mobility for UEs to CSG
                   cells or hybrid cells in RRC_CONNECTED mode.";
              }
              leaf FailedInboundMobility {
                type string;
                description
                  "This measurement provides the number of failed
                   successful inbound mobility for UEs to CSG
                   cells or hybrid cells in RRC_CONNECTED mode by
                   cause.
                
                   {{list| where each item is defined as the
                   \"cause name=measurement value\"}} The total
                   of all the measurements is provided using the
                   cause name= \"sum\".";
              }
            }
          }

          container RRC {
            config false;
            description
              "This object provides monitoring of the RRC in the
               HeNB.";

            container Stats {
              description
                "This object provides the RRC statistics as defined
                 in {{bibref|3GPP-TS.32.453}}.";
              leaf AttConnEstab {
                type string;
                description
                  "This measurement provides the number of RRC
                   connection establishment attempts by cause.
                
                   {{list| where each item is defined as the
                   \"cause name=measurement value\"}} The total
                   of all the measurements is provided using the
                   cause name= \"sum\".";
              }
              leaf FailConnEstab {
                type string;
                description
                  "This measurement provides the number of RRC
                   establishment failures by cause.
                
                   {{list| where each item is defined as the
                   \"cause name=measurement value\"}} The total
                   of all the measurements is provided using the
                   cause name= \"sum\".";
              }
              leaf SuccConnEstab {
                type string;
                description
                  "This measurement provides the number of
                   successful RRC establishments by cause.
                
                   {{list| where each item is defined as the
                   \"cause name=measurement value\"}} The total
                   of all the measurements is provided using the
                   cause name= \"sum\".";
              }
            }
          }

          container ERAB {
            config false;
            description
              "This object provides monitoring of E-RABs in the
               HeNB.";

            container Stats {
              description
                "This object provides the E-RAB statistics as
                 defined in {{bibref|3GPP-TS.32.453}}.";
              leaf EstabInitAttNbr {
                type string;
                description
                  "This measurement provides the number of initial
                   E-RABs attempted to setup by QoS level (QCI).
                
                   {{list| where each item is defined as the
                   \"QCI level name=measurement value\"}} The
                   total of all the measurements is provided
                   using the name= \"sum\".";
              }
              leaf EstabInitSuccNbr {
                type string;
                description
                  "This measurement provides the number of initial
                   E-RABs successfully established QoS level
                   (QCI).
                
                   {{list| where each item is defined as the
                   \"QCI level name=measurement value\"}} The
                   total of all the measurements is provided
                   using the name= \"sum\".";
              }
              leaf EstabInitFailNbr {
                type string;
                description
                  "This measurement provides the number of initial
                   E-RABs failed to setup by cause.
                
                   {{list| where each item is defined as the
                   \"QCI level name=measurement value\"}} The
                   total of all the measurements is provided
                   using the name= \"sum\".";
              }
              leaf EstabAttNbr {
                type string;
                description
                  "This measurement provides the number of E-RABs
                   attempted to setup by QoS level (QCI).
                
                   {{list| where each item is defined as the
                   \"QCI level name=measurement value\"}} The
                   total of all the measurements is provided
                   using the name= \"sum\".";
              }
              leaf EstabSuccNbr {
                type string;
                description
                  "This measurement provides the number of E-RABs
                   successfully established by QoS level (QCI).
                
                   {{list| where each item is defined as the
                   \"QCI level name=measurement value\"}} The
                   total of all the measurements is provided
                   using the name= \"sum\".";
              }
              leaf EstabFailNbr {
                type string;
                description
                  "This measurement provides the number of E-RABs
                   failed to setup by cause.
                
                   {{list| where each item is defined as the
                   \"QCI level name=measurement value\"}} The
                   total of all the measurements is provided
                   using the name= \"sum\".";
              }
              leaf RelEnbNbrQCI {
                type string;
                description
                  "This measurement provides the number of E-RABs
                   requested to release initiated by HeNB by QCI.
                
                   {{list| where each item is defined as the
                   \"QCI level name=measurement value\"}} The
                   total of all the measurements is provided
                   using the name= \"sum\".";
              }
              leaf RelEnbNbrCause {
                type string;
                description
                  "This measurement provides the number of E-RABs
                   requested to release initiated by HeNB by
                   cause.
                
                   {{list| where each item is defined as the
                   \"QCI level name=measurement value\"}} The
                   total of all the measurements is provided
                   using the name= \"sum\".";
              }

              list LGW {
                key "CorrelationID";
                description
                  "This object provides statistics for the Direct
                   User Plane Path between HeNB and Local Gateway
                   as defined in {{bibref|3GPP-TS.32.453}}.";
                leaf CorrelationID {
                  type string;
                  description
                    "The value of this parameter is equal to the
                     user plane PDN GW TEID (GTP-based S5) or GRE
                     key (PMIP-based S5).
                     {{bibref|3GPP-TS.25.401}}.";
                }
                leaf EstabDirectPathLGWAttNbr {
                  type uint32;
                  description
                    "This measurement provides the number of direct
                     user plane path between HeNB and Local GW
                     attempted to setup.";
                }
                leaf EstabDirectPathLGWSuccNbr {
                  type uint32;
                  description
                    "This measurement provides the number of direct
                     user plane path between HeNB and Local GW
                     successfully established.";
                }
                leaf EstabDirectPathLGWFailNbr {
                  type string;
                  description
                    "This measurement provides the number of direct
                     user plane path between HeNB and Local GW
                     E-RABs failed to setup by cause.
                  
                     {{list| where each item is defined as the
                     \"cause name=measurement value\"}} The total
                     of all the measurements is provided using
                     the name= \"sum\".";
                }
              }
            }
          }

          container DRB {
            config false;
            description
              "This object provides monitoring of Data Radio Bearers
               (DRB) in the HeNB.";

            container Stats {
              description
                "This object provides the DRB statistics as defined
                 in {{bibref|3GPP-TS.32.453}}.";
              leaf PdcpSduBitrateDl {
                type string;
                description
                  "This measurement provides the average cell
                   bit-rate of PDCP SDUs on the downlink.  This
                   represents the ingress rate of user plane
                   traffic to the HeNB (via S1) by SAE Bearer QoS
                   level (QCI).
                
                   {{list| where each item is defined as the
                   \"QCI level=measurement value\"}} The total of
                   all the measurements is provided using the
                   name= \"sum\".";
              }
              leaf PdcpSduBitrateUl {
                type string;
                description
                  "This measurement provides the average cell
                   bit-rate of PDCP SDUs on the uplink.  This
                   represents successful transmissions of user
                   plane traffic; control signalling and
                   retransmissions are excluded from this
                   measure.  Measurement is by SAE Bearer QoS
                   level (QCI).
                
                   {{list| where each item is defined as the
                   \"QCI level=measurement value\"}} The total of
                   all the measurements is provided using the
                   name= \"sum\".";
              }
              leaf PdcpSduBitrateDlMax {
                type uint32;
                description
                  "This measurement provides the maximum cell
                   bit-rate of PDCP SDUs on the downlink.  This
                   represents the maximum ingress rate of user
                   plane traffic to the HeNB (via S1).  This is a
                   sum counter measured across all QCIs.";
              }
              leaf PdcpSduBitrateUlMax {
                type uint32;
                description
                  "This measurement provides the maximum cell
                   bit-rate of PDCP SDUs measured on the uplink.
                   This represents successful transmissions of
                   user plane traffic; control signalling and
                   retransmissions are excluded from this
                   measure.  This is a sum counter measured
                   across all QCIs.";
              }
              leaf PdcpSduDelayDl {
                type string;
                description
                  "This measurement provides the average (arithmetic
                   mean) PDCP SDU delay on the downlink by ERAB
                   Bearer QoS level (QCI).
                
                   {{list| where each item is defined as the
                   \"QCI level=measurement value\"}} The total of
                   all the measurements is provided using the
                   name= \"sum\".";
              }
              leaf PdcpSduDropRateDl {
                type string;
                description
                  "This measurement provides the fraction of IP
                   packets (PDCP SDUs) which are dropped on the
                   downlink by ERAB Bearer QoS level (QCI).  Only
                   user-plane traffic (DTCH) is considered.  A
                   dropped packet is one whose context is removed
                   from the HeNB without any part of it having
                   been transmitted on the air interface.
                   Packets discarded during handover are excluded
                   from the count.
                
                   {{list| where each item is defined as the
                   \"QCI level=measurement value\"}} The total of
                   all the measurements is provided using the
                   name= \"sum\".";
              }
              leaf PdcpSduAirLossRateDl {
                type string;
                description
                  "This measurement provides the fraction of IP
                   packets (PDCP SDUs) which are lost (not
                   successfully transmitted) on the downlink air
                   interface by ERAB Bearer QoS level (QCI).
                   Only user-plane traffic (DTCH) is considered.
                   A lost packet is one whose context is removed
                   from the HeNB after an attempt has been made
                   to transmit part or all of the packet on the
                   air interface but the whole packet has not
                   been successfully transmittedafter an attempt
                   has been made to transmit part or all of the
                   packet on the air interface but the whole
                   packet has not been successfully transmitted.
                
                   {{list| where each item is defined as the
                   \"QCI level=measurement value\"}} The total of
                   all the measurements is provided using the
                   name= \"sum\".";
              }
              leaf PdcpSduLossRateUl {
                type string;
                description
                  "This measurement provides the fraction of IP
                   packets (PDCP SDUs) which are lost (not
                   successfully received) on the uplink by ERAB
                   Bearer QoS level (QCI).  Only user-plane
                   traffic (DTCH) and only PDCP SDUs that have
                   entered PDCP (and given a PDCP sequence
                   number) are considered.
                
                   {{list| where each item is defined as the
                   \"QCI level=measurement value\"}} The total of
                   all the measurements is provided using the
                   name= \"sum\".";
              }
              leaf UEActiveDl {
                type string;
                description
                  "This measurement provides the average number of
                   UEs that have user-plane (DTCH) data queued on
                   the downlink by ERAB Bearer QoS level (QCI).
                
                   {{list| where each item is defined as the
                   \"QCI level=measurement value\"}} The total of
                   all the measurements is provided using the
                   name= \"sum\".";
              }
              leaf UEActiveUl {
                type string;
                description
                  "This measurement provides the average number of
                   UEs that have user-plane (DTCH) data queued on
                   the uplink by ERAB Bearer QoS level (QCI).
                
                   {{list| where each item is defined as the
                   \"QCI level=measurement value\"}} The total of
                   all the measurements is provided using the
                   name= \"sum\".";
              }
            }
          }

          container RRU {
            config false;
            description
              "This object provides monitoring of the Radio Resource
               Usage in the HeNB.";

            container Stats {
              description
                "This object provides the RRU statistics as defined
                 in {{bibref|3GPP-TS.32.453}}.";
              leaf PrbTotDl {
                type uint32 {
                  range "0..100";
                }
                description
                  "This measurement provides the total usage, in
                   {{units}}, of physical resource blocks (PRBs)
                   on the downlink for any purpose.";
              }
              leaf PrbTotUl {
                type uint32 {
                  range "0..100";
                }
                description
                  "This measurement provides the total usage, in
                   {{units}}, of physical resource blocks (PRBs)
                   on the uplink for any purpose.";
              }
            }
          }
        }

        container EnergySavings {
          description
            "This object provides for the managment of energy
             savings capabilities in the HeNB.";
          leaf Enable {
            type boolean;
            description
              "This attribute determines whether the energy saving
               function is enabled or disabled.";
          }
          leaf State {
            type enumeration {
              enum "IsEnergySaving";
              enum "IsNotEnergySaving";
            }
            config false;
            description
              "Specifies the status regarding the energy saving in
               the cell.  This parameter is applicable when the
               value of {{param|Enable}} is {{true}}.";
          }

          container ActivationCandidateCellsLoad {
            description
              "This object is relevant if the cell acts as a
               candidate cell.  This object indicates the traffic
               load threshold and the time duration, which are
               used by distributed energy saving algorithms to
               allow an ‘original’ cell to enter the energy
               saving state.  Threshold and TimeDuration are
               applied to the candidate cell(s) which provide
               coverage backup of an original cell when it is in
               the energy saving state.";
            leaf Threshold {
              type uint32 {
                range "min..100";
              }
              description
                "PRB usage as a {{units}} {{bibref|3GPP-TS.36.314}}.
                 The threshold applies in the same way for a
                 candidate cell no matter which original cell it
                 will provide backup coverage.";
            }
            leaf TimeDuration {
              type uint32;
              description
                "This parameter indicates how long the traffic in
                 the candidate cell needs to have been below the
                 threshold, in {{units}}, before any original
                 cells which will be provided backup coverage by
                 the candidate cell enters energy saving state.";
            }
          }

          container DeactivationCandidateCellsLoad {
            description
              "This object is relevant if the cell acts as a
               candidate cell.  This object indicates the traffic
               load threshold and the time duration which is used
               by distributed energy saving algorithms to allow a
               cell to leave the energy saving state.  Threshold
               and time duration are applied to the candidate
               cell when it provides coverage backup for the cell
               in energy saving state.";
            leaf Threshold {
              type uint32 {
                range "min..100";
              }
              description
                "PRB usage as a {{units}} {{bibref|3GPP-TS.36.314}}.
                 The threshold applies in the same way for a
                 candidate cell, no matter for which original
                 cell it provides backup coverage.";
            }
            leaf TimeDuration {
              type uint32;
              description
                "This parameter indicates how long the traffic in
                 the candidate cell needs to have been above the
                 threshold, in {{units}}, to wake up one or more
                 original cells which have been provided backup
                 coverage by the candidate cell.";
            }
          }

          list NotAllowedTimePeriod {
            description
              "This object provides a time period for which energy
               saving is not allowed.
            
               This object can be used to prevent a cell entering
               energy saving state.
            
               This object is valid on the specified day(s) and
               time of every week.";
            leaf Enable {
              type boolean;
              description
                "This attribute determines whether the time period
                 is enabled or disabled.";
            }
            leaf StartTime {
              type string;
              description
                "Starting time for this time period formatted as
                 \"HH:MM:SS\" in UTC.";
            }
            leaf EndTime {
              type string;
              description
                "Ending time for this time period formatted as
                 \"HH:MM:SS\" in UTC.";
            }
            leaf DaysOfWeek {
              type enumeration {
                enum "Monday";
                enum "Tuesday";
                enum "Wednesday";
                enum "Thursday";
                enum "Friday";
                enum "Saturday";
                enum "Sunday";
              }
              description
                "{{list| that represents the days of the week that
                 are effective for this time period}}";
            }
          }
        }
      }

      container CDMA2000 {
        description
          "This object contains parameters relating to configuring
           the CDMA2000 FAP.";
        leaf TunnelInstance {
          type string {
            length "0..256";
          }
          description
            "This is the reference to the IPsec tunnel instance used
             by the CDMA2000 FAP.
          
             For all root data models, which use the tunnel
             definition provided in {{bibref|TR-262}}
             (InternetGatewayDevice:1 {{bibref|TR-098}} and
             Device:1 {{bibref|TR-181i1}}) the {{param}} MUST
             point to a row in the 'FAP.Tunnel.IKESA.{i}.'
             table, defined in {{bibref|TR-262}}.
          
             If the root data model used is Device:2
             {{bibref|TR-181i2}} than the {{param}} MUST point to
             IPsec tunnel instance defined in
             {{bibref|TR-181i2}}.
          
             If the referenced object is deleted, the parameter
             value MUST be set to an empty string.
          
             In case of a multiple-radio-technology FAP product,
             each radio technology can have its own tunnels or
             share common tunnels.  In the former case, {{param}}
             can contain a unique instance number.  In the latter
             case, {{param}} under all radio technologies can
             have the same instance number.";
        }

        container OneX {
          description
            "This object contains parameters relating to configuring
             the CDMA2000 1x FAP.";
          leaf MaxBatchPCFPDSNEntries {
            type uint32;
            config false;
            description
              "Maximum number of entries in the
               {{object|.CellConfig.CDMA2000.OneX.BatchPCFPDSN.{i}.}}
               table.";
          }

          container RAN {
            description
              "This object contains parameters relating to RAN
               configuring the CDMA2000 1x FAP.";
            leaf OneXSectorNID {
              type int32 {
                range "0..65535";
              }
              description
                "SID for 1x.  See {{bibref|3GPP2-C.S0005}}.";
            }
            leaf OneXSectorSID {
              type int32 {
                range "0..32767";
              }
              description
                "NID for 1x .  See {{bibref|3GPP2-C.S0005}}.";
            }
            leaf OneXPZID {
              type int32;
              description
                "packet Zone ID for 1x packet calls";
            }
            leaf BaseID {
              type int32;
              description
                "Base station ID (needed in SPM).  This is also the
                 CellID.  See {{bibref|3GPP2-C.S0005}}.";
            }
            leaf MaxNeighborListEntries {
              type uint32;
              config false;
              description
                "Maximum number of entries avaiable in
                 {{object|.CellConfig.CDMA2000.OneX.RAN.NeighborList.{i}.}}.";
            }

            container RF {
              description
                "This object contains parameters relating to RF
                 configuration of the FAP.";
              leaf RFCNFL {
                type string {
                  length "0..256";
                }
                description
                  "{{list}} Each item is a pair of 2-digit Band
                   class number (as defined in
                   {{bibref|3GPP2-C.S0057}}) followed by 4-digit
                   FL Radio Frequency Channel Number (RFCN).
                   Self-configuration for RFCN is controlled by
                   {{param|.FAPControl.CDMA2000.OneX.SelfConfig.RFCNFLSelfConfigEnable}}.
                   If the FAP's self-configuration capability for
                   RFCN is available and enabled, this parameter
                   MAY contain more than one item and the FAP is
                   expected to select one from the list for
                   RFCNFLInUse.
                
                   If the self-configuration capability is not
                   available or not enabled, then this parameter
                   SHOULD contain only a single item.
                
                   An example value is \"010001, 030500\".  If
                   multiple items are specified, they are done in
                   the order of preference.";
              }
              leaf RFCNFLBandInUse {
                type string {
                  length "0..16";
                }
                config false;
                description
                  "The FL Band being used by the FAP.
                   Self-configuration for Band and RFCN is
                   controlled by
                   {{param|.Capabilities.CDMA2000.OneX.SelfConfig.RFCNFLConfig}}
                   from an availability perspective and
                   {{param|.FAPControl.CDMA2000.OneX.SelfConfig.RFCNFLSelfConfigEnable}}
                   from an enabled perspective.  If the
                   self-configuration capability is available and
                   enabled, this parameter indicates the value
                   selected by the FAP among the choices provided
                   in RFCNFL.  If the self-configuration
                   capability is not available or not enabled,
                   then this parameter contains the first band
                   class value in RFCNFL.";
              }
              leaf RFCNFLInUse {
                type uint32;
                config false;
                description
                  "The FL RFCN being used by the FAP.
                   Self-configuration for RFCN is controlled by
                   {{param|.Capabilities.CDMA2000.OneX.SelfConfig.RFCNFLConfig}}
                   from an availability perspective and
                   {{param|.FAPControl.CDMA2000.OneX.SelfConfig.RFCNFLSelfConfigEnable}}
                   from an enabled perspective.  If the
                   self-configuration capability is available and
                   enabled, this parameter indicates the value
                   selected by the FAP among the choices provided
                   in RFCNFL.  If the self-configuration
                   capability is not available or not enabled,
                   then this parameter contains the first RFCN
                   value in RFCNFL.";
              }
              leaf PilotPN {
                type string {
                  length "0..256";
                }
                description
                  "{{list}} Each item is a pilot PN offset in units
                   of 64 PN chips.  Self-configuration for pilot
                   PN is controlled by
                   {{param|.Capabilities.CDMA2000.OneX.SelfConfig.PilotPNConfig}}
                   from an availability perspective and
                   {{param|.FAPControl.CDMA2000.OneX.SelfConfig.PilotPNSelfConfigEnable}}
                   from an enabled perspective.
                
                   If the FAP's self-configuration capability for
                   Pilot PN Offset is available and enabled, this
                   parameter MAY contain more than one item and
                   the FAP is expected to select one from the
                   list for PilotPNInUse.  If the
                   self-configuration capability is not available
                   or not enabled, then this parameter SHOULD
                   contain only a single item.
                
                   The multiplicity of the PN offset values can
                   also be expressed by defining a range using
                   \"..\" (two periods) between two values.  In
                   this case, the combination of two values
                   defines the lower-bound and upper-bound of the
                   range inclusive.
                
                   The order of the items has no significance.";
              }
              leaf PilotPNInUse {
                type uint32 {
                  range "0..511";
                }
                config false;
                description
                  "The Pilot PN Offset being used by the FAP in
                   {{units}}.  Self-configuration for Pilot PN
                   Offset is controlled by
                   {{param|.Capabilities.CDMA2000.OneX.SelfConfig.PilotPNConfig}}
                   from an availability perspective and
                   {{param|.FAPControl.CDMA2000.OneX.SelfConfig.PilotPNSelfConfigEnable}}
                   from an enabled perspective.  If the
                   self-configuration capability is available and
                   enabled, this parameter indicates the value
                   selected by the FAP among the choices provided
                   in PilotPN.
                
                   If the self-configuration capability is not
                   available or not enabled, then this parameter
                   contains the first value in PilotPN.";
              }
              leaf MaxFAPTxPower {
                type string {
                  length "0..64";
                }
                description
                  "Defines the maximum transmission power allowed on
                   the FAP.  MaxFAPTxPower is expressed as a
                   range of allowed maximum power levels with
                   \"..\" (two periods)
                
                   between the upper and lower values, i.e.
                   \"<Pmax_low>;..<Pmax_high>;\".
                
                   {{param}} identifies the limits between which
                   the FAP can self-configure its maximum
                   transmit power.
                
                   Self-configuration for maximum transmission
                   power is controlled by
                   {{param|.Capabilities.CDMA2000.OneX.SelfConfig.MaxFAPTxPowerConfig}}
                   from an availability perspective and
                   {{param|.FAPControl.CDMA2000.OneX.SelfConfig.MaxFAPTxPowerSelfConfigEnable}}
                   from an enabled perspective.  <Pmax_low>; and
                   <Pmax_high>; are measured in dBm and have a
                   range of -40.0 to 20.0 incremented by 0.1 dB.";
              }
              leaf MaxFAPTxPowerInUse {
                type int32 {
                  range "-400..200";
                }
                config false;
                description
                  "The maximum transmission power measured in
                   {{units}} currently used by the FAP.
                
                   Actual values of the maximum transmission
                   power are -40.0 dBm to 20.0 dBm in steps of
                   0.1 dB.  The value of {{param}} divided by 10
                   yields the
                
                   actual value of the maximum transmission
                   power.
                
                   Self-configuration for maximum transmission
                   power is controlled by
                   {{param|.Capabilities.CDMA2000.OneX.SelfConfig.MaxFAPTxPowerConfig}}
                   from an availability perspective and
                   {{param|.FAPControl.CDMA2000.OneX.SelfConfig.MaxFAPTxPowerSelfConfigEnable}}
                   from an enabled perspective.  If the
                   self-configuration capability is available and
                   enabled, this parameter indicates the value
                   selected by the FAP among the range provided
                   in {{param|MaxFAPTxPower}}.  If the
                   self-configuration capability is not available
                   or not enabled, then this parameter contains a
                   value selected by the ACS.";
              }
              leaf PchPwrPercentage {
                type uint32 {
                  range "1000..1000000";
                }
                description
                  "Percentage of Max Sector Power Used By Paging
                   Channel (expressed in {{units}}).  For
                   example, 93333 means 93.333% of the max sector
                   power.";
              }
              leaf PilotPwrPercentage {
                type uint32 {
                  range "1000..1000000";
                }
                description
                  "Percentage of Max Sector Power Used By Pilot
                   Channel (expressed in {{units}}).  For
                   example, 19950 means 19.95% of total.";
              }
              leaf SyncPwrPercentage {
                type uint32 {
                  range "1000..1000000";
                }
                description
                  "Percentage of Max Sector Power Used By Sync
                   Channel (expressed in {{units}}).  For
                   example, 23458 means 23.4% of the max sector
                   power.";
              }
            }

            container NetworkListenModeConfig {
              description
                "This object contains parameters relating to
                 self-configuration of the MaxFAPTxPower of the
                 FAP.";
              leaf RFCNFLMargin {
                type uint32;
                description
                  "If self-configuration of RFCNFL is enabled, this
                   value indicates the total received signal
                   strength margin to be applied to the entries
                   in RFCNFL when the FAP decides on the
                   RFCNInUse in order to bias the selection of
                   the most preferred frequency.";
              }
              leaf FAPCoverageTarget {
                type string {
                  length "0..32";
                }
                description
                  "Defines the target value measured in dB for the
                   range of the FAP's FL coverage, in terms of RF
                   propagation loss.  This value can be used by
                   the FAP's selfconfiguration algorithms to help
                   derive transmit power levels in the presence
                   of co-channel and adjacent channel
                   interference.
                
                   {{param}} is expressed as a range of the
                   minimum coverage path loss and the maximum
                   coverage path loss with \"..\" (two periods)
                   between the minimum and maximum values, i.e.,
                   \"<FAPCoverageTarget_min>..<FAPCoverageTarget_max>\".
                   These values can be used by the FAP's
                   selfconfiguration algorithms to help derive
                   transmit power levels in the presence of
                   co-channel and adjacent channel interference.
                
                   <FAPCoverageTarget_min> and
                   <FAPCoverageTarget_max> are measured in dB and
                   have a range of [50,150] incremented by 1 dB.";
              }
              leaf FAPBeaconCoverageTarget {
                type string {
                  length "0..32";
                }
                description
                  "Defines the target value measured in dB for the
                   range of the FAP's FL Beacon coverage, in
                   terms of RF propagation loss.  This value can
                   be used by the FAP's selfconfiguration
                   algorithms to help derive beacon transmit
                   power levels.
                
                   {{param}} is expressed as a range of the
                   minimum coverage path loss and the maximum
                   coverage path loss with \"..\" (two periods)
                
                   between the minimum and maximum values, i.e.,
                   \"<BeaconCoverageTarget_min>..<BeaconCoverageTarget_max>\".
                   These values can be used by the FAP's
                   selfconfiguration algorithms to help derive
                   transmit power levels for the beacon(s) in the
                   presence of co-channel and adjacent channel
                   interference.\"
                
                   <BeaconCoverageTarget_min> and
                   <BeaconCoverageTarget_max> are measured in dB
                   and have a range of [50,150] incremented by 1
                   dB.";
              }
              leaf MaxCoverageEdgePilotStrength {
                type int32 {
                  range "-300..0";
                }
                description
                  "The maximum strength of the received pilot energy
                   per chip, Ec, to total received spectral
                   density, Io (signal and noise) desired for FAP
                   users at the edge of the FAP coverage target
                   in units of {{units}}.  This value can be used
                   by the FAP's self configuration algorithms to
                   help prevent aggressive transmit power level
                   settings .";
              }
              leaf MaxAllowablePilotStrengthDegradation {
                type int32 {
                  range "0..150";
                }
                description
                  "The maximum amount in dB by which the strength of
                   the received pilot energy per chip, Ec, to
                   total received spectral density, Io (signal
                   and
                
                   noise) for alien users can be degraded in the
                   presence of FAP interference at the edge of
                   FAP coverage, in {{units}} units.";
              }
              leaf RFCNFLToProtect {
                type string {
                  length "0..256";
                }
                description
                  "{{list}} Each item is a FL RFCN corresponding to
                   a CDMA2000 carrier that is adjacent to the
                   RFCNFLInUse to be protected from adjacent
                   channel interference.  If any of the items in
                   the list are adjacent to the FAP's own FL
                   channel, the FAP MUST take the PilotStrength
                   and total received power spectral density (Io)
                   measured on these channels into account as
                   part of its maximum transmit power
                   selfconfiguration.
                
                   The RFCNs in the list can belong to any
                   operator, allowing for protection of the FAP
                   operator's own macro layer as well as that of
                   other operators.
                
                   The list should take into account the ability
                   of the FAP to self-configure its own FL RFCN
                   and so SHOULD include any channels (requiring
                   protection) which can potentially be adjacent
                   to the RFCN selected by the FAP.
                
                   For example, if only adjacent operator
                   protection is needed and the FAP has the
                   ability to self-configure to any channel owned
                   by its operator, this list would be populated
                   with the RFCNs immediately above and below the
                   range of channels owned by the FAP operator.
                
                   If an empty string then it indicates that
                   there are no channels adjacent to the FAP that
                   require protection, or that self-configuration
                   of the FAP transmit power is not enabled.";
              }
              leaf FAPAllowedAdjChanCoverageHole {
                type uint32 {
                  range "30..150";
                }
                description
                  "Defines the maximum allowed coverage hole created
                   on carriers listed in RFCNFLToProtect by the
                   FAP transmission, measured in {{units}}, in
                   terms of RF propagation loss such that the
                   {{param|MaxAllowablePilotStrengthDegradation}}
                   is maintained outside the {{param}} for MS on
                   that {{param|RFCNFLToProtect}}.  This value
                   can be used by the FAP's self configuration
                   algorithms to help derive transmit power
                   levels.";
              }
              leaf ACIR {
                type uint32;
                description
                  "AdjacentChannelInterferenceRatio value in
                   {{units}} to be used when determining the
                   coverage hole created on adjacent channels due
                   to leakage.";
              }
            }

            container AccessParameters {
              description
                "The object used for configuring access parameter
                 messages for 1x.  See {{bibref|3GPP2-C.S0005}}.";
              leaf NomPwr {
                type int32 {
                  range "-7..8";
                }
                description
                  "Nominal power correction factor used by the
                   mobile in open loop power adjustment.  See
                   {{bibref|3GPP2-C.S0005}}.";
              }
              leaf InitPwr {
                type int32 {
                  range "-15..16";
                }
                description
                  "Initial power offset used by the mobile in open
                   loop power adjustment.  See
                   {{bibref|3GPP2-C.S0005}}.";
              }
              leaf PwrStepIndb {
                type uint32 {
                  range "0..7";
                }
                description
                  "Power step increment in successive access probes.
                   See {{bibref|3GPP2-C.S0005}}.";
              }
              leaf NomPwrExt {
                type uint32 {
                  range "0..1";
                }
                description
                  "{{param}} should be zero for BC0 and BC1.  For
                   other band classes, {{param}} is 1 if Mobile's
                   correction factor is between -24dBm and -9dBm.
                   Otherwise {{param}} is zero.  See
                   {{bibref|3GPP2-C.S0005}}.";
              }
              leaf APMAuth {
                type uint32 {
                  range "0..1";
                }
                description
                  "Enabling/disabling global authentication.  See
                   {{bibref|3GPP2-C.S0005}}.";
              }
              leaf APMRandUpdatePrd {
                type uint32 {
                  range "16..14400";
                }
                description
                  "The period (in {{units}}) that the BSS updates
                   the RAND value sent via APM.  Only 2 second
                   multiples accepted.";
              }
              leaf Initialpwr {
                type uint32 {
                  range "0..31";
                }
                description
                  "Initial power offset for access.  The base
                   station shall set this field to the correction
                   factor to be used by mobile stations in the
                   open loop power estimate for the initial
                   transmission on an Access Channel, expressed
                   as a two's complement value in units of
                   {{units}}.";
              }
              leaf PwrStep {
                type uint32 {
                  range "0..7";
                }
                description
                  "Power increment.  The base station shall set this
                   field to the value by which mobile stations
                   are to increase their transmit power between
                   successive access probes in an access probe
                   sequence, in units of {{units}}.";
              }
              leaf NumStep {
                type uint32 {
                  range "0..15";
                }
                description
                  "Number of access probes.  The base station shall
                   set this field to one less than the maximum
                   number of access probes mobile stations are to
                   transmit in a single access probe sequence.";
              }
              leaf MaxCapSize {
                type uint32 {
                  range "0..7";
                }
                description
                  "Maximum Access Channel message capsule size.  The
                   base station shall set this field to the value
                   in the range 0 to 7.  {{param}} is set to
                   three less than the maximum number of Access
                   Channel frames in an Access Channel message
                   capsule.";
              }
              leaf PreambleSize {
                type uint32 {
                  range "0..15";
                }
                description
                  "Access Channel preamble length.  The base station
                   shall set this field to one less than the
                   number of Access Channel frames that mobile
                   stations are to transmit in each Access
                   Channel preamble.";
              }
              leaf Psist09 {
                type uint32 {
                  range "0..63";
                }
                description
                  "Persistence value for access probes sent by
                   mobiles with Access Overload calls values of 0
                   - 9.  A value of 63 indicates such mobiles are
                   not allowed to send access probes.";
              }
              leaf Psist10 {
                type uint32 {
                  range "0..7";
                }
                description
                  "Persistence value for access probes sent by
                   mobiles with Access Overload calls values of
                   10 (test Mobile).  A value of 7 indicates such
                   mobiles are not allowed to send access probes.";
              }
              leaf Psist11 {
                type uint32 {
                  range "0..7";
                }
                description
                  "Persistence value for access probes sent by
                   mobiles with Access Overload calls values of
                   11 (emergency Mobile).  A value of 7 indicates
                   such mobiles are not allowed to send access
                   probes.";
              }
              leaf Psist12 {
                type uint32 {
                  range "0..7";
                }
                description
                  "Persistence value for access probes sent by
                   mobiles with Access Overload calls values of
                   12.  A value of 7 indicates such mobiles are
                   not allowed to send access probes.";
              }
              leaf Psist13 {
                type uint32 {
                  range "0..7";
                }
                description
                  "Persistence value for access probes sent by
                   mobiles with Access Overload calls values of
                   13.  A value of 7 indicates such mobiles are
                   not allowed to send access probes.";
              }
              leaf Psist14 {
                type uint32 {
                  range "0..7";
                }
                description
                  "Persistence value for access probes sent by
                   mobiles with Access Overload calls values of
                   14.  A value of 7 indicates such mobiles are
                   not allowed to send access probes.";
              }
              leaf Psist15 {
                type uint32 {
                  range "0..7";
                }
                description
                  "Persistence value for access probes sent by
                   mobiles with Access Overload calls values of
                   15.  A value of 7 indicates such mobiles are
                   not allowed to send access probes.";
              }
              leaf MsgPsist {
                type uint32 {
                  range "0..7";
                }
                description
                  "Persistence modifier for access channel attempts
                   transmitting a message.";
              }
              leaf RegPsist {
                type uint32 {
                  range "0..7";
                }
                description
                  "Persistence modifier for registration message
                   transmission.";
              }
              leaf ProbePNRan {
                type uint32 {
                  range "0..9";
                }
                description
                  "Time randomization for access channel probes.";
              }
              leaf AccTmo {
                type uint32 {
                  range "0..15";
                }
                description
                  "Access transmission timeout.  Two less than the
                   time the mobile has to wait before determining
                   that the probe is not received by the BSS.  It
                   is in {{units}}.";
              }
              leaf ProbeBkoff {
                type uint32 {
                  range "0..15";
                }
                description
                  "One less than maximum number for randomized delay
                   between successive access probes in {{units}}.";
              }
              leaf Bkoff {
                type uint32 {
                  range "0..15";
                }
                description
                  "One less than maximum number for randomized delay
                   between successive access sequences in
                   {{units}}.";
              }
              leaf MaxReqSeq {
                type uint32 {
                  range "0..15";
                }
                description
                  "Maximum number of access probe sequences for an
                   access request.";
              }
              leaf MaxRspSeq {
                type uint32 {
                  range "0..15";
                }
                description
                  "Maximum number of access probe sequences for an
                   access response";
              }
            }

            container SystemParameters {
              description
                "The object used for configuring system parameter
                 messages for 1x";
              leaf RegZone {
                type uint32 {
                  range "0..4095";
                }
                description
                  "registration zone number (refer to Section
                   2.6.5.1.5 of {{bibref|3GPP2-C.S0005}})";
              }
              leaf TotalZones {
                type uint32 {
                  range "0..7";
                }
                description
                  "Total number of zones the mobile shall retain for
                   zone based registration.  See
                   {{bibref|3GPP2-C.S0005}}.";
              }
              leaf ZoneTimer {
                type uint32 {
                  range "0..7";
                }
                description
                  "timer value to be used by the mobile in the zone
                   registration timer.  Refer to table
                   3.7.2.3.2.1-1 of the standard
                   {{bibref|3GPP2-C.S0005}}.";
              }
              leaf RegPeriod {
                type uint32 {
                  range "29..85";
                }
                description
                  "Registration period for timer based registration.
                   Registration period is calculated from the
                   formula 2^(REG_PRD/4) x 0.08 seconds.  Thus a
                   value of 59 corresponds to 1853.6 seconds (~
                   1/2 hour).  See {{bibref|3GPP2-C.S0005}}.";
              }
              leaf SrchWinA {
                type uint32 {
                  range "0..15";
                }
                description
                  "Search window size to be used ny the mobile for
                   active set and candidate set.  Refer to table
                   2.6.6.2.1-1 of {{bibref|3GPP2-C.S0005}}.  For
                   example, 11 corresponds to 130 chips";
              }
              leaf SrchWinN {
                type uint32 {
                  range "0..15";
                }
                description
                  "Search window size to be used by the mobile for
                   neighbor set.  Refer to table 2.6.6.2.1-1 of
                   {{bibref|3GPP2-C.S0005}}.  For example, 8
                   corresponds to 60 chips";
              }
              leaf SrchWinR {
                type uint32 {
                  range "0..15";
                }
                description
                  "Search window size to be used by the mobile for
                   remaining set.  Refer to table 2.6.6.2.1-1 of
                   {{bibref|3GPP2-C.S0005}}.  For example, 8
                   corresponds to 60 chips";
              }
              leaf NghbrMaxAge {
                type uint32 {
                  range "0..15";
                }
                description
                  "neighbor set maximum age beyond which the mobiles
                   are supposed to drop a neighbor.  This is the
                   count of neighbout list updat or extended
                   neighbor list updates a mobile shall receive
                   before removing a neighbor from the neighbor
                   list.  See {{bibref|3GPP2-C.S0005}}.";
              }
              leaf PwrRepThresh {
                type uint32 {
                  range "0..31";
                }
                description
                  "Power control reporting threshold.  Number of bad
                   frames a mobile should receive before sending
                   a PMRM message.  See {{bibref|3GPP2-C.S0005}}.";
              }
              leaf PwrRepFrames {
                type uint32 {
                  range "0..15";
                }
                description
                  "Duration (in number of frames) for measuring bad
                   frames - given by equation
                   2^(PWR_REP_FRAMES/2) x 5 frames.  For example,
                   6 corresponds to 40 frames.  See
                   {{bibref|3GPP2-C.S0005}}.";
              }
              leaf PwrThreshEnable {
                type uint32 {
                  range "0..1";
                }
                description
                  "enable/disable power measurement report message.
                   See {{bibref|3GPP2-C.S0005}}.";
              }
              leaf PwrPeriodEnable {
                type uint32 {
                  range "0..1";
                }
                description
                  "enable/disable periodic power measurement report
                   message.  See {{bibref|3GPP2-C.S0005}}.";
              }
              leaf PwrRepDelay {
                type uint32 {
                  range "0..32";
                }
                description
                  "Delay (in unit of four frames) following a PMRM
                   before the mobile restarts counting bad frames
                   for power control measuremnt.  See
                   {{bibref|3GPP2-C.S0005}}.";
              }
              leaf Rescan {
                type uint32 {
                  range "0..1";
                }
                description
                  "If {{param}} is set to 1, the mobiles should
                   restart and reinitialize the System Parameters
                   message.  See {{bibref|3GPP2-C.S0005}}.";
              }
              leaf Tadd {
                type uint32 {
                  range "0..63";
                }
                description
                  "Power threshold (in {{units}}) for transferring a
                   neighbor from neighbor set or remaining set to
                   active set.  For example, a value of 26
                   corresponds to -13 dB.  See
                   {{bibref|3GPP2-C.S0005}}.";
              }
              leaf Tdrop {
                type uint32 {
                  range "0..63";
                }
                description
                  "Drop threshold (in {{units}}) to start a handoff
                   timer to drop a neighbor from active or
                   candidate set.  For example, 30 corresponds to
                   -15dB.  See {{bibref|3GPP2-C.S0005}}.";
              }
              leaf Tcomp {
                type uint32 {
                  range "0..15";
                }
                description
                  "If a pilot in condidate set exceeds the power of
                   a pilot in active set by threshold, the mobile
                   shall send a power strenght measurement report
                   message.  This threshold is defined in unit of
                   {{units}}.  For example, 5 corresponds to a
                   threshold of 2.5 dB.  See
                   {{bibref|3GPP2-C.S0005}}.";
              }
              leaf TTdrop {
                type uint32 {
                  range "0..15";
                }
                description
                  "Timer value for which an action is taken by the
                   mobile for a neighbor in candidate set or in
                   active set.  Refer to Table 2.6.6.2.3-1 of the
                   {{bibref|3GPP2-C.S0005}} for details.  For
                   example, 3 corresponds to four seconds";
              }
              leaf InTrafficTadd {
                type uint32 {
                  range "0..63";
                }
                description
                  "T-ADD value (in {{units}}) used for in-traffic
                   system parameter message.  See
                   {{bibref|3GPP2-C.S0005}}.";
              }
              leaf InTrafficTdrop {
                type uint32 {
                  range "0..63";
                }
                description
                  "T-Drop value (in {{units}}) used in in-traffic
                   system parameter message.  See
                   {{bibref|3GPP2-C.S0005}}.";
              }
              leaf InTrafficTcomp {
                type uint32 {
                  range "0..15";
                }
                description
                  "T_Comp value (in {{units}}) used for in-traffic
                   system parameter message.  See
                   {{bibref|3GPP2-C.S0005}}.";
              }
              leaf InTrafficTtdrop {
                type uint32 {
                  range "0..15";
                }
                description
                  "T_Tdrop timer value value used for in-traffic
                   system parameter message.  See
                   {{bibref|3GPP2-C.S0005}}.";
              }
            }

            container ExtendedSystemParameters {
              description
                "The object used for configuring extended system
                 parameter messages for 1x";
              leaf Prev {
                type uint32 {
                  range "0..255";
                }
                description
                  "protocol revision";
              }
              leaf PMinRev {
                type uint32 {
                  range "0..255";
                }
                description
                  "minimum protocol revision";
              }
              leaf DeleteForTMSI {
                type uint32 {
                  range "0..1";
                }
                description
                  "Delete Foreign TMSI.
                
                   The base station shall set this field to '1'
                   to cause the mobile station to delete its TMSI
                   if the TMSI was assigned in a different TMSI
                   zone from that specified by the TMSI_ZONE
                   field of this message; otherwise, the base
                   station shall set this field to '0'.";
              }
              leaf UseTMSI {
                type uint32 {
                  range "0..1";
                }
                description
                  "Use TMSI indicator.
                
                   The base station shall set this field to the
                   value shown next field corresponding to the
                   type of MSID that the mobile station is to use
                   on the Access Channel.";
              }
              leaf PrefMSIDType {
                type uint32 {
                  range "0..3";
                }
                description
                  "Preferred Access Channel Mobile Station
                   Identifier Type.  F294.
                
                   The base station shall set this field to the
                   value shown as below corresponding to the type
                   of MSDI that the mobile station is to use on
                   the Access Channel.
                
                   [useTMSI] [prefMSIDType] [description]
                
                   0 00 IMSI_S and ESN
                
                   0 10 IMSI
                
                   0 11 IMSI and ESN
                
                   1 10 TMSI; IMSI
                
                   1 11 TMSI; IMSI and ESN";
              }
              leaf MCC {
                type uint32 {
                  range "0..1023";
                }
                description
                  "Mobile Country Code.  See
                   {{bibref|3GPP2-C.S0005}}.";
              }
              leaf IMSI1112 {
                type uint32 {
                  range "0..255";
                }
                description
                  "11th and 12th digits of IMSI.  See
                   {{bibref|3GPP2-C.S0005}}.";
              }
              leaf TMSIZoneLen {
                type uint32 {
                  range "1..8";
                }
                description
                  "TMSI zone length.
                
                   The base station shall set this field to the
                   number of octets included in the TMSI_ZONE.
                   The base station shall set this field to a
                   value in the range 1 to 8 inclusive.";
              }
              leaf TMSIZone {
                type uint32 {
                  range "0..65535";
                }
                description
                  "TMSI zone.
                
                   The base station shall set this field to the
                   TMSI zone number as specified in
                   {{bibref|3GPP2-N.S0010}}.";
              }
              leaf BcastIndex {
                type uint32 {
                  range "0..7";
                }
                description
                  "Broadcast slot cycle index.  To enable periodic
                   broadcast paging, the base station shall set
                   this field to and unsigned 3-bit number in the
                   range 1-7, equal to the broadcast slot cycle
                   index.  To disable periodic broadcast paging,
                   the base station shall set this field to
                   '000'.";
              }
              leaf IMSITSupported {
                type int32 {
                  range "0..1";
                }
                description
                  "1: IMISI_T is supported, 0: IMSI_T is not
                   supported.  See {{bibref|3GPP2-C.S0005}}.";
              }
              leaf SoftSlope {
                type uint32 {
                  range "0..63";
                }
                description
                  "The slope in the inequality criterion for adding
                   a pilot to the Active Set, or dropping a pilot
                   from the Active Set.  The base station shall
                   set this field as an unsigned binary number.";
              }
              leaf AddIntercept {
                type uint32 {
                  range "0..63";
                }
                description
                  "The intercept in the inequality criterion for
                   adding a pilot to the Active Set.  The base
                   station shall set this field as a two's
                   complement signed binary number, in units of
                   {{units}}.";
              }
              leaf DropIntercept {
                type uint32 {
                  range "0..63";
                }
                description
                  "The intercept in the inequality criterion for
                   dropping a pilot from the Active Set.  The
                   base station shall set this field as a two's
                   complement signed binary number, in units of
                   {{units}}.";
              }
              leaf MaxNumAltSo {
                type uint32 {
                  range "0..7";
                }
                description
                  "Maximum number of alternative service options.
                   The base station shall set this field to the
                   maximum number of alternative service option
                   numbers that the mobile station is allowed to
                   include in the Origination Message or the Page
                   Response Message.
                
                   For mobile stations with MOB_P_REVs less than
                   seven, the alternative service options are
                   those service options defined in TSB-58B and
                   related to SERVICE_OPTION in Origination
                   Message and the Page Response Message.
                
                   For mobile stations with MOB_P_REVs equal to
                   or greater than seven, the alternative service
                   options are those service options defined in
                   TSB-58B without service group number assigned
                   and related to SERVICE_OPTION in Origination
                   Message and the Page Response Message.
                
                   The base station sets this field to a value
                   greater than zero, in addition, the base
                   station shall allow the mobile station with
                   MOB_P_REVs equal to or greater than 7 to
                   include
                
                   - a 4 or 8-bit service option bitmap in the
                   Origination Message and the Page Response
                   Message;
                
                   - alternative service option numbers, not
                   limited to MAX_ALT_SO_NUM, in the Enhanced
                   Origination Message.";
              }
              leaf ReselectedIncluded {
                type uint32 {
                  range "0..1";
                }
                description
                  "System reselection parameters included.
                
                   If the base station is including system
                   reselection parameters, the base station shall
                   set this field to '1'; otherwise, the base
                   station shall set this field to '0'.";
              }
              leaf EcThresh {
                type uint32;
                description
                  "Pilot power threshold.
                
                   If RESELECTINCLUDED is set to '1', the base
                   station shall include the field EC_THRESH and
                   set this field to:
                
                   [ (pilot_power_threshold + 115 ) ]
                
                   where pilot_power_threshold is the pilot
                   power, Ec, in {{units}}/1.23 MHz, below which
                   the mobile station is to perform system
                   reselection; otherwise, the base station shall
                   omit this field.";
              }
              leaf EcIoThresh {
                type uint32;
                description
                  "Pilot Ec / Io threshold.
                
                   If RESELECTINCLUDED is set to '1', the base
                   station shall include the field EC_I0_THRESH
                   and set this field to:
                
                   [ - 20 x log10 (pilot_threshold) ]
                
                   where pilot_threshold is the pilot Ec/Io below
                   which the mobile station is to perform system
                   reselection; otherwise, the base station shall
                   omit this field.";
              }
              leaf PilotReport {
                type uint32 {
                  range "0..1";
                }
                description
                  "Pilot reporting indicator.
                
                   The base station shall set this field to '1'
                   if the mobile station is to report the
                   additional pilots which have pilot strength
                   exceeding T_ADD in all Access Channel
                   messages.  The base station shall set this
                   field to '0' if the mobile station is to
                   report the additional pilots which have pilot
                   strengths exceeding T_ADD only in the
                   Origination Message and the Page Response
                   Message.";
              }
              leaf NghbrSetEntryInfo {
                type uint32 {
                  range "0..1";
                }
                description
                  "Neighbor Set access entry handoff information
                   included indicator.
                
                   If the base station is including information
                   on the Neighbor Set access entry handoff, the
                   base station shall set this field to '1';
                   otherwise, the base station shall set this
                   field to '0'.";
              }
              leaf AccessHOOrder {
                type uint32 {
                  range "0..1";
                }
                description
                  "Access entry handoff permitted indicator.
                
                   If NghbrSetEntryInfo is set to '1', the base
                   station shall set this field to '1' if the
                   mobile station is permitted to perform an
                   access entry handoff after receiving a message
                   while performing the Mobile Station Order and
                   Message Processing Operation in the Mobile
                   Station Idle State; otherwise, the base
                   station shall set this field to '0'.";
              }
              leaf NghbrSetAccessInfo {
                type uint32 {
                  range "0..1";
                }
                description
                  "Neighbor Set access handoff included indicator.
                
                   If the base station is including information
                   on the Neighbor Set access handoff or access
                   probe handoff, the base station shall set this
                   field to '1', otherwise, the base station
                   shall set this field to '0'.";
              }
              leaf AccessHO {
                type uint32 {
                  range "0..1";
                }
                description
                  "Access handoff permitted indicator.
                
                   If NghbrSetEntryInfo is set to '1', the base
                   station shall set this field to '1' if the
                   mobile station is permitted to perform an
                   access handoff; otherwise, the base station
                   shall set this field to '0'.";
              }
              leaf AccessHOMsgRsp {
                type uint32 {
                  range "0..1";
                }
                description
                  "Access handoff permitted for message response
                   indicator.
                
                   If AccessHO is set to '1', the base station
                   shall include this field and set it as
                   described below; otherwise, the base station
                   shall omit this field.
                
                   The base station shall set this field to '1'
                   if the mobile station is permitted to perform
                   an access handoff after receiving a message
                   and before responding to that message in the
                   System Access State; otherwise, the base
                   station shall set this field to '0'.";
              }
              leaf AccessProbeHO {
                type uint32 {
                  range "0..1";
                }
                description
                  "Access probe handoff permitted indicator.
                
                   If NghbrSetEntryInfo is set to '1', the base
                   station shall set this field to '1' if the
                   base station is permitted to perform an access
                   probe handoff; otherwise, the base station
                   shall set this field to '0'.";
              }
              leaf AccHOListUpd {
                type uint32 {
                  range "0..1";
                }
                description
                  "Access handoff list update permitted indicator.
                
                   If AccessProbeHO is included and is set to
                   '1', the base station shall set this field to
                   '1' if the mobile station is permitted to
                   update the access handoff list during an
                   access attempt; otherwise, the base station
                   shall set this field to '0'.";
              }
              leaf AccProbeHOOtherMsg {
                type uint32 {
                  range "0..1";
                }
                description
                  "Access probe handoff permitted for messages other
                   than the Origination Message and the Page
                   Response Message.
                
                   If AccessProbeHO is set to '1', the base
                   station shall set this field to '1' if the
                   mobile station is permitted to perform an
                   access probe handoff for messages other than
                   the Origination Message and the Page Response.
                   The base station shall set this field to '0'
                   if the mobile station is permitted to perform
                   an access probe handoff only for the
                   Origination Message and the Page Response
                   Message.";
              }
              leaf MaxNumProbeHO {
                type uint32 {
                  range "0..3";
                }
                description
                  "Maximum number of times that mobile station is
                   permitted to perform an access probe handoff.
                
                   If AccessProbeHO is set to '1', the base
                   station shall set this field to the maximum
                   number of times the mobile station is allowed
                   to perform an access probe handoff within an
                   access attempt minus one.";
              }
              leaf BrdcastGPSAssit {
                type uint32 {
                  range "0..1";
                }
                description
                  "If {{param}} is set to 1, then Braodcast GPS
                   assist is supported.  See
                   {{bibref|3GPP2-C.S0005}}.";
              }
              leaf QPCHSupported {
                type uint32 {
                  range "0..1";
                }
                description
                  "Quick Paging Channel Supported Indication.
                
                   If the base station supports Quick Paging
                   Channel operation, the base station shall set
                   this field to '1'; otherwise the base station
                   shall set this field to '0'.";
              }
              leaf NumQPCH {
                type uint32 {
                  range "1..3";
                }
                description
                  "Number of Quick Paging Channels.
                
                   If the base station sets QPCHSUPPORTED to '1',
                   the base station shall include this field and
                   set it as described below; otherwise, the base
                   station shall omit this field.
                
                   The base station shall set this field to the
                   number of Quick Paging Channels on this CDMA
                   Channel.  The base station shall not set this
                   field to '00'.";
              }
              leaf QPCHRate {
                type uint32 {
                  range "0..1";
                }
                description
                  "Quick Paging Channel indicator rate.
                
                   See {{bibref|3GPP2-C.S0005}}.  {{param}} is
                   set as follows: 0: 4800bps; 1: 9600bps.";
              }
              leaf QPCHPwrLevelPage {
                type uint32 {
                  range "0..7";
                }
                description
                  "Quick Paging Channel paging indicator transmit
                   power level.
                
                   {{param}} is set as follows: 0: 5 dB below; 1:
                   4 dB below; 2: 3 dB below; 3: 2 dB below; 4: 1
                   dB below; 5: Same; 6: 1 dB above; 7: 2dB
                   above.";
              }
              leaf QPCHcciSupported {
                type uint32 {
                  range "0..1";
                }
                description
                  "Quick Paging Channel configuration change
                   indicator supported.
                
                   {{param}} is set as follows: if the base
                   station is to support configuration change
                   indicators on the Quick Paging Channel,
                   {{param}} to '1'; otherwise {{param}} is set
                   to '0'.";
              }
              leaf QPCHPwrLevelConfig {
                type uint32 {
                  range "0..255";
                }
                description
                  "Quick Paging Channel configuration change
                   indicator CONFIG transmit power level.
                
                   See {{bibref|3GPP2-C.S0005}}.";
              }
              leaf SDBSupported {
                type uint32 {
                  range "0..1";
                }
                description
                  "Short Data Burst supported indicator.
                
                   See {{bibref|3GPP2-C.S0005}}.";
              }
              leaf RLgainTrafficPilot {
                type uint32 {
                  range "0..63";
                }
                description
                  "Gain adjustment of the Reverse Traffic Channel
                   relative to the Reverse Pilot Channel for
                   Radio Configurations greater than 2.
                
                   {{param}} is set to the correction factor to
                   be used by mobile stations in setting the
                   power of a reverse traffic channel, expressed
                   as a two's complement value in units of
                   {{units}}.";
              }
              leaf RvsPwrCtrlDelayIncl {
                type uint32 {
                  range "0..1";
                }
                description
                  "Reverse Power Control Delay included indicator.
                
                   See {{bibref|3GPP2-C.S0005}}.";
              }
              leaf RvsPwrCtrlDelay {
                type uint32 {
                  range "0..3";
                }
                description
                  "The reverse power control delay.
                
                   {{param}} is setto the closed-loop reverse
                   power control delay minus one (the closed-loop
                   reverse power control delay is the time
                   between the end of a gated-on reverse PCG and
                   the beginning of the Forward Power Control
                   Subchannel in units of {{units}}.";
              }
            }

            container ForwardPwrCtr {
              description
                "The object used for configuring extended channel
                 assignment messages for 1x";
              leaf FPCFCHInitSetpt {
                type int32 {
                  range "-128..127";
                }
                description
                  "Initial Fundamental Channel outer loop Eb/Nt
                   setpoint in {{units}}.  For example, 56
                   corresponds to 7 dB.  See
                   {{bibref|3GPP2-C.S0005}}.";
              }
              leaf FPCSubchanGain {
                type int32 {
                  range "-16..15";
                }
                description
                  "Forward power control subchannel relative to fwd
                   traffic channel in {{units}}.  See
                   {{bibref|3GPP2-C.S0005}}.";
              }
              leaf RLGainAdj {
                type int32 {
                  range "-8..7";
                }
                description
                  "Reverse Traffic Channel power relative to access
                   power in {{units}}.  See
                   {{bibref|3GPP2-C.S0005}}.";
              }
              leaf FPCFCHFER {
                type uint32 {
                  range "0..31";
                }
                description
                  "Fundamental Channel target frame error rate.
                   Refer to table 3.7.3.3.2.25-2 of
                   {{bibref|3GPP2-C.S0005}}";
              }
              leaf FPCFCHMinSetpt {
                type int32 {
                  range "-128..127";
                }
                description
                  "Minimum Fundamental Channel Outer Loop Eb/Nt
                   setpoint in {{units}}.  See
                   {{bibref|3GPP2-C.S0005}}.";
              }
              leaf FPCFCHMaxSetpt {
                type int32 {
                  range "-128..127";
                }
                description
                  "Maximum Fundamental Channel Outer Loop Eb/Nt
                   setpoint in {{units}}.  See
                   {{bibref|3GPP2-C.S0005}}.";
              }
            }

            container HardHandoff {
              description
                "This object provides configurable parameters for 1x
                 Handout";
              leaf HandoutEnable {
                type boolean;
                description
                  "Enabling handout operation.";
              }
              leaf HOPilotPowerThresh {
                type int32 {
                  range "0..5";
                }
                description
                  "Pilot power threshold (in {{units}} relative to
                   the FAP pilot power) for handout declaration";
              }
              leaf HOPilotDuration {
                type uint32 {
                  range "20..50";
                }
                description
                  "Timethreshold for handout declaration (in
                   {{units}})";
              }

              container Stats {
                config false;
                description
                  "This object contains statistics for all Handouts
                   of the 1x FAP.";
                leaf TxHORequired {
                  type uint32 {
                    range "0..4294967295";
                  }
                  description
                    "Total number of Handout Required messages sent
                     to the MSC";
                }
                leaf RxHOCommand {
                  type uint32 {
                    range "0..4294967295";
                  }
                  description
                    "Total number of Handout Command messegaes
                     received from the MSC";
                }
                leaf HORequiredRejected {
                  type uint32 {
                    range "0..4294967295";
                  }
                  description
                    "Total number of HO required requests rejected
                     by the MSC";
                }
                leaf HORequiredUnanswered {
                  type uint32 {
                    range "0..4294967295";
                  }
                  description
                    "Total number of HO required requests for which
                     no response received from the MSC";
                }
                leaf TxUHDM {
                  type uint32 {
                    range "0..4294967295";
                  }
                  description
                    "Total number UHDMs sent to mobiles";
                }
                leaf RxNSAck {
                  type uint32 {
                    range "0..4294967295";
                  }
                  description
                    "Total number of MSAcks received from the mobile
                     in response to UHDM";
                }
                leaf HOFailureCount {
                  type uint32 {
                    range "0..4294967295";
                  }
                  description
                    "Total number of Handout attempts declared as
                     failure";
                }
                leaf CallDropCount {
                  type uint32 {
                    range "0..4294967295";
                  }
                  description
                    "Total numer of call drops after a HO attempt.
                     RTC lost without MSack";
                }
                leaf TxHOCommence {
                  type uint32 {
                    range "0..4294967295";
                  }
                  description
                    "Number of Handout Commenced messages sent to
                     MSC";
                }
                leaf RxHOSessionClear {
                  type uint32 {
                    range "0..4294967295";
                  }
                  description
                    "Number of session clear commands received form
                     the core";
                }
                leaf ReturnOnFailureCount {
                  type uint32 {
                    range "0..4294967295";
                  }
                  description
                    "Total number of times a Return On Handoff
                     failure was declared";
                }
                leaf OnePilotReportCount {
                  type uint32 {
                    range "0..4294967295";
                  }
                  description
                    "Number of times only one pilot was reported in
                     HO Required message";
                }
                leaf TwoPilotReportCount {
                  type uint32 {
                    range "0..4294967295";
                  }
                  description
                    "Number of times only two pilot was reported in
                     HO Required message";
                }
                leaf ThreePilotReportCount {
                  type uint32 {
                    range "0..4294967295";
                  }
                  description
                    "Number of times only three pilot was reported
                     in HO Required message";
                }
              }
            }

            container PowerControl {
              description
                "Configuration Managed Object for OTA power control
                 attribute.";
              leaf OneXPCFPCIncl {
                type int32 {
                  range "0..1";
                }
                description
                  "Whether Forward power control information
                   included in Power Control message";
              }
              leaf OneXPCFPCFCHMinSetpt {
                type int32 {
                  range "0..255";
                }
                description
                  "The value for the minimum Fundamental Channel
                   Outer Loop Eb/Nt setpoint, in units of
                   {{units}}.";
              }
              leaf OneXPCFPCFCHMaxSetpt {
                type int32 {
                  range "0..255";
                }
                description
                  "The value for the maximum Fundamental Channel
                   Outer Loop Eb/Nt setpoint, in units of
                   {{units}}.";
              }
              leaf OneXPCRPCIncl {
                type int32 {
                  range "0..1";
                }
                description
                  "Whether reverse Power control information
                   included in the Power Control Message.";
              }
              leaf OneXPCFCHChanAdjGain {
                type int32 {
                  range "-48..48";
                }
                description
                  "Channel adjustment gain (in {{units}}) for
                   Reverse Fundamental Channel.";
              }
              leaf OneXPCPwrRepThresh {
                type uint32 {
                  range "0..31";
                }
                description
                  "The number of bad frames to be received in a
                   measurement period on the channel which
                   carries the Power Control Subchannel before
                   mobile stations are to generate a Power
                   easurement Report Message";
              }
              leaf OneXPCPwrRepFrames {
                type uint32 {
                  range "0..15";
                }
                description
                  "Power control reporting frame count.  Number of
                   frames over which the mobile station measures
                   frame errors.  For example, 7 corresponds to
                   55 frames.  Refer to {{bibref|3GPP2-C.S0005}}
                   for mapping between this value and the actual
                   frame count.";
              }
              leaf OneXPwrThreshEnable {
                type int32 {
                  range "0..1";
                }
                description
                  "Threshold report mode indicator.  If the mobile
                   station is to generate threshold Power
                   Measurement Report Messages, the base station
                   shall set this field to '1'.  If the mobile
                   station is not to generate threshold Power
                   Measurement Report Messages, the base station
                   shall set this field to '0'.";
              }
              leaf OneXPCPwrPeriodEnable {
                type int32 {
                  range "0..1";
                }
                description
                  "Periodic report mode indicator.  If the mobile
                   station is to generate periodic Power
                   Measurement Report Messages, the base station
                   shall set this field to '1'.  If the mobile
                   station is not to generate periodic Power
                   Measurement Report Messages, the base station
                   shall set this field to '0'.";
              }
              leaf OneXPCPwrRepDelay {
                type uint32 {
                  range "0..31";
                }
                description
                  "Power report delay.  The period that the mobile
                   station waits following a Power Measurement
                   Report Message before restarting frame
                   counting for power control purposes.  The base
                   station shall set this field to the power
                   report delay values in units of {{units}}.";
              }
            }

            list NeighborList {
              key "OneXNeighborIndex NeighborPN";
              description
                "This object contains information common to all
                 neighbors of a sector.  This object has only one
                 instance.";
              leaf Enable {
                type boolean;
                default "false";
                description
                  "Enables or disables the {{object}} entry.";
              }
              leaf PilotInc {
                type int32 {
                  range "1..15";
                }
                default "1";
                description
                  "pilot increment policy for this network.  See
                   {{bibref|3GPP2-C.S0005}}.";
              }
              leaf OneXNeighborIndex {
                type int32 {
                  range "0..19";
                }
                default "0";
                description
                  "Macro neighbour index.  See
                   {{bibref|3GPP2-C.S0005}}.";
              }
              leaf NeighborConfig {
                type enumeration {
                  enum "SameConfig";
                  enum "SamePaging";
                  enum "DiffPaging";
                  enum "Unknown";
                }
                default "SameConfig";
                description
                  "Neighbor configuration in terms of number of
                   frequencies having paging channels as defined
                   in Section 3.7.2.3.2 of the
                   {{bibref|3GPP2-C.S0005}} standard";
              }
              leaf NeighborPN {
                type int32 {
                  range "0..511";
                }
                default "0";
                description
                  "PN offset of the neighbor.  See
                   {{bibref|3GPP2-C.S0005}}.";
              }
              leaf SearchPriority {
                type enumeration {
                  enum "Low";
                  enum "Medium";
                  enum "High";
                  enum "VeryHigh";
                }
                default "Medium";
                description
                  "priority level for serching this neighbor.  See
                   {{bibref|3GPP2-C.S0005}}.";
              }
              leaf NeighborBand {
                type enumeration {
                  enum "0";
                  enum "1";
                  enum "2";
                  enum "3";
                  enum "4";
                  enum "5";
                  enum "6";
                }
                description
                  "Neighbor band class.  See
                   {{bibref|3GPP2-C.S0005}}.";
              }
              leaf NeighborFrequency {
                type int32 {
                  range "0..2016";
                }
                default "0";
                description
                  "frequency of neighbor.  See
                   {{bibref|3GPP2-C.S0005}}.";
              }
              leaf FrequencyIncluded {
                type int32 {
                  range "0..1";
                }
                default "1";
                description
                  "Flag to indicate if the channel id included.  See
                   {{bibref|3GPP2-C.S0005}}.";
              }
              leaf InTraffic {
                type int32 {
                  range "0..1";
                }
                default "1";
                description
                  "whether this neighbor can be used for in-traffic
                   neighborlist message";
              }
              leaf OverheadMsg {
                type int32 {
                  range "0..1";
                }
                default "1";
                description
                  "whether this neighbor can be used for overhead
                   neighborlist message";
              }
              leaf BaseIdentifier {
                type int32;
                default "0";
                description
                  "unique identifire of the neighboring cell
                   (optional)";
              }
              leaf AirInterface {
                type enumeration {
                  enum "OneX";
                  enum "IS95";
                  enum "HRPD";
                  enum "Other";
                }
                default "OneX";
                description
                  "Air interface technology of the neighbor.";
              }
              leaf HandOutCapable {
                type int32 {
                  range "0..1";
                }
                default "0";
                description
                  "Flag to indicate if the handOutCapability is
                   possible.";
              }
              leaf OneXNeighborLongitude {
                type string {
                  length "0..16";
                }
                default "";
                description
                  "Longitude for this neighbor.  Parameter is a
                   string representing a floating point real
                   number (+/- XXX.YY).  Where + for East, - for
                   West, XXX.Y ranges between 0.0 and 180.0 .";
              }
              leaf OneXNeighborLatitude {
                type string {
                  length "0..16";
                }
                default "";
                description
                  "Lattitude for this neighbor.  Parameter is a
                   string representing a floating point number
                   (+/-XX.Y).  + for North, - for South, XX.Y
                   ranges between 0.0 and 90.0.";
              }
              leaf OneXNeighborMSCId {
                type uint32 {
                  range "0..16777215";
                }
                default "0";
                description
                  "IOS MSCID of the neighbors.  See
                   {{bibref|3GPP2-A.S0014}}.";
              }
              leaf OneXNeighborIOSCellId {
                type uint32 {
                  range "0..65535";
                }
                default "0";
                description
                  "Cell Identifier of the neighbor (formatted
                   according to Cell Identification Discriminator
                   = '0000 0010', i.e., 12-bit cell value and
                   4-bit sector value).  See
                   {{bibref|3GPP2-A.S0014}}.";
              }
              leaf ForceInOverhead {
                type boolean;
                default "false";
                description
                  "If {{param}} is set to {{true}}, the FAP SHOULD
                   include this Neighbor List entry in the
                   Neighbor List overhead messages (see
                   {{bibref|3GPP2-C.S0005}}.  Otherwise,
                   {{param}} is set to {{false}}, in which case
                   the FAP MAY include this Neighbor List entry
                   in the Neighbor List overhead messages.";
              }
              leaf IncludedInOverhead {
                type boolean;
                config false;
                description
                  "If {{param}} is set to {{true}}, the FAP is
                   currently including this Neighbor List entry
                   in the Neighbor List overhead messages (see
                   {{bibref|3GPP2-C.S0005}}.  Otherwise,
                   {{param}} is set to {{false}}.";
              }
            }

            container APIDM {
              description
                "This object can be configured only if
                 {{param|.Capabilities.CDMA2000.OneX.FemtoOverheadMessagesCapable}}
                 is set to {{true}}.";
              leaf AssociationType {
                type uint32 {
                  range "0..7";
                }
                description
                  "The FAP shall set this field to the value shown
                   in {{bibref|3GPP2-C.S0005}} corresponding to
                   the configuration of the base station.";
              }
              leaf APIDLEN {
                type uint32 {
                  range "0..15";
                }
                description
                  "The FAP shall set this field to the length of the
                   access point identification in units of 16
                   bits.  Refer to {{bibref|3GPP2-C.S0005}}.";
              }
              leaf APID {
                type yang:hex-string {
                  length "0..16";
                }
                description
                  "Access Point Identification.  Refer
                   {{bibref|3GPP2-C.S0005}} for definition.";
              }
              leaf APIDMASK {
                type uint32 {
                  range "0..255";
                }
                description
                  "Access Point identification Mask.  Refer
                   {{bibref|3GPP2-C.S0005}} for definition.";
              }
              leaf IOSMSCID {
                type uint32 {
                  range "0..16777215";
                }
                description
                  "MSC_ID of the base station.  Refer
                   {{bibref|3GPP2-C.S0005}} for definition.";
              }
              leaf IOSCELLID {
                type uint32 {
                  range "0..65535";
                }
                description
                  "CELL_ID of the base station.  Refer
                   {{bibref|3GPP2-C.S0005}} for definition.";
              }
              leaf INTRAFREQHOHYSINCL {
                type boolean;
                description
                  "This field indicates whether the INTRAFREQHOHYS
                   field is valid and included in Access Point
                   Identification message.  Refer
                   {{bibref|3GPP2-C.S0005}} for definition.";
              }
              leaf INTRAFREQHOHYS {
                type uint32 {
                  range "0..127";
                }
                description
                  "Intra Frequency Handoff Hysteresis.  Refer
                   {{bibref|3GPP2-C.S0005}} for definition.";
              }
              leaf INTRAFREQHOSLOPEINCL {
                type boolean;
                description
                  "This field indicates whether the INTRAFREQHOSLOPE
                   field is valid and included in Access Point
                   Identification message.  Refer
                   {{bibref|3GPP2-C.S0005}} for definition.";
              }
              leaf INTRAFREQHOSLOPE {
                type uint32 {
                  range "0..63";
                }
                description
                  "Intra Frequency Handoff Slope.  Refer
                   {{bibref|3GPP2-C.S0005}} for definition.";
              }
              leaf INTERFREQHOHYSINCL {
                type boolean;
                description
                  "This field indicates whether the INTERFREQHOHYS
                   field is valid and included in Access Point
                   Identification message.  Refer
                   {{bibref|3GPP2-C.S0005}} for definition.";
              }
              leaf INTERFREQHOHYS {
                type uint32 {
                  range "0..127";
                }
                description
                  "Inter frequency handoff hysteresis.  Refer
                   {{bibref|3GPP2-C.S0005}} for definition.";
              }
              leaf INTERFREQHOSLOPEINCL {
                type boolean;
                description
                  "This field indicates whether the INTERFREQHOSLOPE
                   field is valid and included in Access Point
                   Identification message.  Refer
                   {{bibref|3GPP2-C.S0005}} for definition.";
              }
              leaf INTERFREQHOSLOPE {
                type uint32 {
                  range "0..63";
                }
                description
                  "Inter frequency handoff slope.  Refer
                   {{bibref|3GPP2-C.S0005}} for definition.";
              }
              leaf INTERFREQSRCHTHINCL {
                type boolean;
                description
                  "This field indicates whether the INTERFREQSRCHTH
                   field is valid and included in Access Point
                   Identification message.  Refer
                   {{bibref|3GPP2-C.S0005}} for definition.";
              }
              leaf INTERFREQSRCHTH {
                type uint32 {
                  range "0..31";
                }
                description
                  "Inter-frequency search threshold.  Refer
                   {{bibref|3GPP2-C.S0005}} for definitions";
              }
            }

            container APIDTM {
              description
                "This object can be configured only if
                 {{param|.Capabilities.CDMA2000.OneX.FemtoOverheadMessagesCapable}}
                 is set to {{true}}.";
              leaf APIDTEXTCHARiLEN {
                type uint32 {
                  range "0..256";
                }
                description
                  "Access Point identification Text CHARi field
                   Length ({{param|APIDTEXTCHARi}}).  Refer
                   {{bibref|3GPP2-C.S0005}} for definitions";
              }
              leaf APIDTEXTMSGENCODING {
                type uint32 {
                  range "0..31";
                }
                description
                  "Access Point identification Text message
                   encoding.  Refer {{bibref|3GPP2-C.S0005}} and
                   {{bibref|3GPP2-C.R1001}} for definitions";
              }
              leaf APIDTEXTCHARi {
                type string {
                  length "0..256";
                }
                description
                  "Access Point Identification Text.  Refer
                   {{bibref|3GPP2-C.S0005}} and
                   {{bibref|3GPP2-C.R1001}} for definitions.";
              }
            }

            container APPIM {
              description
                "This object can be configured only if
                 {{param|.Capabilities.CDMA2000.OneX.FemtoOverheadMessagesCapable}}
                 is set to {{true}}.";
              leaf LIFETIME {
                type uint32 {
                  range "0..255";
                }
                description
                  "Lifetime of the information in the access point
                   pilot information record.  Refer
                   {{bibref|3GPP2-C.S0005}} for definitions";
              }
              leaf NUMAPPIREC {
                type uint32 {
                  range "0..511";
                }
                description
                  "The number of entries for
                   {{object|.CellConfig.CDMA2000.OneX.RAN.APPIM.APPIREC.{i}.}}";
              }

              list APPIREC {
                key "APSID APNID APBAND APFREQ APPNRECTYPE APPNRECLEN APPNREC";
                description
                  "This object can be configured only if
                   {{param|.Capabilities.CDMA2000.OneX.FemtoOverheadMessagesCapable}}
                   is set to {{true}}.";
                leaf Enable {
                  type boolean;
                  default "false";
                  description
                    "Enables or disables the {{object}} entry.";
                }
                leaf APASSNTYPE {
                  type uint32 {
                    range "0..7";
                  }
                  default "0";
                  description
                    "Access point association type the access point
                     pilot information record.  Refer
                     {{bibref|3GPP2-C.S0005}} for definitions";
                }
                leaf APSIDSAMEASPREVIOUS {
                  type uint32 {
                    range "0..1";
                  }
                  default "0";
                  description
                    "SID same as previous indicator in the access
                     point pilot information record.  Refer
                     {{bibref|3GPP2-C.S0005}} for definitions";
                }
                leaf APNIDSAMEASPREVIOUS {
                  type uint32 {
                    range "0..1";
                  }
                  default "0";
                  description
                    "NID same as previous indicator in the access
                     point pilot information record.  Refer
                     {{bibref|3GPP2-C.S0005}} for definitions";
                }
                leaf APBANDSAMEASPREVIOUS {
                  type uint32 {
                    range "0..1";
                  }
                  default "0";
                  description
                    "Bandclass same as previous indicator in the
                     access point pilot information record.
                     Refer {{bibref|3GPP2-C.S0005}} for
                     definitions";
                }
                leaf APFREQSAMEASPREVIOUS {
                  type uint32 {
                    range "0..1";
                  }
                  default "0";
                  description
                    "Frequency same as previous indicator in the
                     access point pilot information record.
                     Refer {{bibref|3GPP2-C.S0005}} for
                     definitions";
                }
                leaf APPNRECSAMEASPREVIOUS {
                  type uint32 {
                    range "0..1";
                  }
                  default "0";
                  description
                    "PN offset same as previous indicator in the
                     access point pilot information record.
                     Refer {{bibref|3GPP2-C.S0005}} for
                     definitions";
                }
                leaf APSID {
                  type uint32 {
                    range "0..32767";
                  }
                  default "0";
                  description
                    "Access point SID in the access point pilot
                     information record.  Refer
                     {{bibref|3GPP2-C.S0005}} for definitions";
                }
                leaf APNID {
                  type uint32 {
                    range "0..65535";
                  }
                  default "0";
                  description
                    "Access point NID in the access point pilot
                     information record.  Refer
                     {{bibref|3GPP2-C.S0005}} for definitions";
                }
                leaf APBAND {
                  type uint32 {
                    range "0..31";
                  }
                  default "0";
                  description
                    "Access point bandclass in the access point
                     pilot information record.  Refer
                     {{bibref|3GPP2-C.S0005}} for definitions";
                }
                leaf APFREQ {
                  type uint32 {
                    range "0..2047";
                  }
                  default "0";
                  description
                    "Access point frequency in the access point
                     pilot information record.  Refer
                     {{bibref|3GPP2-C.S0005}} for definitions";
                }
                leaf APPNRECTYPE {
                  type uint32 {
                    range "0..7";
                  }
                  default "0";
                  description
                    "Access point PN offset in the access point
                     pilot information record.  Refer
                     {{bibref|3GPP2-C.S0005}} for definitions";
                }
                leaf APPNRECLEN {
                  type uint32 {
                    range "0..31";
                  }
                  default "0";
                  description
                    "Length in octets of the access point PN record
                     ({{param|APPNREC}}) in the access point
                     pilot information record.  Refer
                     {{bibref|3GPP2-C.S0005}} for definitions";
                }
                leaf APPNREC {
                  type yang:hex-string {
                    length "0..31";
                  }
                  default "";
                  description
                    "Access point PN Record in the access point
                     pilot information record.  Refer
                     {{bibref|3GPP2-C.S0005}} for definitions";
                }
              }
            }
          }

          container PCFConfig {
            description
              "CDMA2000 1x PCF configuration information.";
            leaf PCFPDSNHealthMonitorInterval {
              type uint32 {
                range "0..180";
              }
              description
                "PDSN health check monitor interval in {{units}}.
                 Setting the value to 0 disables the PDSN Health
                 Monitoring Feature.  Setting any non-zero value
                 enables the PDSN Health Monitoring Feature and
                 sets that non-zero value as the timer interval.";
            }

            container PCFPerformanceStats {
              config false;
              description
                "This object is used in obtaining the PCF stats";
              leaf A10SetupFailureNoReason {
                type uint32;
                description
                  "Number of times the PCF was refused an A10
                   connection with an unspecified reason (A11
                   error code : 0x80)";
              }
              leaf A10SetupFailureAdminProhibit {
                type uint32;
                description
                  "Number of times the PCF was refused an A10
                   connection with a reason \"Admin Prohibited\"
                   (A11 error code : 0x81).";
              }
              leaf A10SetupFailureInsuffResources {
                type uint32;
                description
                  "Number of times the PCF was refused an A10
                   connection with a reason \"Insufficient
                   Resources\" (A11 error code: 0x82).";
              }
              leaf A10SetupFailureFailedAuth {
                type uint32;
                description
                  "Number of times the PCF was refused an A10
                   connection with a reason \"Mobile Node
                   Authentication Failure\" (A11 error code:
                   0x83).";
              }
              leaf A10SetupFailureIdMismatch {
                type uint32;
                description
                  "Number of times the PCF was refused an A10
                   connection with a reason \"Id Mismatch\" (A11
                   error code: 0x85)";
              }
              leaf A10SetupFailureMalformedReq {
                type uint32;
                description
                  "Number of times the PCF was refused an A10
                   connection with a reason \"Malformed Request\"
                   (A11 error code: 0x86)";
              }
              leaf A10SetupFailureUnknownPDSN {
                type uint32;
                description
                  "Number of times the PCF was refused an A10
                   connection with a reason \"Unknown PDSN\" (A11
                   error code: 0x88)";
              }
              leaf A10SetupFailureUnsuppVendId {
                type uint32;
                description
                  "Number of times the PCF was refused an A10
                   connection with a reason \"Unsupported Vendor
                   Id\" (A11 error code: 0x89)";
              }
              leaf TotalA10ClosedByRnc {
                type uint32;
                description
                  "Number of A10 closed by the FAP RNC.";
              }
              leaf TotalA10ClosedByPDSN {
                type uint32;
                description
                  "Number of A10 closed by the PDSN.";
              }
              leaf TotalA10SuccessPages {
                type uint32;
                description
                  "Numebr of A10 Pages initiated by PCFsucceeded.";
              }
              leaf TotalA10FailedPages {
                type uint32;
                description
                  "Numebr of A10 Pages initiated by PCF failed.";
              }
              leaf TotalA10IngressBytes {
                type uint32;
                description
                  "Number of {{units}} received from the PDSN.";
              }
              leaf TotalA10EgressBytes {
                type uint32;
                description
                  "Number of {{units}} transmitted to the PDSN";
              }
              leaf A10RegUpdateReceived {
                type uint32;
                description
                  "Number of A10 Registration updates received by
                   the FAP PCF";
              }
              leaf TotalA10DroppedPages {
                type uint32;
                description
                  "Number of A10 Pages initiated by PCF dropped";
              }
            }
          }

          list BatchPCFPDSN {
            key "BatchTableNumber";
            description
              "The Batch configuration Object used to configure PDSN
               table using a start and end IP address.  The order
               of the address is used as part of PDSN selection
               algorithm, e.g., the first element is considered
               PDSN number 0.  (Refer to
               {{bibref|3GPP2-A.S0013}}).  To get individual PDSN
               entries use the
               {{object|.CellConfig.CDMA2000.OneX.PCFPDSN.{i}.}}.";
            leaf Enable {
              type boolean;
              default "false";
              description
                "Enables or disables the {{object}} entry.";
            }
            leaf BatchTableNumber {
              type int32 {
                range "0..127";
              }
              default "0";
              description
                "The BatchTable Number should be given only once
                 during the creation of a Batch Table.  This is
                 the Key Attribute that uniquely identifies a
                 BatchTable entry.  This number indicates the
                 index of this batch to determine the PDSN number
                 in the PDSN selection algorithm
                 ({{bibref|3GPP2-A.S0013}}).";
            }
            leaf BatchTableStartIPAddress {
              type types:IPAddress;
              default "";
              description
                "Start IP address of the range of PDSNs.";
            }
            leaf BatchTableEndIPAddress {
              type types:IPAddress;
              default "";
              description
                "End IP address of the range of PDSNs.";
            }
            leaf BatchTableSecurityParameterIndex {
              type uint32 {
                range "256..4294967295";
              }
              default "0";
              description
                "Security Parameter Index to be used.";
            }
            leaf BatchTableSecretKey {
              type yang:hex-string {
                length "0..16";
              }
              default "";
              description
                "Secret key in 32-digit hexidecimal representation.";
            }
            leaf BatchTableIOSVersion {
              type enumeration {
                enum "TIA-878-ballot";
                enum "TIA-878-1";
                enum "TIA-878-a";
                enum "TIA-878-legacy";
              }
              default "TIA-878-a";
              description
                "IOS Version of this PDSN.";
            }
            leaf BatchTablePDSNAdminStatus {
              type int32 {
                range "0..1";
              }
              default "0";
              description
                "Administrative status of this PDSN.  0- UP 1-DOWN.";
            }
            leaf PDSNType {
              type enumeration {
                enum "OneX";
                enum "HRPDRev0";
                enum "HRPDRevA";
              }
              default "HRPDRevA";
              description
                "Indicates the PDSN type for this batch.";
            }
          }

          list PCFPDSN {
            key "PDSNNumber SecurityParameterIndex SecurityKey";
            description
              "PCFPDSN Object configured for 1x.
               {{object|.CellConfig.CDMA2000.OneX.BatchPCFPDSN.{i}.}}
               table should be used to configure PDSN details.";
            leaf Enable {
              type boolean;
              default "false";
              description
                "Enables or disables the {{object}} entry.";
            }
            leaf PDSNNumber {
              type int32 {
                range "0..127";
              }
              default "0";
              description
                "Index of this PDSN object in the PCFPDSNCollection
                 array.  The index is used as PDSN number in PDSN
                 selection algorithm.  ({{bibref|3GPP2-A.S0013}})";
            }
            leaf SecurityParameterIndex {
              type uint32 {
                range "256..4294967295";
              }
              default "0";
              description
                "Security Parameter Index used";
            }
            leaf SecurityKey {
              type yang:hex-string {
                length "0..16";
              }
              default "";
              description
                "Secret key in 32-digit hexidecimal representation.";
            }
            leaf IOSVersion {
              type enumeration {
                enum "TIA-878-ballot";
                enum "TIA-878-1";
                enum "TIA-878-a";
                enum "TIA-878-legacy";
              }
              default "TIA-878-ballot";
              description
                "HRPD IOS Version of this PDSN.";
            }
            leaf PDSNadminStatus {
              type int32 {
                range "0..1";
              }
              default "0";
              description
                "Administrative status of this PDSN.  0- UP 1-DOWN.";
            }
            leaf PDSNHealthStatus {
              type uint32 {
                range "0..1";
              }
              default "0";
              description
                "Reachability status of this PDSN.  0-unreachable,
                 1-reachable.";
            }
            leaf PDSNIPAddress {
              type types:IPAddress;
              default "";
              description
                "IP address of the PDSN.";
            }

            container A11RegUpdateStats {
              config false;
              description
                "This object is used in obtaining the A11
                 Registration Update stats for each PDSN";
              leaf PDSNNumberRegUpdatePerf {
                type int32 {
                  range "0..127";
                }
                description
                  "The PDSN Number";
              }
              leaf PDSNIPAddressRegUpdatePerf {
                type types:IPAddress;
                description
                  "The IP Address of the PDSN for which the A11 Reg
                   Update stats is obtained";
              }
              leaf A11RegUpdateReceivedPDSN {
                type uint32;
                description
                  "Number of A10 Reg-update messages receieved from
                   a PDSN";
              }
              leaf A11RegUpdateIDCheckFailPDSN {
                type uint32;
                description
                  "Number of A10 Reg-Update messages receieved from
                   a PDSN that failed ID validation";
              }
              leaf A11RegUpdateAuthCheckFailPDSN {
                type uint32;
                description
                  "Number of A10 Reg-Update messages received from a
                   PDSN that failed Authentication";
              }
              leaf A11RegUpdateForUnknownPSIPDSN {
                type uint32;
                description
                  "Number of A10 Reg-Update messages received from a
                   PDSN with unknown PSI";
              }
              leaf A11RegUpdateUnspecifiedReasonPDSN {
                type uint32;
                description
                  "Number of A10 Reg-Update messages received from a
                   PDSN with unspecified reason code";
              }
              leaf A11RegUpdatePppTimeoutPDSN {
                type uint32;
                description
                  "Number of A10 Reg-Update messages received from a
                   PDSN with reason code \"PPP Timeout\"";
              }
              leaf A11RegUpdateRegistrationTimeoutPDSN {
                type uint32;
                description
                  "Number of A10 Reg-Update messages received from a
                   PDSN with reason code \"Registration Timeout\"";
              }
              leaf A11RegUpdatePDSNErrorPDSN {
                type uint32;
                description
                  "Number of A10 Reg-Update messages received from a
                   PDSN with reason code \"PDSN Error\"";
              }
              leaf A11RegUpdateInterPCFHandoffPDSN {
                type uint32;
                description
                  "Number of A10 Reg-Update messages received from a
                   PDSN with reason code \"Inter PCF Handoff\"";
              }
              leaf A11RegUpdateInterPDSNHandoffPDSN {
                type uint32;
                description
                  "Number of A10 Reg-Update messages received from a
                   PDSN with reason code \"Inter PDSN Handoff\"";
              }
              leaf A11RegUpdatePDSNOAMPInterventionPDSN {
                type uint32;
                description
                  "Number of A10 Reg-Update messages received from a
                   PDSN with reason code \"PDSN OAMP
                   Intervention\"";
              }
              leaf A11RegUpdateAccountingErrorPDSN {
                type uint32;
                description
                  "Number of A10 Reg-Update messages received from a
                   PDSN with reason code \"Accounting Error\"";
              }
              leaf A11RegUpdateUserFailedAuthenticationPDSN {
                type uint32;
                description
                  "Number of A10 Reg-Update messages received from a
                   PDSN with reason code \"User Failed
                   Authentication\"";
              }
              leaf A11RegUpdateUnknownCauseCodePDSN {
                type uint32;
                description
                  "Number of A10 Reg-Update messages received from a
                   PDSN with Unknown Cause Code";
              }
              leaf A11RegUpdateWithoutReasonCodePDSN {
                type uint32;
                description
                  "Number of A10 Reg-Update messages received from a
                   PDSN with PDSN Code Not Included";
              }
            }

            container PCFPDSNStats {
              config false;
              description
                "This object is used in obtaining the PCF PDSN stats
                 for each PDSN";
              leaf A10SetupAttemptsPDSN {
                type uint32;
                description
                  "Number of attempts the PCF made to establish an
                   A10 connection with PDSN.  If PCF fails
                   establishing such a connection on this PDSN
                   and goes on to use another PDSN for that
                   connection, it will be counted as two setup
                   attempts.";
              }
              leaf A10SetupSuccessesPDSN {
                type uint32;
                description
                  "Number of times PCF succeeded in establishing an
                   A10 connection with this PDSN.";
              }
              leaf A10SetupBlocksPDSN {
                type uint32;
                description
                  "Number of times PCF was blocked in establishing
                   an A10 connection with this PDSN.";
              }
              leaf A11RegReqDeniedIdMismatchPDSN {
                type uint32;
                description
                  "Number ofA11 Registration Request denied with a
                   reason \"Id Mismatch\" (A11 error code: 0x85)
                   by the PDSN";
              }
              leaf A11RegReqDeniedUnknownPDSNPDSN {
                type uint32;
                description
                  "Number of A11 Registration Request denied with a
                   reason \"Unknown PDSN\" (A11 error code:
                   0x88)by the PDSN.";
              }
              leaf A11RegReqDeniedNoReasonPDSN {
                type uint32;
                description
                  "Number of A11 Registration Request denied with no
                   reason code by the PDSN.";
              }
              leaf A11RegReqDeniedAdminProhibitPDSN {
                type uint32;
                description
                  "Number of A11 Registration Request denied with a
                   reason \"Admin Prohibited\" (A11 error code :
                   0x81) by the PDSN.";
              }
              leaf A11RegReqDeniedInsuffResourcesPDSN {
                type uint32;
                description
                  "Number of A11 Registration Request denied with a
                   reason \"Insufficient Resources\" (A11 error
                   code: 0x82) by the PDSN.";
              }
              leaf A11RegReqDeniedFailedAuthPDSN {
                type uint32;
                description
                  "Number of A11 Registration Request denied with a
                   reason \"Mobile Node Authentication Failure\"
                   (A11 error code: 0x83) by the PDSN.";
              }
              leaf A11RegReqDeniedMalformedReqPDSN {
                type uint32;
                description
                  "Number of A11 Registration Request denied with a
                   reason \"Malformed Request\" (A11 error code:
                   0x86) by the PDSN";
              }
              leaf A11RegReqDeniedUnsuppVendIdPDSN {
                type uint32;
                description
                  "Number ofA11 Registration Request denied with a
                   reason \"Unsupported Vendor Id\" (A11 error
                   code: 0x8D)by the PDSN";
              }
              leaf A11RegReqDeniedReverseTunnelUnavailablePDSN {
                type uint32;
                description
                  "Number ofA11 Registration Request denied with a
                   reason \"Reverse Tunnel Unavailable\" (A11
                   error code: 0x89)by the PDSN";
              }
              leaf A11RegReqDeniedReverseTunnelTbitNotSetPDSN {
                type uint32;
                description
                  "Number ofA11 Registration Request denied with a
                   reason \"Reverse Tunnel Tbit Not Set\" (A11
                   error code: 0x8A)by the PDSN";
              }
              leaf A11RegReqDeniedUnknownErrorCodePDSN {
                type uint32;
                description
                  "Number of A11 Registration Request denied with an
                   unspecified reason (A11 error code : 0x80) by
                   the PDSN";
              }
              leaf A10RegReqForRegistrationRetransmissionsPDSN {
                type uint32;
                description
                  "Number of A11 Registration Requests retransmitted
                   during A10 setup";
              }
              leaf A10RegReqForReRegistrationRetransmissionsPDSN {
                type uint32;
                description
                  "Number of A11 Registration Requests retransmitted
                   during A10 reregistration";
              }
              leaf A10RegReqForReleaseRetransmissionsPDSN {
                type uint32;
                description
                  "Number of A11 Registration Requests retransmitted
                   during A10 realease";
              }
              leaf PDSNNumberPDSNPerf {
                type int32 {
                  range "0..127";
                }
                description
                  "The PDSN Number";
              }
              leaf PDSNipAddressPDSNPerf {
                type types:IPAddress;
                description
                  "The IP Address of the PDSN for which the PCF PDSN
                   stats is obtained";
              }
            }
          }

          container Stats {
            config false;
            description
              "This object contains 1x FAP statistics aggregated
               over all connections of all users over all
               sectors.";
            leaf RegistrationAttempts {
              type uint32 {
                range "0..4294967295";
              }
              description
                "Total number of registration attempts";
            }
            leaf RegistrationFails {
              type uint32 {
                range "0..4294967295";
              }
              description
                "Total number of registrations failed";
            }
            leaf RegistrationsBlocked {
              type uint32 {
                range "0..4294967295";
              }
              description
                "Unauthorized registrations blocked by admission
                 control";
            }
            leaf PageAttempts {
              type uint32 {
                range "0..4294967295";
              }
              description
                "Total number of attemots to page requests received
                 from the core";
            }
            leaf PageFails {
              type uint32 {
                range "0..4294967295";
              }
              description
                "Total number of page requests rejected or not
                 responded";
            }
            leaf VoiceCallAttempts {
              type uint32 {
                range "0..4294967295";
              }
              description
                "Total number of voice call attempts";
            }
            leaf VoiceCallFailures {
              type uint32 {
                range "0..4294967295";
              }
              description
                "Total number of voice call attempts which failed
                 for various reasons";
            }
            leaf VoiceCallsBlocked {
              type uint32 {
                range "0..4294967295";
              }
              description
                "Total number of voice calls blocked due to lack of
                 authorization";
            }
            leaf VoiceCallsDropped {
              type uint32 {
                range "0..4294967295";
              }
              description
                "Number of voice calls dropped due to various
                 reasons other than a normal call release";
            }
            leaf DataCallAttempts {
              type uint32 {
                range "0..4294967295";
              }
              description
                "Total number of data call attempts";
            }
            leaf DataCallFailures {
              type uint32 {
                range "0..4294967295";
              }
              description
                "Total number of data call attemots failed for
                 various reasons";
            }
            leaf DataCallsBlocked {
              type uint32 {
                range "0..4294967295";
              }
              description
                "Total number of data calls failed due to lack of
                 authorization";
            }
            leaf DataCallsDropped {
              type uint32 {
                range "0..4294967295";
              }
              description
                "Total number of data calls dropped due to reasons
                 other than a normal release.";
            }
            leaf AverageVoiceCall {
              type uint32 {
                range "0..4294967295";
              }
              description
                "Average voice call duration in {{units}}.";
            }
            leaf AverageDataCall {
              type uint32 {
                range "0..4294967295";
              }
              description
                "Average data call duration in {{units}}";
            }
            leaf AverageSessionInSec {
              type uint32 {
                range "0..4294967295";
              }
              description
                "Average session duration in {{units}}.";
            }
            leaf TotalVoiceCalls {
              type uint32 {
                range "0..4294967295";
              }
              description
                "Total number of successful voice calls";
            }
            leaf TotalDataCalls {
              type uint32 {
                range "0..4294967295";
              }
              description
                "Total number of successful data calls";
            }
            leaf FwdVoicePacketDropPercentage {
              type uint32 {
                range "0..4294967295";
              }
              description
                "Percentage of voice packets dropped in MAC due to
                 signaling";
            }
            leaf RevVoicePacketDropPercentage {
              type uint32 {
                range "0..4294967295";
              }
              description
                "Percentage of voice packets received with bad FQI";
            }
            leaf FwdAvgDataRate {
              type uint32 {
                range "0..4294967295";
              }
              description
                "Average data rate of the scheduler on the forward
                 link";
            }
            leaf RevAvgDataRate {
              type uint32 {
                range "0..4294967295";
              }
              description
                "Average data rate of the scheduler on reverse link";
            }
            leaf BcIndexZeroToOneTransitions {
              type uint32 {
                range "0..4294967295";
              }
              description
                "Num of times the bcIndex was changed from 0 to 1 in
                 the Extended System Parameters Message.";
            }
            leaf BcIndexOneToZeroTransitions {
              type uint32 {
                range "0..4294967295";
              }
              description
                "Num of times the bcIndex was changed from 0 to 1 in
                 the Extended System Parameters Message.";
            }
          }

          container Redirect {
            description
              "CDMA2000 1x service redirection parameters.";
            leaf RedirectChannelNumber {
              type uint32 {
                range "0..2047";
              }
              description
                "The channel number set from ACS that the FAP uses
                 to redirect the MS in case of closed access or
                 when exceeding session capacity.  The ACS shall
                 push this if the the operator has provided this
                 information in a configuration file.  If this is
                 not configured, the FAP rejects the AT.  The
                 supported range is 0..2047.";
            }
            leaf RedirectBandClass {
              type uint32 {
                range "0..31";
              }
              description
                "The bandclass set from ACS that the FAP uses to
                 redirect the MS incase of closed access or when
                 exceeding session capacity.  The ACS shall push
                 this if the the operator has provided this
                 information in a configuration file.  If this is
                 not configured, the FAP rejects the MS.  The
                 supported range is 0..9.";
            }
          }
        }

        container HRPD {
          description
            "The object contains attributes related to HRPD.";
          leaf MaxBatchPCFPDSNEntries {
            type uint32;
            config false;
            description
              "Maximum number of entries in the
               {{object|.CellConfig.CDMA2000.HRPD.BatchPCFPDSN.{i}.}}
               table.";
          }

          container RAN {
            description
              "The object contains attributes related to HRPD RAN.";

            container RF {
              description
                "Contains the details related to HRPD RF";
              leaf HRPDCarBandClass {
                type uint32 {
                  range "0..31";
                }
                description
                  "The Band Class this HRPD Carrier object is to
                   operate on.  Reference -
                   {{bibref|3GPP2-C.S0057}}, Band Class
                   Specification for CDMA2000 Spread Spectrum
                   Systems.";
              }
              leaf RFCNFL {
                type string {
                  length "0..64";
                }
                description
                  "{{list}} Each item is a FL Radio Frequency
                   Channel Number (RFCN).  Self-configuration for
                   RFCNFL is controlled by
                   {{param|.Capabilities.CDMA2000.HRPD.SelfConfig.RFCNFLConfig}}
                   from an availability perspective and
                   {{param|.FAPControl.CDMA2000.HRPD.SelfConfig.RFCNFLSelfConfigEnable}}
                   from an enabled perspective.  If the FAP's
                   self-configuration capability for RFCNFL is
                   available and enabled, this parameter MAY
                   contain more than one item and the FAP is
                   expected to select one from the list for
                   {{param|RFCNFLInUse}}.  If the
                   self-configuration capability is not available
                   or not enabled, then this parameter SHOULD
                   contain only a single item.  If multiple items
                   are specified, they are done in the order of
                   preference.";
              }
              leaf RFCNFLInUse {
                type uint32;
                config false;
                description
                  "The FL RFCN being used by the FAP.
                   Self-configuration for RFCNFL is controlled by
                
                   {{param|.Capabilities.CDMA2000.HRPD.SelfConfig.RFCNFLConfig}}
                   from an availability perspective and
                
                   {{param|.FAPControl.CDMA2000.HRPD.SelfConfig.RFCNFLSelfConfigEnable}}
                   from an enabled perspective.  If the
                   self-configuration capability is available and
                   enabled, this parameter indicates the value
                   selected by the FAP among the choices provided
                   in {{param|RFCNFL}}.  If the
                   self-configuration capability is not available
                   or not enabled, then this parameter contains
                   the first value in {{param|RFCNFL}}.";
              }
              leaf PilotPN {
                type string {
                  length "0..64";
                }
                description
                  "{{list}} (maximum length 32) (minimum 1 items) of
                   strings.  Each item is a pilot PN offset in
                   units of 64 PN chips.  Self-configuration for
                   pilot PN is controlled by
                   {{param|.Capabilities.CDMA2000.HRPD.SelfConfig.PilotPNConfig}}
                   from an availability perspective and
                   {{param|.FAPControl.CDMA2000.HRPD.SelfConfig.PilotPNSelfConfigEnable}}
                   from an enabled perspective.
                
                   If the FAP's self-configuration capability for
                   Pilot PN Offset is available and enabled, this
                   parameter MAY contain more than one item and
                   the FAP is expected to select one from the
                   list for {{param|PilotPNInUse}}.  If the
                   self-configuration capability is not available
                   or not enabled, then this parameter SHOULD
                   contain only a single item.
                
                   The multiplicity of the PN offsets values can
                   also be expressed by defining a range using
                   \"..\" (two periods) between two values.  In
                   this case, the combination of two values
                   defines the lower-bound and upper-bound of the
                   range inclusive.
                
                   The order of the items has no significance.";
              }
              leaf PilotPNInUse {
                type uint32;
                description
                  "The Pilot PN Offset being used by the FAP.
                   Self-configuration for Pilot PN Offset is
                   controlled by
                   {{param|.Capabilities.CDMA2000.HRPD.SelfConfig.PilotPNConfig}}
                   from an availability perspective and
                   {{param|.FAPControl.CDMA2000.HRPD.SelfConfig.PilotPNSelfConfigEnable}}
                   from an enabled perspective.  If the
                   self-configuration capability is available and
                   enabled, this parameter indicates the value
                   selected by the FAP among the choices provided
                   in {{param|PilotPN}}.
                
                   If the self-configuration capability is not
                   available or not enabled, then this parameter
                   contains the first value in {{param|PilotPN}}.";
              }
              leaf MaxFAPTxPower {
                type string {
                  length "0..64";
                }
                description
                  "Defines the maximum transmission power allowed on
                   the FAP.  {{param}} is expressed as a range of
                   allowed maximum power levels with \"..\" (two
                   periods) between the upper and lower values,
                   i.e.  \"<;Pmax_low>..<;Pmax_high>\".
                
                   {{param}} identifies the limits between which
                   the FAP can self-configure its maximum
                   transmit power.
                
                   Self-configuration for maximum transmission
                   power is controlled by
                   {{param|.Capabilities.CDMA2000.HRPD.SelfConfig.MaxFAPTxPowerConfig}}
                   from an availability perspective and
                   {{param|.FAPControl.CDMA2000.HRPD.SelfConfig.MaxFAPTxPowerSelfConfigEnable}}
                   from an enabled perspective.  <;Pmax_low> and
                   <;Pmax_high> are measured in dBm and have a
                   range of -40.0 to 20.0 incremented by 0.1 dB.";
              }
              leaf MaxFAPTxPowerInUse {
                type int32 {
                  range "-200..200";
                }
                description
                  "The maximum transmission power measured in
                   {{units}} currently used by the FAP.
                
                   Actual values of the maximum transmission
                   power are -40.0 dBm to 20.0 dBm in steps of
                   {{units}}.  The value of {{param}} divided by
                   10 yields the actual value of the maximum
                   transmission power.
                
                   Self-configuration for maximum transmission
                   power is controlled by
                   {{param|.Capabilities.CDMA2000.HRPD.SelfConfig.MaxFAPTxPowerConfig}}
                   from an availability perspective and
                   {{param|.FAPControl.CDMA2000.HRPD.SelfConfig.MaxFAPTxPowerSelfConfigEnable}}
                   from an enabled perspective.  If the
                   self-configuration capability is available and
                   enabled, this parameter indicates the value
                   selected by the FAP among the range provided
                   in {{param|MaxFAPTxPower}}.  If the
                   self-configuration capability is not available
                   or not enabled, then this parameter contains a
                   value selected by the ACS.";
              }
              leaf ControlChannelRate {
                type int32;
                description
                  "The data rate of the Control Channel of this HRPD
                   SectorElement object.  Reference -
                   {{bibref|3GPP2-C.S0024-B}}, CDMA2000 High Rate
                   Packet Data Air Interface Specification,
                   section-10.4.1.3.2.4";
              }
              leaf SyncCapsuleOffset {
                type int32 {
                  range "0..3";
                }
                description
                  "The offset from the control channel cycle
                   boundary at which the synchronous capsules are
                   to be transmitted for this HRPD SectorElement
                   object.  Reference
                   -{{bibref|3GPP2-C.S0024-B}}, CDMA2000 High
                   Rate Packet Data Air Interface Specification,
                   section-9.2.6.1.4.1.2";
              }
              leaf RabLength {
                type int32 {
                  range "8 | 16 | 32 | 64";
                }
                description
                  "The Reverse Activity Bit (RAB) length measured in
                   slots for this HRPD SectorElement object.
                   Reference -{{bibref|3GPP2-C.S0024-B}},
                   CDMA2000 High Rate Packet Data Air Interface
                   Specification, section-7.8.6.2.2, Table
                   9.7.6.2-2.";
              }
              leaf RabOffset {
                type int32 {
                  range "0..7";
                }
                description
                  "The Reverse Activity Bit (RAB) offset for this
                   HRPD SectorElement object.  Reference -
                   {{bibref|3GPP2-C.S0024-B}}, CDMA2000 High Rate
                   Packet Data Air Interface Specification,
                   section-7.8.6.2.2.";
              }
              leaf SectorID {
                type yang:hex-string {
                  length "16";
                }
                description
                  "The 128 bit Sector ID for this HRPD SectorElement
                   object.  The Sector ID is used in the
                   computation of the long code mask.  See
                   {{bibref|3GPP2-C.S0024-B}}, CDMA2000 High Rate
                   Packet Data Air Interface Specification.";
              }
              leaf ColorCode {
                type int32 {
                  range "0..255";
                }
                description
                  "The HRPD color code associated with this
                   sector-element.  Reference
                   -{{bibref|3GPP2-C.S0024-B}}, CDMA2000 High
                   Rate Packet Data Air Interface Specification";
              }
              leaf SubnetMaskLength {
                type int32 {
                  range "0..104";
                }
                description
                  "{{param}} is the length of the HRPD SubnetMask in
                   {{units}}.  See {{bibref|3GPP2-C.S0024-B}},
                   CDMA2000 High Rate Packet Data Air Interface
                   Specification";
              }
              leaf HRPDSecElReverseLinkSilenceDuration {
                type int32 {
                  range "0..3";
                }
                description
                  "Duration of the Reverse Link Silence Interval in
                   units of {{units}}.  The duration of the
                   silence interval to be maintained on the
                   reverse link.  Reference
                   -{{bibref|3GPP2-C.S0024-B}}, CDMA2000 High
                   Rate Packet Data Air Interface Specification.
                   Section-9.4.6.1.4.1.1.";
              }
              leaf HRPDSecElReverseLinkSilencePeriod {
                type int32 {
                  range "0..3";
                }
                description
                  "The Reverse Link Silence Interval is defined as
                   the time interval of duration
                   ReverseLinkSilenceDuration frames that starts
                   at times T where T is the CDMA System Time in
                   units of {{units}} and it satisfies the
                   following equation:
                
                   T mod (2048 x 2^(ReverseLinkSilencePeriod) -
                   1) = 0.
                
                   The period in the access cycle duration for
                   which the silence interval shall be maintained
                   on the reverse link.
                   {{bibref|3GPP2-C.S0024-B}}, CDMA2000 High Rate
                   Packet Data Air Interface Specification.
                   Section-9.4.6.1.4.1.1.";
              }
              leaf OpenLoopAdjust {
                type int32 {
                  range "0..255";
                }
                description
                  "The open loop adjustment (in {{units}}) for the
                   access parameters of this sector-element.  FAP
                   sets this field to the negative of the nominal
                   power to be used by ATs in the open loop power
                   estimate, expressed as an unsigned value in
                   units of 1 dB.  The value used by the AT is -1
                   times the value of this field.  Reference
                   -{{bibref|3GPP2-C.S0024-B}}, CDMA2000 High
                   Rate Packet Data Air Interface Specification.
                   Section-9.4.6.2.6";
              }
              leaf ProbeInitialAdjust {
                type int32 {
                  range "-15..15";
                }
                description
                  "The probe initial adjustment (in {{units}}) for
                   the access parameters of this sector-element.
                   FAP sets this field to the correction factor
                   to be used by ATs in the open loop power
                   estimate for the initial transmission on the
                   Access Channel, expressed as a two's
                   complement value in units of 1 dB.  Reference
                   -{{bibref|3GPP2-C.S0024-B}}, CDMA2000 High
                   Rate Packet Data Air Interface Specification.
                   Section-9.4.6.2.6";
              }
              leaf ProbeNumSteps {
                type int32 {
                  range "1..15";
                }
                description
                  "The number of power level steps for access probes
                   for the access parameters of this
                   sector-element.  FAP sets this field to the
                   maximum number of access probes ATs are to
                   transmit in a single access probe sequence.
                   The access network shall set this field to a
                   value in the range [1 ...  15].  Reference
                   -{{bibref|3GPP2-C.S0024-B}}, CDMA2000 High
                   Rate Packet Data Air Interface Specification.
                   Section-9.4.6.2.6";
              }
              leaf ProbePowerStep {
                type int32 {
                  range "0..15";
                }
                description
                  "The power step size (in {{units}}) applied to
                   successive probes on the access channel
                   associated with this sector-element.  Probe
                   power increase step.  FAPsets this field to
                   the increase in power between probes, in
                   resolution of 0.5 dB.  Reference
                   -{{bibref|3GPP2-C.S0024-B}}, CDMA2000 High
                   Rate Packet Data Air Interface Specification.
                   Section-9.4.6.2.6";
              }
              leaf APersistence {
                type string {
                  length "0..16";
                }
                description
                  "The A-Persistence vector, as per HRPD
                   specification, for controlling contention
                   access on the access channel associated with
                   this sector-element.  Reference -
                   {{bibref|3GPP2-C.S0024-B}}, CDMA2000 High Rate
                   Packet Data Air Interface Specification.
                   Section-9.4.6.2.6.  Format is \"0xAABBCCDD\",
                   where AA, BB, CC, DD are in the range \"01\"
                   through \"3F\" hex.";
              }
              leaf RSSIRABThreshold {
                type int32 {
                  range "-1600..1600";
                }
                description
                  "RAB threshold for RSSI based RAB algorithm.";
              }
              leaf LoadRABThreshold {
                type uint32 {
                  range "0..480";
                }
                description
                  "RAB threshold for Load based RAB algorithm in
                   units of {{units}}.";
              }
              leaf ConnectionRateLimit {
                type uint32 {
                  range "0..3";
                }
                description
                  "4 different configurations.";
              }
              leaf RfeRLBalanceRatio {
                type uint32 {
                  range "1..20";
                }
                description
                  "Config Parameter for DRC based rate control";
              }
            }
          }

          container PCFConfig {
            description
              "CDMA2000 HRPD PCF configuration parameters.";
            leaf PCFPDSNHealthMonitorInterval {
              type uint32 {
                range "0..180";
              }
              description
                "PDSN health check monitor interval in {{units}}.
                 Setting the value to 0 disables the PDSN Health
                 Monitoring Feature.  Setting any non-zero value
                 enables the PDSN Health Monitoring Feature and
                 sets that non-zero value as the timer interval.";
            }

            container PCFPerformanceStats {
              config false;
              description
                "This object is used in obtaining the PCF stats";
              leaf A10SetupFailureNoReason {
                type uint32;
                description
                  "Number of times the PCF was refused an A10
                   connection with an unspecified reason (A11
                   error code : 0x80)";
              }
              leaf A10SetupFailureAdminProhibit {
                type uint32;
                description
                  "Number of times the PCF was refused an A10
                   connection with a reason \"Admin Prohibited\"
                   (A11 error code : 0x81).";
              }
              leaf A10SetupFailureInsuffResources {
                type uint32;
                description
                  "Number of times the PCF was refused an A10
                   connection with a reason \"Insufficient
                   Resources\" (A11 error code: 0x82).";
              }
              leaf A10SetupFailureFailedAuth {
                type uint32;
                description
                  "Number of times the PCF was refused an A10
                   connection with a reason \"Mobile Node
                   Authentication Failure\" (A11 error code:
                   0x83).";
              }
              leaf A10SetupFailureIdMismatch {
                type uint32;
                description
                  "Number of times the PCF was refused an A10
                   connection with a reason \"Id Mismatch\" (A11
                   error code: 0x85)";
              }
              leaf A10SetupFailureMalformedReq {
                type uint32;
                description
                  "Number of times the PCF was refused an A10
                   connection with a reason \"Malformed Request\"
                   (A11 error code: 0x86)";
              }
              leaf A10SetupFailureUnknownPDSN {
                type uint32;
                description
                  "Number of times the PCF was refused an A10
                   connection with a reason \"Unknown PDSN\" (A11
                   error code: 0x88)";
              }
              leaf A10SetupFailureUnsuppVendId {
                type uint32;
                description
                  "Number of times the PCF was refused an A10
                   connection with a reason \"Unsupported Vendor
                   Id\" (A11 error code: 0x89)";
              }
              leaf TotalA10ClosedByRnc {
                type uint32;
                description
                  "Number of A10 closed by the FAP RNC";
              }
              leaf TotalA10ClosedByPDSN {
                type uint32;
                description
                  "Number of A10 closed by the PDSN";
              }
              leaf TotalA10SuccessPages {
                type uint32;
                description
                  "Numebr of A10 Pages initiated by PCFsucceeded";
              }
              leaf TotalA10FailedPages {
                type uint32;
                description
                  "Numebr of A10 Pages initiated by PCF failed";
              }
              leaf TotalA10IngressBytes {
                type uint32;
                description
                  "Number of {{units}} received from the PDSN";
              }
              leaf TotalA10EgressBytes {
                type uint32;
                description
                  "Number of {{units}} transmitted to the PDSN";
              }
              leaf A10RegUpdateReceived {
                type uint32;
                description
                  "Number of A10 Registration updates received by
                   the FAP PCF";
              }
              leaf TotalA10DroppedPages {
                type uint32;
                description
                  "Number of A10 Pages initiated by PCF dropped";
              }
            }
          }

          list BatchPCFPDSN {
            key "BatchTableNumber BatchTableSecurityParameterIndex BatchTableSecretKey";
            description
              "The Batch configuration Object used to configure PDSN
               table using a start and end IP address.  The order
               of the address is used as part of PDSN selection
               algorithm, e.g., the first element is considered
               PDSN number 0 (refer to {{bibref|3GPP2-A.S0008}}
               and {{bibref|3GPP2-A.S0009}}).  To get individual
               PDSN entries use the
               {{object|.CellConfig.CDMA2000.HRPD.PCFPDSN.{i}.}}.";
            leaf Enable {
              type boolean;
              default "false";
              description
                "Enables or disables the {{object}} entry.";
            }
            leaf BatchTableNumber {
              type int32 {
                range "0..127";
              }
              default "0";
              description
                "The BatchTable Number should be given only once
                 during the creation of a Batch Table.  This is
                 the Key Attribute that uniquely identifies a
                 BatchTable entry";
            }
            leaf BatchTableStartIPAddress {
              type types:IPAddress;
              default "";
              description
                "Start IP address of the range of PDSNs";
            }
            leaf BatchTableEndIPAddress {
              type types:IPAddress;
              default "";
              description
                "End IP address of the range of PDSNs";
            }
            leaf BatchTableSecurityParameterIndex {
              type uint32 {
                range "256..4294967295";
              }
              default "0";
              description
                "Security Parameter Index to be used";
            }
            leaf BatchTableSecretKey {
              type yang:hex-string {
                length "0..16";
              }
              default "";
              description
                "Secret key in 32-digit hexidecimal representation.";
            }
            leaf BatchTableIOSVersion {
              type enumeration {
                enum "TIA-878-ballot";
                enum "TIA-878-1";
                enum "TIA-878-a";
                enum "TIA-878-legacy";
              }
              default "TIA-878-a";
              description
                "HRPD IOS Version of this PDSN";
            }
            leaf BatchTablePDSNAdminStatus {
              type int32 {
                range "0..1";
              }
              default "0";
              description
                "Administrative status of this PDSN.  0- UP 1-DOWN.";
            }
            leaf PDSNType {
              type string {
                length "0..32";
              }
              default "HRPD RevA";
              description
                "Indicates the PDSN type for this batch.";
            }
          }

          list PCFPDSN {
            key "PDSNNumber SecurityParameterIndex SecurityKey";
            description
              "PCFPDSN Object configured for HRPD.
               {{object|.CellConfig.CDMA2000.HRPD.BatchPCFPDSN.{i}.}}
               table should be used to configure PDSN details.";
            leaf Enable {
              type boolean;
              default "false";
              description
                "Enables or disables the {{object}} entry.";
            }
            leaf PDSNNumber {
              type int32 {
                range "0..127";
              }
              default "0";
              description
                "Index of this PDSN object in the PCFPDSNCollection
                 array.  The index is used as PDSN number in PDSN
                 selection algorithm (refer to
                 {{bibref|3GPP2-A.S0008}} and
                 {{bibref|3GPP2-A.S0009}})";
            }
            leaf SecurityParameterIndex {
              type uint32 {
                range "256..4294967295";
              }
              default "256";
              description
                "Security Parameter Index used";
            }
            leaf SecurityKey {
              type yang:hex-string {
                length "0..16";
              }
              default "";
              description
                "Secret key in 32-digit hexidecimal representation.";
            }
            leaf IOSVersion {
              type enumeration {
                enum "TIA-878-ballot";
                enum "TIA-878-1";
                enum "TIA-878-a";
                enum "TIA-878-legacy";
              }
              default "TIA-878-a";
              description
                "HRPD IOS Version of this PDSN";
            }
            leaf PDSNadminStatus {
              type int32 {
                range "0..1";
              }
              default "0";
              description
                "Administrative status of this PDSN.  0- UP 1-DOWN.";
            }
            leaf PDSNHealthStatus {
              type uint32 {
                range "0..1";
              }
              default "0";
              description
                "Reachability status of this PDSN.  0-unreachable,
                 1-reachable.";
            }
            leaf PDSNIPAddress {
              type types:IPAddress;
              default "";
              description
                "IP address of the PDSN.";
            }

            container A11SessionUpdateStats {
              config false;
              description
                "This object is used in obtaining the A11 Session
                 Update stats for each PDSN";
              leaf PDSNNumberSessionUpdatePerf {
                type int32 {
                  range "0..127";
                }
                description
                  "The PDSN Number";
              }
              leaf PDSNIPAddressSessionUpdatePerf {
                type types:IPAddress;
                description
                  "The IP Address of the PDSN for which the A11
                   Session Update stats is obtained";
              }
              leaf A11SessionUpdateReceivedPDSN {
                type uint32;
                description
                  "Number of A11 Session Updates received from a
                   PDSN";
              }
              leaf A11SessionUpdateAcceptedPDSN {
                type uint32;
                description
                  "Number of A11 Session Updates accepted for a PDSN";
              }
              leaf A11SessionUpdateExtendedAPIPDSN {
                type uint32;
                description
                  "Number of A11 Session Updates received from this
                   PDSN that contained extended API";
              }
              leaf A11SessionUpdateForUnknownPSIPDSN {
                type uint32;
                description
                  "Number of A11 Session Updates received from this
                   PDSN that conatained unknown PSI";
              }
              leaf A11SessionUpdateDeniedIDCheckFailPDSN {
                type uint32;
                description
                  "Number of A11 Session Updates received from this
                   PDSN denied due to reason code \"ID Check
                   Failed \"";
              }
              leaf A11SessionUpdateDeniedAuthCheckFailPDSN {
                type uint32;
                description
                  "Number of A11 Session Updates received from this
                   PDSN denied due to reason code\"Auth Check
                   Failed\"";
              }
              leaf A11SessionUpdateDeniedReasonUnspecifiedPDSN {
                type uint32;
                description
                  "Number of A11 Session Updates received from this
                   PDSN denied due to reason code \"Unspecified
                   Reason\"";
              }
              leaf A11SessionUpdateDeniedPoorlyFormedPDSN {
                type uint32;
                description
                  "Number of A11 Session Updates received from this
                   PDSN denied due to reason code \"Poorly
                   Formed\"";
              }
              leaf A11SessionUpdateDeniedSessionParamsNotUpdatedPDSN {
                type uint32;
                description
                  "Number of A11 Session Updates received from this
                   PDSN denied due to reason code \"Parameters
                   Not Updated\"";
              }
              leaf A11SessionUpdateDeniedQoSProfileIdNotSupportedPDSN {
                type uint32;
                description
                  "Number of A11 Session Updates received from this
                   PDSN denied due to reason code \"QoS Profile
                   Id Not Updated\"";
              }
              leaf A11SessionUpdateDeniedInsufficientResourcesPDSN {
                type uint32;
                description
                  "Number of A11 Session Updates received from this
                   PDSN denied due to reason code \"Insufficient
                   Resources\"";
              }
              leaf A11SessionUpdateDeniedHandoffInProgressPDSN {
                type uint32;
                description
                  "Number of A11 Session Updates received from this
                   PDSN denied due to reason code\"Handoff In
                   Progress\"";
              }
            }

            container A11RegUpdateStats {
              config false;
              description
                "This object is used in obtaining the A11
                 Registration Update stats for each PDSN.";
              leaf PDSNNumberRegUpdatePerf {
                type int32 {
                  range "0..127";
                }
                description
                  "The PDSN Number";
              }
              leaf PDSNIPAddressRegUpdatePerf {
                type types:IPAddress;
                description
                  "The IP Address of the PDSN for which the A11 Reg
                   Update stats is obtained";
              }
              leaf A11RegUpdateReceivedPDSN {
                type uint32;
                description
                  "Number of A10 Reg-update messages receieved from
                   a PDSN";
              }
              leaf A11RegUpdateIDCheckFailPDSN {
                type uint32;
                description
                  "Number of A10 Reg-Update messages receieved from
                   a PDSN that failed ID validation";
              }
              leaf A11RegUpdateAuthCheckFailPDSN {
                type uint32;
                description
                  "Number of A10 Reg-Update messages received from a
                   PDSN that failed Authentication";
              }
              leaf A11RegUpdateForUnknownPSIPDSN {
                type uint32;
                description
                  "Number of A10 Reg-Update messages received from a
                   PDSN with unknown PSI";
              }
              leaf A11RegUpdateUnspecifiedReasonPDSN {
                type uint32;
                description
                  "Number of A10 Reg-Update messages received from a
                   PDSN with unspecified reason code";
              }
              leaf A11RegUpdatePppTimeoutPDSN {
                type uint32;
                description
                  "Number of A10 Reg-Update messages received from a
                   PDSN with reason code \"PPP Timeout\"";
              }
              leaf A11RegUpdateRegistrationTimeoutPDSN {
                type uint32;
                description
                  "Number of A10 Reg-Update messages received from a
                   PDSN with reason code \"Registration Timeout\"";
              }
              leaf A11RegUpdatePDSNErrorPDSN {
                type uint32;
                description
                  "Number of A10 Reg-Update messages received from a
                   PDSN with reason code \"PDSN Error\"";
              }
              leaf A11RegUpdateInterPCFHandoffPDSN {
                type uint32;
                description
                  "Number of A10 Reg-Update messages received from a
                   PDSN with reason code \"Inter PCF Handoff\"";
              }
              leaf A11RegUpdateInterPDSNHandoffPDSN {
                type uint32;
                description
                  "Number of A10 Reg-Update messages received from a
                   PDSN with reason code \"Inter PDSN Handoff\"";
              }
              leaf A11RegUpdatePDSNOAMPInterventionPDSN {
                type uint32;
                description
                  "Number of A10 Reg-Update messages received from a
                   PDSN with reason code \"PDSN OAMP
                   Intervention\"";
              }
              leaf A11RegUpdateAccountingErrorPDSN {
                type uint32;
                description
                  "Number of A10 Reg-Update messages received from a
                   PDSN with reason code \"Accounting Error\"";
              }
              leaf A11RegUpdateUserFailedAuthenticationPDSN {
                type uint32;
                description
                  "Number of A10 Reg-Update messages received from a
                   PDSN with reason code \"User Failed
                   Authentication\"";
              }
              leaf A11RegUpdateUnknownCauseCodePDSN {
                type uint32;
                description
                  "Number of A10 Reg-Update messages received from a
                   PDSN with Unknown Cause Code";
              }
              leaf A11RegUpdateWithoutReasonCodePDSN {
                type uint32;
                description
                  "Number of A10 Reg-Update messages received from a
                   PDSN with PDSN Code Not Included";
              }
            }

            container AuxA10Stats {
              config false;
              description
                "This object is used in obtaining the Auxillary A10
                 Connection stats for each PDSN";
              leaf PDSNNumberAuxA10Perf {
                type int32 {
                  range "0..127";
                }
                description
                  "The PDSN Number";
              }
              leaf PDSNIPAddressAuxA10Perf {
                type types:IPAddress;
                description
                  "The IP Address of the PDSN for which the PCF PDSN
                   stats is obtained";
              }
              leaf AuxA10ConnectionsCreatedInFirstRegReqPDSN {
                type uint32;
                description
                  "Number of Auxillary A10 Connections Created in
                   the First Registration Request Message to the
                   PDSN";
              }
              leaf AuxA10ConnectionsCreatedInSubsequentRegReqPDSN {
                type uint32;
                description
                  "Number of Auxillary A10 Connections Created in
                   Subsequent Registration Request Messages to
                   the PDSN";
              }
              leaf AuxA10FwdIpFlowsCreatedPDSN {
                type uint32;
                description
                  "Number of Forward IP Flows created with this PDSN
                   for the Auxillary A10s";
              }
              leaf AuxA10RevIpFlowsCreatedPDSN {
                type uint32;
                description
                  "Number of Forward IP Flows created with this PDSN
                   for the Auxillary A10s";
              }
              leaf AuxA10IpFlowAccountingRegRequestsPDSN {
                type uint32;
                description
                  "Number of IP flow Accounting Reg Requests sent to
                   the PDSN";
              }
            }

            container PCFPDSNStats {
              config false;
              description
                "This object is used in obtaining the PCF PDSN stats
                 for each PDSN";
              leaf A10SetupAttemptsPDSN {
                type uint32;
                description
                  "Number of attempts the PCF made to establish an
                   A10 connection with PDSN.  If PCF fails
                   establishing such a connection on this PDSN
                   and goes on to use another PDSN for that
                   connection, it will be counted as two setup
                   attempts.";
              }
              leaf A10SetupSuccessesPDSN {
                type uint32;
                description
                  "Number of times PCF succeeded in establishing an
                   A10 connection with this PDSN.";
              }
              leaf A10SetupBlocksPDSN {
                type uint32;
                description
                  "Number of times PCF was blocked in establishing
                   an A10 connection with this PDSN.";
              }
              leaf A11RegReqDeniedIdMismatchPDSN {
                type uint32;
                description
                  "Number ofA11 Registration Request denied with a
                   reason \"Id Mismatch\" (A11 error code: 0x85)
                   by the PDSN";
              }
              leaf A11RegReqDeniedUnknownPDSNPDSN {
                type uint32;
                description
                  "Number of A11 Registration Request denied with a
                   reason \"Unknown PDSN\" (A11 error code:
                   0x88)by the PDSN.";
              }
              leaf A11RegReqDeniedNoReasonPDSN {
                type uint32;
                description
                  "Number of A11 Registration Request denied with no
                   reason code by the PDSN.";
              }
              leaf A11RegReqDeniedAdminProhibitPDSN {
                type uint32;
                description
                  "Number of A11 Registration Request denied with a
                   reason \"Admin Prohibited\" (A11 error code :
                   0x81) by the PDSN.";
              }
              leaf A11RegReqDeniedInsuffResourcesPDSN {
                type uint32;
                description
                  "Number of A11 Registration Request denied with a
                   reason \"Insufficient Resources\" (A11 error
                   code: 0x82) by the PDSN.";
              }
              leaf A11RegReqDeniedFailedAuthPDSN {
                type uint32;
                description
                  "Number of A11 Registration Request denied with a
                   reason \"Mobile Node Authentication Failure\"
                   (A11 error code: 0x83) by the PDSN.";
              }
              leaf A11RegReqDeniedMalformedReqPDSN {
                type uint32;
                description
                  "Number of A11 Registration Request denied with a
                   reason \"Malformed Request\" (A11 error code:
                   0x86) by the PDSN";
              }
              leaf A11RegReqDeniedUnsuppVendIdPDSN {
                type uint32;
                description
                  "Number ofA11 Registration Request denied with a
                   reason \"Unsupported Vendor Id\" (A11 error
                   code: 0x8D)by the PDSN";
              }
              leaf A11RegReqDeniedReverseTunnelUnavailablePDSN {
                type uint32;
                description
                  "Number ofA11 Registration Request denied with a
                   reason \"Reverse Tunnel Unavailable\" (A11
                   error code: 0x89)by the PDSN";
              }
              leaf A11RegReqDeniedReverseTunnelTbitNotSetPDSN {
                type uint32;
                description
                  "Number ofA11 Registration Request denied with a
                   reason \"Reverse Tunnel Tbit Not Set\" (A11
                   error code: 0x8A)by the PDSN";
              }
              leaf A11RegReqDeniedUnknownErrorCodePDSN {
                type uint32;
                description
                  "Number of A11 Registration Request denied with an
                   unspecified reason (A11 error code : 0x80) by
                   the PDSN";
              }
              leaf A10RegReqForRegistrationRetransmissionsPDSN {
                type uint32;
                description
                  "Number of A11 Registration Requests retransmitted
                   during A10 setup";
              }
              leaf A10RegReqForReRegistrationRetransmissionsPDSN {
                type uint32;
                description
                  "Number of A11 Registration Requests retransmitted
                   during A10 reregistration";
              }
              leaf A10RegReqForReleaseRetransmissionsPDSN {
                type uint32;
                description
                  "Number of A11 Registration Requests retransmitted
                   during A10 realease";
              }
              leaf PDSNNumberPDSNPerf {
                type int32 {
                  range "0..127";
                }
                description
                  "The PDSN Number";
              }
              leaf PDSNipAddressPDSNPerf {
                type types:IPAddress;
                description
                  "The IP Address of the PDSN for which the PCF PDSN
                   stats is obtained";
              }
            }
          }

          container Redirect {
            description
              "CDMA2000 HRPD service redirection parameters.";
            leaf RedirectChannelNumber {
              type uint32 {
                range "0..2047";
              }
              description
                "The channel number set from ACS that the FAP uses
                 to redirect the AT in case of closed access or
                 when exceeding session capacity.  The ACS shall
                 push this if the the operator has provided this
                 information in a configuration file.  If this is
                 not configured, the FAP rejects the AT.  The
                 supported range is 0..2047.";
            }
            leaf RedirectBandClass {
              type uint32 {
                range "0..31";
              }
              description
                "The bandclass set from ACS that the FAP uses to
                 redirect the AT incase of closed access or when
                 exceeding session capacity.  The ACS shall push
                 this if the the operator has provided this
                 information in a configuration file.  If this is
                 not configured, the FAP rejects the AT.  The
                 supported range is 0..9.";
            }
          }

          container CallControlStats {
            config false;
            description
              "Details on call control stats";
            leaf NumSessionSetupAttempts {
              type uint32;
              description
                "This parameter is a counter for the total number of
                 session instances that are created on a specific
                 FAP when a regular session setup attempt is
                 initiated with an unknown RATI";
            }
            leaf NumSessionSetupSuccessful {
              type uint32;
              description
                "This parameter is a counter for the total number of
                 successful regular session setup attempts that
                 are initiated with an unknown RATI";
            }
            leaf NumCurrentSessionsEstablished {
              type uint32;
              description
                "This parameter is a counter for the total number of
                 successfully established HRPD Sessions that
                 exists on a specific picasso";
            }
            leaf NumPageMessagesToAt {
              type uint32;
              description
                "The number of times a Page Message was sent to the
                 AT to facilitate the setup of a connection.";
            }
            leaf NumPagesSucceeded {
              type uint32;
              description
                "The total number of pages succeeded";
            }
            leaf NumConnectionsOpened {
              type uint32;
              description
                "Total HRPD Connections Opened";
            }
            leaf NumSessionSetupsFailedToTermAuth {
              type uint32;
              description
                "This parameter is a counter for the total number of
                 HRPD session setups that are aborted due to
                 various failure reasons";
            }
            leaf NumForwardRLPBytes {
              type uint32;
              description
                "Number of HRPD packets(bytes) sent from PDSN to AT.";
            }
            leaf NumReverseRLPBytes {
              type uint32;
              description
                "No.  of HRPD packets(bytes) sent from AT to PDSN.";
            }
            leaf AverageSessionSetupTime {
              type uint32;
              description
                "This parameter maintains a record of the average
                 session setup time for all successfully setup
                 sessions on a specific FAP.  The average session
                 setup time is in units of {{units}}.";
            }
            leaf AveragePageSetupTime {
              type uint32;
              description
                "The average connection setup time in response to a
                 FAP initiated page.  The time is from initiation
                 of Page to the time the connection is declared
                 open";
            }
            leaf NumConnSetupsAborted {
              type uint32;
              description
                "The number of connection setups that were aborted";
            }
            leaf NumForwardPreRLPDroppedPkts {
              type uint32;
              description
                "Number of packets dropped at Pre-RLP queue due to
                 overflow in forward direction.  This counter
                 will also be written to the performance log.";
            }
          }

          container QoSStats {
            config false;
            description
              "This object is used in obtaining the QoS Common
               Performance stats";
            leaf NumQoSSubscriberProfileUpdatesRcvd {
              type uint32;
              description
                "Number of subscriber QoS profile updates received
                 from the PDSN.";
            }
            leaf NumPDSNIPFlowUpdatesMsgRcvd {
              type uint32;
              description
                "Number of PDSN IP flow update messages received
                 from PDSN.";
            }
            leaf NumPDSNIPFlowUpdatesMsgFailed {
              type uint32;
              description
                "Number of PDSN IP Flow updates messages that failed
                 per RNC.";
            }
            leaf NumQoSSetupRequestsReceived {
              type uint32;
              description
                "Number of QoS setup requests received from the AT.";
            }
            leaf NumQoSSetupRequestsAccepted {
              type uint32;
              description
                "Number of QoS setup requests received from the AT
                 that the FAP RNC accepted.";
            }
            leaf NumQoSSetupRequestsRejected {
              type uint32;
              description
                "Number of QoS setup requests from the AT that the
                 FAP RNC rejected.";
            }
            leaf NumReservationOnRequestsReceived {
              type uint32;
              description
                "Number of ReservationOnRequest messages received
                 from the AT.";
            }
            leaf NumReservationOnRequestsAccepted {
              type uint32;
              description
                "Number of ReservationOnRequest messages received
                 from the AT that the FAP RNC accepted.";
            }
            leaf NumReservationOnRequestsRejected {
              type uint32;
              description
                "Number of ReservationOnRequest message received
                 from the AT that the FAP RNC rejected.";
            }
            leaf NumReservationOnRequestsFailed {
              type uint32;
              description
                "Number of ReservationOnRequest message received
                 from the AT that the FAP RNC failed.";
            }
            leaf NumFwdReservationOnMessagesSent {
              type uint32;
              description
                "Number of times the FAP RNC sent a FwdReservationOn
                 message to the AT to activate a forward
                 Reservation.";
            }
            leaf NumRevReservationOnMessagesSent {
              type uint32;
              description
                "Number of times the FAP RNC sent a RevReservationOn
                 message to the AT to activate a reverse
                 Reservation.";
            }
            leaf NumReservationOffRequestsReceived {
              type uint32;
              description
                "Number of ReservationOffRequest message is received
                 from the AT.";
            }
            leaf NumReservationOffRequestsAccepted {
              type uint32;
              description
                "Number of ReservationOffRequest messages received
                 from the AT that the FAP RNC accepted.";
            }
            leaf NumReservationOffRequestsRejected {
              type uint32;
              description
                "Number of ReservationOffRequest messages received
                 from the AT that the FAP RNC rejected.";
            }
            leaf NumFwdReservationOffMessagesSent {
              type uint32;
              description
                "Number of times the FAP RNC sent a
                 FwdReservationOff message to the AT to
                 deactivate a forward Reservation.";
            }
            leaf NumRevReservationOffMessagesSent {
              type uint32;
              description
                "Number of times the FAP RNC sent a
                 RevReservationOff message to the AT to
                 deactivate a reverse Reservation.";
            }
            leaf NumQoSReleaseRequestsReceived {
              type uint32;
              description
                "Number of QoS release requests received from the
                 AT.";
            }
            leaf NumConnectionCloseInitiatedNoRANRsr {
              type uint32;
              description
                "Number of times FAP RNC initiated a connection
                 close in response to the ReservationOnRequest
                 because it did not have the RAN resources to
                 satisfy one or more Reservations included in the
                 request.";
            }
          }

          container RNCSigAppsStats {
            config false;
            description
              "Stats for HRPD RNC signaling procedures.";
            leaf CNumPageRequests {
              type uint32;
              description
                "Number of HRPD Page requests made after data has
                 flowed on the A10 connection.";
            }
            leaf SNumPageRequests {
              type uint32;
              description
                "Number of HRPD Page requests made before data has
                 flowed on the A10 connection.";
            }
            leaf SNumConnectionSetupAttempts {
              type uint32;
              description
                "Number of HRPD Connection setups attempted before
                 data has flowed on the A10 connection.";
            }
            leaf CNumConnectionSetupAttempts {
              type uint32;
              description
                "Number of HRPD Connection setups attempted after
                 data has flowed on the A10 connection.";
            }
            leaf SNumConnectionSetupSuccess {
              type uint32;
              description
                "Number of HRPD Connection setups succeeded before
                 data has flowed on the A10 connection.";
            }
            leaf CNumConnectionSetupSuccess {
              type uint32;
              description
                "Number of HRPD Connection setups succeeded after
                 data has flowed on the A10 connection.";
            }
            leaf SNumNormalConnectionCloses {
              type uint32;
              description
                "The number of HRPD connections that were closed
                 normally before data has flowed on the A10
                 connection.";
            }
            leaf CNumNormalConnectionCloses {
              type uint32;
              description
                "The number of HRPD connections that were closed
                 normally after data has flowed on the A10
                 connection.";
            }
            leaf SNumTotalConnectionCloses {
              type uint32;
              description
                "The total number of HRPD connections closed,
                 normally or abnormally, data has flowed on the
                 A10 connection.";
            }
            leaf CNumTotalConnectionCloses {
              type uint32;
              description
                "The total number of HRPD connections closed,
                 normally or abnormally, after data has flowed on
                 the A10 connection.";
            }
            leaf SNumRFRelatedDrops {
              type uint32;
              description
                "Number of HRPD connection close because of RTC loss
                 or No FTC before data has flowed on the A10
                 connection";
            }
            leaf CNumRFRelatedDrops {
              type uint32;
              description
                "Number of HRPD connection close because of RTC loss
                 or No FTC after data has flowed on the A10
                 connection";
            }
            leaf SNumPageResponses {
              type uint32;
              description
                "Total number of successful responses to HRPD page
                 requests that were received from the AT before
                 the final page timeout and before data has
                 flowed on the A10 connection.";
            }
            leaf CNumPageResponses {
              type uint32;
              description
                "Total number of successful responses to HRPD page
                 requests that were received from the AT before
                 the final page timeout and after data has flowed
                 on the A10 connection.";
            }
            leaf SNumRFRelatedDropsRTCLost {
              type uint32;
              description
                "This statistic counts the number of times the HRPD
                 connection was dropped before data has flowed on
                 the A10 connection because a Reverse Traffic
                 Channel (RTC) lost indication was received, and
                 as a result, no reverse link for the connection
                 were available.";
            }
            leaf CNumRFRelatedDropsRTCLost {
              type uint32;
              description
                "This statistic counts the number of times the HRPD
                 connection was dropped after data has flowed on
                 the A10 connection because a Reverse Traffic
                 Channel (RTC) lost indication was received, and
                 as a result, no reverse link for the connection
                 were available.";
            }
            leaf SNumRFRelatedDropsNoFTC {
              type uint32;
              description
                "This statistic counts the number of HRPD
                 connections that were dropped before data has
                 flowed on the A10 connection because of
                 indications that there is no active Forward
                 Traffic Channel (FTC) available.";
            }
            leaf CNumRFRelatedDropsNoFTC {
              type uint32;
              description
                "This statistic counts the number of HRPD
                 connections that were dropped after data has
                 flowed on the A10 connection because of
                 indications that there is no active Forward
                 Traffic Channel (FTC) available.";
            }
            leaf SNumNetworkErrorDrops {
              type uint32;
              description
                "This statistic counts the number of HRPD
                 connections that were closed before data has
                 flowed on the A10 connection because the FAP
                 closed the open A10 connection.";
            }
            leaf CNumNetworkErrorDrops {
              type uint32;
              description
                "This statistic counts the number of HRPD
                 connections that were closed after data has
                 flowed on the A10 connection because the FAP
                 closed the open A10 connection.";
            }
            leaf SNumNetworkErrorDropsRNCInternal {
              type uint32;
              description
                "This statistic counts the number of open HRPD
                 connections that were closed before data has
                 flowed on the A10 connection because the FAP
                 closed the A10 connection due to internal
                 failures.";
            }
            leaf CNumNetworkErrorDropsRNCInternal {
              type uint32;
              description
                "This statistic counts the number of open HRPD
                 connections that were closed after data has
                 flowed on the A10 connection because the FAP
                 closed the A10 connection due to internal
                 failures.";
            }
            leaf SNumNetworkErrorDropsRNCExternal {
              type uint32;
              description
                "This statistic counts the number of open HRPD
                 connections that were closed before data has
                 flowed on the A10 connection because the FAP
                 closed the A10 connection due to the PDSN
                 unreachablity.";
            }
            leaf CNumNetworkErrorDropsRNCExternal {
              type uint32;
              description
                "This statistic counts the number of open HRPD
                 connections that were closed after data has
                 flowed on the A10 connection because the FAP
                 closed the A10 connection due to the PDSN
                 unreachablity.";
            }
            leaf SNumNetworkErrorDropsA10SetupFail {
              type uint32;
              description
                "This statistic counts the number of open HRPD
                 connections that were closed before data has
                 flowed on the A10 connection because there was
                 failure in the A10 connection set-up.";
            }
            leaf CNumNetworkErrorDropsA10SetupFail {
              type uint32;
              description
                "This statistic counts the number of open HRPD
                 connections that were closed after data has
                 flowed on the A10 connection because there was
                 failure in the A10 connection set-up.";
            }
            leaf SNumMiscDropsSectorDown {
              type uint32;
              description
                "This statistic counts the number of HRPD
                 connections that were dropped before data has
                 flowed on the A10 connection because there is
                 only one pilot available for the connection and
                 a sector down indication has been received for
                 that pilot.";
            }
            leaf CNumMiscDropsSectorDown {
              type uint32;
              description
                "This statistic counts the number of HRPD
                 connections that were dropped after data has
                 flowed on the A10 connection because there is
                 only one pilot available for the connection and
                 a sector down indication has been received for
                 that pilot.";
            }
            leaf SNumMiscDropsInternalError {
              type uint32;
              description
                "This statistic counts the number of HRPD
                 connections that were dropped before data has
                 flowed on the A10 connection due to internal
                 software errors.";
            }
            leaf CNumMiscDropsInternalError {
              type uint32;
              description
                "This statistic counts the number of HRPD
                 connections that were dropped after data has
                 flowed on the A10 connection due to internal
                 software errors.";
            }
            leaf CNumMiscDropsStateMismatch {
              type uint32;
              description
                "This statistic counts the number of HRPD
                 connections that were dropped after data has
                 flowed on the A10 connection when the FAP finds
                 a state mismatch between itself andthe AT.  Such
                 a mismatch is found when a connection request
                 message is received from the AT, and the
                 connection is already open as perceived by the
                 FAP.";
            }
            leaf SNumMiscDropsStateMismatch {
              type uint32;
              description
                "This statistic counts the number of connections
                 that were dropped before the demarcation point
                 when the FAP finds a state mismatch between
                 itself and the AT.  Such a mismatch is found
                 when a connection request message is received
                 from the AT, and the connection is already open
                 as perceived by the FAP.";
            }
            leaf SNumMiscDropsDueToRLP {
              type uint32;
              description
                "This statistic counts the number of times the HRPD
                 connection was dropped before data has flowed on
                 the A10 connection at the request of the Radio
                 Link Protocol.  This request is generated when
                 the HDR Fast Path component finds that the reset
                 acknowledgment timeout has expired for the
                 connection.";
            }
            leaf CNumMiscDropsDueToRLP {
              type uint32;
              description
                "This statistic counts the number of times the HRPD
                 connection was dropped after data has flowed on
                 the A10 connection at the request of the Radio
                 Link Protocol.  This request is generated when
                 the HDR Fast Path component finds that the reset
                 acknowledgment timeout has expired for the
                 connection.";
            }
          }

          container AccessAuthConfig {
            description
              "HRPD A12-related service stats.";
            leaf A12AccessAuthenticationEnable {
              type int32 {
                range "0..1";
              }
              description
                "Flag to enable/Disable HRPD Access Authentication.
                 {{true}} - Enabled, {{false}} - Disabled.";
            }
          }

          container AccessAuthStats {
            config false;
            description
              "This object is used in obtaining the Access
               Authentication related stats.";
            leaf AnPppAuthenticationAttemptsByNode {
              type uint32;
              description
                "Number of AnPppAuthentications attempted by the
                 FAP.";
            }
            leaf A12RequestsSentFromNode {
              type uint32;
              description
                "Number of A12 Access Requests Sent from the FAP.";
            }
            leaf A12RejectsReceivedByNode {
              type uint32;
              description
                "Number of A12 Access Rejects received from the FAP.";
            }
            leaf A12AcceptsReceivedByNode {
              type uint32;
              description
                "Number of A12 Access Accepts received by the FAP.";
            }
            leaf A12AccessChallengesReceivedByNode {
              type uint32;
              description
                "Number of A12 Access Challenges received by the
                 FAP.";
            }
            leaf A12RetransmitsSentFromNode {
              type uint32;
              description
                "Number of A12 Access Requests retransmitted from
                 the FAP.";
            }
            leaf A12TimeoutsEventsForNode {
              type uint32;
              description
                "Number of A12 Timeout events occurred at the FAP
                 due to unreachability of the AAA server/ no
                 response from the AAA server.";
            }
            leaf A12MalformedresponseReceivedByNode {
              type uint32;
              description
                "Number of Malformed A12 Access Response received by
                 the FAP RNC.";
            }
            leaf A12BadAuthenticatorReceivedByNode {
              type uint32;
              description
                "Number of A12 Access Response with Bad
                 Authenticator received by the FAP RNC.";
            }
            leaf A12UnknownTypeReceivedByNode {
              type uint32;
              description
                "Number of A12 Packet of unknown type received by
                 the FAP RNC.";
            }
            leaf A12UnknownPktReceivedByNode {
              type uint32;
              description
                "Number of unknown A12 packets received by the FAP
                 RNC.";
            }
            leaf A12UnknownServerReceivedByNode {
              type uint32;
              description
                "Number of A12 packets received from unknown AAA
                 server by the FAP RNC.";
            }
            leaf A12OtherFailureOccurencesInNode {
              type uint32;
              description
                "Number of A12 packets failed due to other failure
                 occurences in the AAA server.";
            }
            leaf A12ByPassNumAtsWithUnknownMfrCodeByNode {
              type uint32;
              description
                "Number of ATs with UnknowMfrCode detected in the
                 FAP RNC.";
            }
            leaf A12TxPathFailDueToAnPppErrorByNode {
              type uint32;
              description
                "Number of times sending of A12 packet failed in Tx
                 Path in the FAP RNC due to \"AnPPP Error\".";
            }
            leaf A12TxPathFailDueToNoServerAvailableByNode {
              type uint32;
              description
                "Number of times sending of A12 packet failed in Tx
                 Path in the FAP RNC due to \"No Server
                 Available\".";
            }
            leaf A12TxPathFailDueToInternalErrorByNode {
              type uint32;
              description
                "Number of times sending of A12 packet failed in Tx
                 Path in the FAP RNC due to \"internal error\".";
            }
            leaf A12TxPathFailDueToNoPacketIdAvailableByNode {
              type uint32;
              description
                "Number of times sending of A12 packet failed in Tx
                 Path in the FAP RNC due to \"No packet id
                 available\".";
            }
            leaf A12TxPathFailDueToTransmitErrorByNode {
              type uint32;
              description
                "Number of times sending of A12 packet failed in Tx
                 Path in the FAP RNC due to \"Transmit Error\".";
            }
            leaf A12SvrTimeoutsForNode {
              type uint32;
              description
                "Number of A12 server timeouts happened in the FAP
                 RNC.";
            }
            leaf A12EnhTaBypassLcpTimeoutByNode {
              type uint32;
              description
                "Number of LCP timeouts happened in the FAP RNC when
                 Enhanced TA A12Bypass mode is enabled.";
            }
            leaf A12EnhTaBypassChapTimeoutByNode {
              type uint32;
              description
                "Number of CHAP timeouts happened in the FAP RNC
                 when Enhanced TA A12Bypass mode is enabled.";
            }
            leaf A12EnhTaBypassChapInvalidByNode {
              type uint32;
              description
                "Number of CHAP Challenge response received from the
                 AT when Enhanced TA A12Bypass mode is enabled.";
            }
            leaf A12EnhTaBypassChapNaiMatchesA12BypassListByNode {
              type uint32;
              description
                "Number of times the CHAP NAI received from the AT
                 matches with A12Bypass List in the FAP RNC when
                 Enhanced TA A12Bypass mode is enabled.";
            }
            leaf A12SessionTaTimeoutByNode {
              type uint32;
              description
                "Number of times Session timeouts occurred due to
                 TA.";
            }
            leaf AccessAuthFailedDueToSessionCloseTotal {
              type uint32;
              description
                "Number of times the Access Authenticaiton failed
                 due to Sesion close.";
            }
            leaf AccessAuthSucceeded {
              type uint32;
              description
                "Number of times the Access Authenticaiton
                 succeeded.";
            }
          }
        }

        container Beacon {
          description
            "This object models the attributes to control the
             generalized beacon.  The beacon is modeled as a
             beacon frame composed of multiple beacon intervals.
             The beacon frame start is time-aligned to the
             instant when 1x 80ms paging frames and HRPD control
             channel frames align (occurs once every 1.28s).";
          leaf BeaconAdminStatus {
            type enumeration {
              enum "Locked";
              enum "Unlocked";
            }
            description
              "Allows administrative control of beacon.";
          }
          leaf BeaconOperStatus {
            type enumeration {
              enum "Locked";
              enum "Unlocked";
              enum "Fault";
            }
            config false;
            description
              "Reports operational status of beacon.";
          }
          leaf HRPDBeaconEnable {
            type boolean;
            description
              "If set to {{true}} the HRPD-specific beacon described
               by {{object|HRPDBeaconList}} object is enabled.
               If set to {{false}}, all HRPD beacons (if any) are
               contained in the BeaconList object.";
          }
          leaf Period {
            type uint32 {
              range "0..32767";
            }
            description
              "Length and periodicity of the beacon frame in
               {{units}}.  Reference - {{bibref|3GPP2-C.S0005}}.";
          }
          leaf MaxFAPBeaconTxPower {
            type string {
              length "0..64";
            }
            description
              "Maximum transmission power allowed on the FAP Beacon
               frequencies.  {{param}} is expressed as a range of
               allowed maximum power levels with \"..\" (two
               periods)
            
               between the upper and lower values, i.e.
               \"<;Pmax_low>..<;Pmax_high>\".
            
               {{param}} identifies the limits between which the
               FAP can self-configure its maximum beacon transmit
               power.
            
               Self-configuration for maximum beacon transmission
               power is controlled by
               {{param|.Capabilities.CDMA2000.OneX.SelfConfig.MaxFAPBeaconTxPowerConfig}}
               from an availability perspective and
               {{param|.FAPControl.CDMA2000.OneX.SelfConfig.MaxFAPBeaconTxPowerSelfConfigEnable}}
               from an enabled perspective.  <;Pmax_low> and
               <;Pmax_high> are measured in dBm and have a range
               of -40.0 to 20.0 incremented by 0.1 dB.";
          }
          leaf MaxFAPBeaconTxPowerInUse {
            type int32 {
              range "-400..200";
            }
            config false;
            description
              "Maximum beacon transmission power measured in
               {{units}} currently used by the FAP on any beacon
               frequency.  Actual values of the maximum
               transmission power are -40.0 dBm to 20.0 dBm in
               steps of 0.1 dB.  The value of {{param}} divided
               by 10 yields the actual value of the maximum
               transmission power.";
          }
          leaf BeaconPchPwrPercentage {
            type int32 {
              range "1000..1000000";
            }
            description
              "Percentage of Max Sector Power Used By Paging Channel
               (expressed in {{units}}).
            
               For example, 93333 means 93.333% of the max sector
               power.";
          }
          leaf MaxHRPDBeaconTxPower {
            type string {
              length "0..64";
            }
            description
              "Maximum transmission power allowed on the dedicated
               HRPD beacon.  {{param}} is expressed as a range of
               allowed maximum power levels with \"..\" (two
               periods) between the upper and lower values, i.e.
               \"<Pmax_low>..<Pmax_high>\".
            
               MaxHRPDBeaconTxPower identifies the limits between
               which the FAP can self-configure its maximum
               beacon transmit power.  Self-configuration for
               maximum beacon transmission power is controlled by
               {{param|.Capabilities.CDMA2000.OneX.SelfConfig.MaxFAPBeaconTxPowerConfig}}
               from an availability perspective and
               {{param|.FAPControl.CDMA2000.OneX.SelfConfig.MaxFAPBeaconTxPowerSelfConfigEnable}}
               from an enabled perspective.  <Pmax_low> and
               <Pmax_high> are measured in dBm and have a range
               of -40.0 to 20.0 incremented by 0.1 dB.";
          }
          leaf MaxHRPDBeaconTxPowerInUse {
            type int32 {
              range "-400..200";
            }
            config false;
            description
              "Maximum beacon transmission power measured in dBm
               currently used by the FAP on any beacon frequency.
            
               Actual values of the maximum transmission power
               are -40.0 dBm to 20.0 in units of {{units}}.  The
               value of {{param}} divided by 10 yields the actual
               value of the maximum transmission power.";
          }
          leaf BeaconPilotPwrPercentage {
            type int32 {
              range "1000..1000000";
            }
            description
              "Percentage of Max Sector Power Used By Pilot Channel
               (expressed in {{units}}).  For example, 19950
               means 19.950% of total.";
          }
          leaf BeaconSyncPwrPercentage {
            type int32 {
              range "1000..1000000";
            }
            description
              "Percentage of Max Sector Power Used By Sync Channel
               (expressed in {{units}}).  For example, 23458
               means 23.458% of the max sector power.";
          }
          leaf MaxBeaconListEntries {
            type uint32;
            config false;
            description
              "Maximum number of entries in the
               {{object|.CellConfig.CDMA2000.Beacon.BeaconList.{i}.}}
               object.";
          }
          leaf MaxHRPDBeaconListEntries {
            type uint32;
            config false;
            description
              "Maximum number of entries in the
               {{object|.CellConfig.CDMA2000.Beacon.HRPDBeaconList.{i}.}}
               object.";
          }

          list BeaconList {
            key "BeaconIndex";
            description
              "This object models an individual beacon intervals.
               It may be used to model both 1x and HRPD beacons
               with offset from start of beacon frame measured in
               80ms slots.";
            leaf Enable {
              type boolean;
              default "false";
              description
                "Enables or disables the {{object}} entry.";
            }
            leaf BeaconIndex {
              type int32;
              config false;
              default "0";
              description
                "Instance identifier for this beacon interval.
                 Allowed range is
                 0..(BeaconListNumberOfEntries-1).";
            }
            leaf Offset {
              type uint32 {
                range "0..32767";
              }
              default "0";
              description
                "Offset from the start of the beacon frame in 80ms
                 slots.";
            }
            leaf Duration {
              type uint32 {
                range "0..32767";
              }
              default "0";
              description
                "Duration of this beacon interval in {{units}}.";
            }
            leaf TransmissionFormat {
              type enumeration {
                enum "0";
                enum "1";
              }
              default "1";
              description
                "Determines if this beacon interval shall transmit
                 HRPD (HRPD) or CDMA2000 1x.{HRPD=\"0\",
                 1x=\"1\"}.";
            }
            leaf BeaconBandClass {
              type int32 {
                range "0..31";
              }
              default "0";
              description
                "Band class for this beacon interval.";
            }
            leaf BeaconChannelFreq {
              type uint32 {
                range "0..2016";
              }
              default "0";
              description
                "Channel number for this beacon interval.";
            }
            leaf BeaconPNOffset {
              type string {
                length "0..32";
              }
              description
                "{{list}} Each item is a pilot PN offset of the
                 pilot beacon for this channel in units of 64 PN
                 chips.  If this parameter contains more than one
                 item, then the FAP is expected to select one
                 from the list as the PilotPN to be used for this
                 channel.  If the self-configuration capability
                 is not to be used, then this parameter SHALL
                 contain only a single item.";
            }
            leaf TxPower {
              type int32 {
                range "-40..20";
              }
              default "-40";
              description
                "TX power for the beacon interval (in {{units}}).
                 If self-configuration of the Beacon Tx Power is
                 enabled, then this value is determined by the
                 FAP.";
            }
            leaf BeaconSID {
              type uint32 {
                range "0..65535";
              }
              default "0";
              description
                "SID for this beacon interval.";
            }
            leaf BeaconNID {
              type uint32 {
                range "0..32767";
              }
              default "0";
              description
                "NID for this beacon interval.";
            }
            leaf BeaconPZID {
              type uint32;
              default "0";
              description
                "PZID for this beacon interval.";
            }
          }

          list HRPDBeaconList {
            key "BeaconIndex";
            description
              "This object models individual HRPD beacon intervals
               where the beacon start is expressed as a number of
               HRPD control channel slots from the start of the
               beacon frame.";
            leaf Enable {
              type boolean;
              default "false";
              description
                "Enables or disables the {{object}} entry.";
            }
            leaf BeaconIndex {
              type int32;
              config false;
              default "0";
              description
                "Instance identifier for this beacon interval.
                 Allowed range is
                 0..(HRPDBeaconListNumberOfEntries-1).";
            }
            leaf CCoffset {
              type uint32 {
                range "0..2048";
              }
              default "0";
              description
                "Offset of the current beacon interval from the
                 start of the beacon frame, in Control Channel
                 cycles.  The HRPDBeaconList interval SHOULD not
                 overlap in time with any beacon interval for the
                 same channel defined in the BeaconList object.";
            }
            leaf Offset {
              type int32 {
                range "-127..128";
              }
              default "0";
              description
                "Start of beacon transmission with respect to the
                 Control Channel boundary.";
            }
            leaf Duration {
              type uint32 {
                range "0..256";
              }
              default "0";
              description
                "Duration of the beacon transmission within a
                 Control Channel cycle, in slots.  Beacon is
                 transmitted starting offset from the CC boundary
                 for duration.  Transmission restarts offset from
                 the next CC boundary, given that beacon interval
                 spans more than 1 CC cycles.";
            }
            leaf NumCCcycles {
              type uint32 {
                range "0..48";
              }
              default "0";
              description
                "Number of Control Channel Cycles this beacon
                 interval spans.";
            }
            leaf BeaconBandClass {
              type uint32 {
                range "0..31";
              }
              default "0";
              description
                "Band class for this beacon interval.";
            }
            leaf BeaconChannelFreq {
              type uint32 {
                range "0..2016";
              }
              default "0";
              description
                "Channel number for this beacon interval.";
            }
            leaf BeaconPNOffset {
              type string {
                length "0..256";
              }
              default "";
              description
                "{{list}} Each item is a pilot PN offset of the
                 pilot beacon for this channel in units of 64 PN
                 chips.  If this parameter contains more than one
                 item, then the FAP is expected to select one
                 from the list as the PilotPN to be used for this
                 channel.  If the self-configuration capability
                 is not to be used, then this parameter SHALL
                 contain only a single item.";
            }
            leaf TxPower {
              type int32 {
                range "-40..20";
              }
              default "-40";
              description
                "TX power for the beacon interval.  If
                 self-configuration of the HRPD Beacon Tx Power
                 is enabled, then this value is determined by the
                 FAP.";
            }
          }
        }
      }
    }

    container REM {
      description
        "This object contains parameters relating to REM (Radio
         Environment Measurement).";

      container UMTS {
        description
          "This object contains Radio Environment Measurement
           parameters for UMTS FAP.";

        container WCDMA {
          description
            "This object contains parameters relating to radio
             environment measurement capabilities for the UMTS
             system.";
          leaf InServiceHandling {
            type enumeration {
              enum "Immediate";
              enum "Delayed";
            }
            default "Immediate";
            description
              "FAP REM behavior with respect to ongoing active
               connections.";
          }
          leaf ScanOnBoot {
            type boolean;
            default "true";
            description
              "Enables or disables Radio Environment Measurement
               during the FAP start up.";
          }
          leaf ScanPeriodically {
            type boolean;
            default "false";
            description
              "Enable Periodic Radio Environment Measurement on all
               enabled RAT.";
          }
          leaf PeriodicInterval {
            type uint32;
            description
              "When {{param|ScanPeriodically}} is {{true}}, this
               value indicates the interval in {{units}} which
               REM is performed while the FAP service is enabled.";
          }
          leaf PeriodicTime {
            type yang:date-and-time;
            description
              "An absolute time reference in UTC to determine when
               the CPE will initiate the periodic REM.  Each REM
               MUST occur at (or as soon as possible after) this
               reference time plus or minus an integer multiple
               of the {{param|PeriodicInterval}}.
            
               {{param}} is used only to set the \"phase\" of the
               REM.  The actual value of {{param}} can be
               arbitrarily far into the past or future.
            
               For example, if {{param|PeriodicInterval}} is
               86400 (a day) and if {{param}} is set to UTC
               midnight on some day (in the past, present, or
               future) then periodic REMs will occur every day at
               UTC midnight.  These MUST begin on the very next
               midnight, even if {{param}} refers to a day in the
               future.
            
               The Unknown Time value defined in
               {{bibref|TR-106a2|Section 3.2}} indicates that no
               particular time reference is specified.  That is,
               the CPE MAY locally choose the time reference, and
               needs only to adhere to the specified
               PeriodicInformInterval.
            
               If absolute time is not available to the CPE, its
               periodic REM behavior MUST be the same as if
               {{param}} parameter was set to the Unknown Time
               value.";
          }
          leaf REMPLMNList {
            type string;
            description
              "{{list}} Each item is a PLMN ID to measure.  PLMN ID
               consists of Mobile Country Code (MCC) and Mobile
               Network Code (MNC) {{bibref|3GPP-TS.23.003}},
               {{bibref|3GPP-TS.24.008}}.
            
               If {{empty}}, then no specific PLMN ID is
               provided, meaning that the FAP is required to scan
               all available PLMN IDs.";
          }
          leaf REMBandList {
            type string {
              length "0..64";
            }
            description
              "{{list}} Each item is a UMTS Band to measure.  Each
               band is identified in by a roman numeral
               {{bibref|3GPP-TS.25.104}}.
            
               If {{empty}} then no specific UMTS band is
               provided, meaning that the FAP is required to scan
               all available bands.
            
               The order of the band indicator has no
               significance.";
          }
          leaf UARFCNDLList {
            type string;
            description
              "{{list}} Each entry is a UARFCN in the DL direction
               to measure.
            
               If {{empty}}, then no specific UARFCN is provided,
               meaning that the FAP is required to scan all
               UARFCNs that it is aware of.";
          }
          leaf ScanTimeout {
            type uint32;
            description
              "Specifies the time-out value in {{units}}, measured
               from the start of the REM scan, before the REM
               scan will time out.";
          }
          leaf ScanStatus {
            type enumeration {
              enum "Indeterminate";
              enum "InProgress";
              enum "Success";
              enum "Error";
              enum "Error_TIMEOUT";
            }
            config false;
            description
              "Indicates the current status of this scan.";
          }
          leaf ErrorDetails {
            type string {
              length "0..256";
            }
            config false;
            description
              "Provides more detail when the {{param|ScanStatus}} is
               either {{enum|Error|ScanStatus}} or
               {{enum|Error_TIMEOUT|ScanStatus}}.";
          }
          leaf LastScanTime {
            type yang:date-and-time;
            config false;
            description
              "The time of the last UMTS system radio environment
               measurement.";
          }
          leaf MaxCellEntries {
            type uint32;
            config false;
            description
              "The maximum number of entries available in the
               {{object|.REM.UMTS.WCDMA.Cell.{i}.}} table.";
          }

          list Cell {
            config false;
            description
              "Table indicating the components of the discovered
               cells.";

            container RF {
              description
                "Table indicating the RF aspect of the discovered
                 cells.";
              leaf UARFCNDL {
                type uint32 {
                  range "0..16383";
                }
                description
                  "The UTRA Absolute Radio Frequency Channel Number
                   (UARFCN) in the DL direction of an FDD mode
                   cell.  {{bibref|3GPP-TS.25.433}}";
              }
              leaf CPICHRSCP {
                type int32 {
                  range "-120..-25";
                }
                description
                  "Received signal level in {{units}} of the CPICH
                   channel.  (Ref.  3GPP TS 25.133)";
              }
              leaf CPICHEcNo {
                type int32 {
                  range "-48..0";
                }
                description
                  "Measured EcNo.  (energy per chip to interference
                   power density) in {{units}} received in the
                   downlink pilot channel.
                
                   Actual values of the range are -24.0 {{units}}
                   to 0.0 {{units}} in steps of 0.5 {{units}}.
                   The value of {{param}} divided by 2 yields the
                   actual value of the range.
                   {{bibref|3GPP-TS.25.133|Section 9.1.2.3}}";
              }
              leaf RSSI {
                type int32 {
                  range "-100..-25";
                }
                description
                  "This measurement is for Inter-frequency handover
                   evaluation, measured in total {{units}} in the
                   band.  {{bibref|3GPP-TS.25.133|Section9.1.3}}";
              }
              leaf PrimaryScramblingCode {
                type uint32 {
                  range "0..511";
                }
                description
                  "Primary scrambling code.";
              }
            }

            container BCCH {
              description
                "Table containing the system information broadcast
                 in the BCCH logical channel.";
              leaf PLMNType {
                type enumeration {
                  enum "GSM-MAP";
                  enum "ANSI-41";
                }
                description
                  "Type of Public Land Mobile Network (PLMN).";
              }
              leaf PLMNID {
                type string {
                  length "0..6";
                }
                description
                  "PLMN ID consists of Mobile Country Code (MCC) and
                   Mobile Network Code (MNC)
                   {{bibref|3GPP-TS.23.003}},
                   {{bibref|3GPP-TS.24.008}}.
                
                   Mobile Country Code consists of three digits
                   and uniquely identifies the country of
                   domicile of the subscriber.
                
                   Mobile Network Code consists of two or three
                   digits and identifies the Home PLMN within a
                   country.
                
                   For a 2-digit MNC the total string length of
                   {{param}} is 5.";
              }
              leaf LAC {
                type uint32 {
                  range "0..65535";
                }
                description
                  "Location Area Code (LAC) as defined in SIB 1
                   {{bibref|3GPP-TS.25.331}}.  The concatenation
                   of PLMN ID (MCC+MNC) and LAC uniquely
                   identifies the LAI (Location Area ID)
                   {{bibref|3GPP-TS.23.003}}.";
              }
              leaf RAC {
                type uint32 {
                  range "0..255";
                }
                description
                  "Routing Area Code (RAC) as defined in SIB 1
                   {{bibref|3GPP-TS.25.331}}.  The concatenation
                   of PLMN ID (MCC+MNC), LAC, and RAC uniquely
                   identifies the RAI (Routing Area ID)
                   {{bibref|3GPP-TS.23.003}}.";
              }
              leaf CellID {
                type uint32 {
                  range "min..268435455";
                }
                description
                  "Cell Identity as defined in SIB3
                   {{bibref|3GPP-TS.25.331|Section10.3.2.2}}.
                   {{bibref|3GPP-TS.24.008}}";
              }
              leaf PCPICHTxPower {
                type int32 {
                  range "-10..50";
                }
                description
                  "Primary Common Pilot Channel (CPICH) power level
                   on SIB 5/6
                   {{bibref|3GPP-TS.25.331|Section10.3.6.55}}.";
              }
              leaf CSGIndicator {
                type boolean;
                description
                  "The CSG-indicator Information Element (IE) in the
                   Master Information Block reflects the access
                   mode of the CSG cell.  It is hence dependent
                   on the value of
                   {{param|.AccessMgmt.UMTS.AccessMode}}.
                
                   If {{true}} the CSG-indicator IE is present,
                   reflecting closed access to the CSG cell.
                
                   If {{false}} the CSG-indicator IE is absent,
                   reflecting the access mode as \"not a
                   closed-access\".
                
                   {{bibref|3GPP-TS.25.331|Section 10.2.48.8.1}}";
              }
              leaf CSGID {
                type uint32 {
                  range "min..134217727";
                }
                description
                  "Defines the Closed Subscriber Group of the Access
                   Control List.  FAP broadcasts this CSG ID in
                   SIB3 {{bibref|3GPP-TS.25.331|Section10.3.2.8}}
                   depending on the AccessMode.";
              }
              leaf UARFCNDLList {
                type uint32 {
                  range "min..16383";
                }
                description
                  "{{list}} Each item is a UTRA Absolute Radio
                   Frequency Channel Number (UARFCN} in the DL
                   direction dedicated to the CSG cells.
                
                   {{param}} is broadcast in SIB 11bis
                   {{bibref|3GPP-TS.25.331|Section
                   10.2.48.8.14a}}.
                
                   The corresponding UTRA Absolute Radio
                   Frequency Channel Number (UARFCN} in the UL
                   direction is derived based on the fixed offset
                   applicable for the frequency band.";
              }

              container CSGPSCSplitInfo {
                description
                  "This object contains parameters relating to the
                   Primary Scambling Code (PSC) split information
                   for the CSG.  Defined in SIB3/11bis
                   {{bibref|3GPP-TS.25.331|Section 10.3.2.8 and
                   10.3.2.9}}.";
                leaf StartPSCRange1Coefficient {
                  type uint32 {
                    range "0..63";
                  }
                  description
                    "The value of this Information Element (IE)
                     multiplied by 8 specifies the start PSC
                     value of the first PSC range as specified in
                     {{bibref|3GPP-TS.25.331|Section 8.6.2.4}}.";
                }
                leaf NumberOfPSCs {
                  type enumeration {
                    enum "5";
                    enum "10";
                    enum "15";
                    enum "20";
                    enum "30";
                    enum "40";
                    enum "50";
                    enum "64";
                    enum "80";
                    enum "120";
                    enum "160";
                    enum "256";
                    enum "alltherest";
                    enum "spare3";
                    enum "spare2";
                    enum "spare1";
                  }
                  description
                    "This Information Element (IE) specifies the
                     number of PSCs reserved for CSG cells in
                     each PSC range.";
                }
                leaf PSCRange2Offset {
                  type uint32 {
                    range "0..63";
                  }
                  description
                    "If this Information Element (IE) is included,
                     the UE shall calculate the second PSC range
                     as specified in
                     {{bibref|3GPP-TS.25.331|Section 8.6.2.4}}.
                  
                     If this Information Element (IE) is not
                     included, the UE shall consider the second
                     PSC range to be not present.";
                }
              }

              container ReferencePosition {
                description
                  "This object defines parameters related to the
                   surface point of the ellipsoid.
                   {{bibref|3GPP-TS.23.032|Section 5}}
                
                   It is characterized by the co-ordinates of an
                   ellipsoid point with altitude, distances, and
                   an angle of orientation.
                
                   This information is used to refer to a point
                   on the Earth's surface, or close to the
                   Earth's surface, with the same longitude and
                   latitude.";
                leaf Latitude {
                  type int32 {
                    range "-90000000..90000000";
                  }
                  description
                    "This parameter specifies the latitude of the
                     device's position in degrees, multiplied by
                     1 million.  The positive value signifies the
                     direction, north of the equator.  The
                     negative value signifies the direction,
                     south of the equator.
                  
                     Range is from: 90.00.00' South (-90,000,000)
                     to 90.00.00' North (90,000,000).
                  
                     Example: A latitude of 13.19.43' N would be
                     represented as 13,323,833, derived as
                     (13*1,000,000)+((19.43*1,000,000)/60).
                     Latitude of 50.00.00' S would be represented
                     as value -50,000,000.
                  
                     If 0 then SIB15 is not detected in the
                     specific cell.";
                }
                leaf Longitude {
                  type int32 {
                    range "-180000000..180000000";
                  }
                  description
                    "This parameter specifies the longitude of the
                     device's position in degrees, multiplied by
                     1 million.  The positive value signifies the
                     direction, east of the prime meridian.  The
                     negative value signifies the direction, west
                     of the prime meridian.
                  
                     Range is from: 180.00.00' West
                     (-180,000,000) to 180.00.00' East
                     (180,000,000).
                  
                     Example: A longitude of 13.19.43' E would be
                     represented as 13,323,833, derived as
                     (13*1,000,000)+((19.43*1,000,000)/60).  A
                     longitude of 50.00'0'' W would be
                     represented as value -50,000,000.
                  
                     If 0 then SIB15 is not detected in the
                     specific cell.";
                }
                leaf UncertaintySemiMajor {
                  type uint32 {
                    range "0..127";
                  }
                  description
                    "The uncertainty r is derived from the
                     \"uncertainty code\" k by
                  
                     r = 10 x ( 1.1 <power> (k-1) )
                  
                     {{bibref|3GPP-TS.23.032|Section6.2}}";
                }
                leaf UncertaintySemiMinor {
                  type uint32 {
                    range "0..127";
                  }
                  description
                    "The uncertainty r is derived from the
                     \"uncertainty code\" k by
                  
                     r = 10 x ( 1.1 <power> (k-1) )
                  
                     {{bibref|3GPP-TS.23.032|Section6.2}}";
                }
                leaf OrientationOfMajorAxis {
                  type uint32 {
                    range "0..89";
                  }
                  description
                    "The Information Element (IE) value 'N' is
                     derived by this formula:
                  
                     2N <= a < 2(N+1)
                  
                     Where 'a' is the orientation in degrees
                     (0..179).";
                }
                leaf Confidence {
                  type uint32 {
                    range "0..100";
                  }
                  description
                    "The degree of confidence in the ellipsoid's
                     points expressed in {{units}}.";
                }
              }
            }
          }
        }

        container GSM {
          description
            "This object contains parameters relating to GSM REM
             capabilities.";
          leaf InServiceHandling {
            type enumeration {
              enum "Immediate";
              enum "Delayed";
            }
            default "Immediate";
            description
              "FAP REM behavior with respect to ongoing active
               connections.";
          }
          leaf ScanOnBoot {
            type boolean;
            default "true";
            description
              "Enables or disables Radio Environment Measurement
               during the FAP start up.";
          }
          leaf ScanPeriodically {
            type boolean;
            default "false";
            description
              "Enable Periodic Radio Environment Measurement on all
               enabled RAT.";
          }
          leaf PeriodicInterval {
            type uint32;
            description
              "When {{param|ScanPeriodically}} is {{true}}, this
               value indicates the interval in {{units}} which
               REM is performed while the FAP service is enabled.";
          }
          leaf PeriodicTime {
            type yang:date-and-time;
            description
              "An absolute time reference in UTC to determine when
               the CPE will initiate the periodic REM.  Each REM
               MUST occur at (or as soon as possible after) this
               reference time plus or minus an integer multiple
               of the {{param|PeriodicInterval}}.
            
               {{param}} is used only to set the \"phase\" of the
               REM.  The actual value of {{param}} can be
               arbitrarily far into the past or future.
            
               For example, if {{param|PeriodicInterval}} is
               86400 (a day) and if {{param}} is set to UTC
               midnight on some day (in the past, present, or
               future) then periodic REMs will occur every day at
               UTC midnight.  These MUST begin on the very next
               midnight, even if {{param}} refers to a day in the
               future.
            
               The Unknown Time value defined in
               {{bibref|TR-106a2|Section 3.2}} indicates that no
               particular time reference is specified.  That is,
               the CPE MAY locally choose the time reference, and
               needs only to adhere to the specified
               PeriodicInformInterval.
            
               If absolute time is not available to the CPE, its
               periodic REM behavior MUST be the same as if
               {{param}} parameter was set to the Unknown Time
               value.";
          }
          leaf REMPLMNList {
            type string {
              length "0..6";
            }
            description
              "{{list}} Each item is a PLMNID.
            
               PLMN ID consists of Mobile Country Code (MCC) and
               Mobile Network Code (MNC)
               {{bibref|3GPP-TS.23.003}},
               {{bibref|3GPP-TS.24.008}}.
            
               Mobile Country Code consists of three digits and
               uniquely identifies the country of domicile of the
               subscriber.
            
               Mobile Network Code consists of two or three
               digits and identifies the Home PLMN within a
               country.
            
               For a 2-digit MNC the total string length of the
               PLMNID is 5.
            
               If {{empty}} no specific PLMN ID is provided,
               meaning that the FAP is required to report all
               available PLMN IDs.
            
               If a list is provided, the FAP is expected to
               limit the REM measurement to the PLMN(s) specified
               in this list only and ignore others even if they
               are detected.";
          }
          leaf REMBandList {
            type enumeration {
              enum "T-GSM380";
              enum "T-GSM410";
              enum "GSM450";
              enum "GSM480";
              enum "GSM710";
              enum "GSM750";
              enum "T-GSM810";
              enum "GSM850";
              enum "P-GSM900";
              enum "E-GSM900";
              enum "R-GSM900";
              enum "T-GSM900";
              enum "DCS1800";
              enum "PCS1900";
            }
            description
              "{{list}} Each item is a GSM Band to measure.
               {{enum}}
            
               If {{empty}} then no specific GSM band is
               provided, meaning that the FAP MUST scan all
               bands.
            
               If a list is provided, the FAP is expected to
               limit the REM measurement to the band(s) specified
               in this list only and ignore others even if they
               are detected.";
          }
          leaf ARFCNList {
            type string;
            description
              "{{list}} Each item is a GSM ARFCN to measure.
            
               If {{empty}} then no specific ARFCN is provided,
               meaning that the FAP is required to scan all
               ARFCNs.
            
               If a list is provided, the FAP is expected to
               limit the REM measurement to the ARFCN(s)
               specified in this list only and ignore others even
               if they are detected.";
          }
          leaf ScanTimeout {
            type uint32;
            description
              "Specifies the time-out value in {{units}}, measured
               from the start of the REM scan, before the REM
               scan will time out.";
          }
          leaf ScanStatus {
            type enumeration {
              enum "Indeterminate";
              enum "InProgress";
              enum "Success";
              enum "Error";
              enum "Error_TIMEOUT";
            }
            config false;
            description
              "Indicates the current status of this scan.";
          }
          leaf ErrorDetails {
            type string {
              length "0..256";
            }
            config false;
            description
              "Provides more detail when the {{param|ScanStatus}} is
               either {{enum|Error|ScanStatus}} or
               {{enum|Error_TIMEOUT|ScanStatus}}.";
          }
          leaf LastScanTime {
            type yang:date-and-time;
            config false;
            description
              "The time of the last GSM radio environment
               measurement.";
          }
          leaf MaxCellEntries {
            type uint32;
            config false;
            description
              "The maximum number of entries allowed in the
               {{object|.REM.UMTS.GSM.Cell.{i}.}} table.";
          }

          list Cell {
            key "ARFCN BSIC";
            config false;
            description
              "Table indicating the components of the discovered
               cells.";
            leaf BandIndicator {
              type enumeration {
                enum "GSM 850";
                enum "GSM 900";
                enum "DCS 1800";
                enum "PCS 1900";
              }
              description
                "Indicates how to interpret the BCCH ARFCN.";
            }
            leaf ARFCN {
              type uint32 {
                range "0..1023";
              }
              description
                "Absolute Radio Frequency Channel Number (ARFCN)
                 {{bibref|3GPP-TS.05.05}}.";
            }
            leaf BSIC {
              type uint32 {
                range "0..63";
              }
              description
                "Base Station Identity Code
                 {{bibref|3GPP-TS.03.03}}.";
            }
            leaf PLMNID {
              type string {
                length "0..6";
              }
              description
                "PLMN ID consists of Mobile Country Code (MCC) and
                 Mobile Network Code (MNC)
                 {{bibref|3GPP-TS.23.003}},
                 {{bibref|3GPP-TS.24.008}}.
              
                 Mobile Country Code consists of three digits and
                 uniquely identifies the country of domicile of
                 the subscriber.
              
                 Mobile Network Code consists of two or three
                 digits and identifies the Home PLMN within a
                 country.
              
                 For a 2-digit MNC the total string length of the
                 PLMNID is 5.";
            }
            leaf LAC {
              type uint32 {
                range "1..65535";
              }
              description
                "Location Area Code (LAC) as defined in SIB1
                 {{bibref|3GPP-TS.25.331}}.  The concatenation of
                 PLMN ID (MCC+MNC) and LAC uniquely identifies
                 the LAI (Location Area ID)
                 {{bibref|3GPP-TS.23.003}}.";
            }
            leaf RAC {
              type uint32 {
                range "min..255";
              }
              description
                "Routing Area Code (RAC) consists of up to 3
                 numerical characters.  The concatenation of PLMN
                 ID (MCC+MNC), LAC, and RAC uniquely identifies
                 the Routing Area ID (RAI).
                 {{bibref|3GPP-TS.23.003|Section 4.2}}
                 {{bibref|3GPP-TS.25.413|Section 9.2.3.7}}";
            }
            leaf CI {
              type uint32 {
                range "min..63535";
              }
              description
                "Cell Identity.  {{bibref|3GPP-TS.25.331|Section
                 10.3.2.2}}";
            }
            leaf RSSI {
              type int32 {
                range "-110..48";
              }
              description
                "Received signal level in {{units}} of the BCCH
                 carrier.";
            }
          }
        }
      }

      container LTE {
        description
          "This object contains parameters relating to radio
           environment measurement capabilities for the LTE
           system.";
        leaf InServiceHandling {
          type enumeration {
            enum "Immediate";
            enum "Delayed";
          }
          default "Immediate";
          description
            "FAP REM behavior with respect to ongoing active
             connections.";
        }
        leaf ScanOnBoot {
          type boolean;
          default "true";
          description
            "Enables or disables Radio Environment Measurement
             during the FAP start up.";
        }
        leaf ScanPeriodically {
          type boolean;
          default "false";
          description
            "Enable Periodic Radio Environment Measurement on LTE
             EUTRAN bands.";
        }
        leaf PeriodicInterval {
          type uint32;
          description
            "When {{param|ScanPeriodically}} is {{true}}, this value
             indicates the interval in {{units}} which REM is
             performed while the FAP service is enabled.";
        }
        leaf PeriodicTime {
          type yang:date-and-time;
          description
            "An absolute time reference in UTC to determine when the
             CPE will initiate the periodic REM.  Each REM MUST
             occur at (or as soon as possible after) this
             reference time plus or minus an integer multiple of
             the {{param|PeriodicInterval}}.
          
             {{param}} is used only to set the \"phase\" of the
             REM.  The actual value of {{param}} can be
             arbitrarily far into the past or future.
          
             For example, if {{param|PeriodicInterval}} is 86400
             (a day) and if {{param}} is set to UTC midnight on
             some day (in the past, present, or future) then
             periodic REMs will occur every day at UTC midnight.
             These MUST begin on the very next midnight, even if
             {{param}} refers to a day in the future.
          
             The Unknown Time value defined in
             {{bibref|TR-106a2|Section 3.2}} indicates that no
             particular time reference is specified.  That is,
             the CPE MAY locally choose the time reference, and
             needs only to adhere to the specified
             PeriodicInformInterval.
          
             If absolute time is not available to the CPE, its
             periodic REM behavior MUST be the same as if
             {{param}} parameter was set to the Unknown Time
             value.";
        }
        leaf REMPLMNList {
          type string;
          description
            "{{list}} Each item is a PLMN ID to measure.  PLMN ID
             consists of Mobile Country Code (MCC) and Mobile
             Network Code (MNC) {{bibref|3GPP-TS.23.003}},
             {{bibref|3GPP-TS.24.008}}.
          
             If {{empty}}, then no specific PLMN ID is provided,
             meaning that the FAP is required to scan all
             available PLMN IDs.";
        }
        leaf REMBandList {
          type string {
            length "0..64";
          }
          description
            "{{list}} Each item is a LTE Band to measure.
             Corresponds to frequency band indicator defined in
             {{bibref|3GPP-TS.36.101|Table 5.5-1}}.
          
             If {{empty}} then no specific LTE band is provided,
             meaning that the FAP is required to scan all
             available bands.
          
             The order of the band indicator has no significance.";
        }
        leaf EUTRACarrierARFCNDLList {
          type string;
          description
            "{{list}} Each entry is a EUTRA ARFCN in the DL
             direction to measure.  Corrsponds to the parameter
             NDL in {{bibref|3GPP-TS.36.101|Section 5.7.3}}.
          
             If {{empty}}, then no specific EUTRA ARFCN is
             provided, meaning that the FAP is required to scan
             all ARFCNs that it is aware of.";
        }
        leaf ScanTimeout {
          type uint32;
          description
            "Specifies the time-out value in {{units}}, measured
             from the start of the REM scan, before the REM scan
             will time out.";
        }
        leaf ScanStatus {
          type enumeration {
            enum "Indeterminate";
            enum "InProgress";
            enum "Success";
            enum "Error";
            enum "Error_TIMEOUT";
          }
          config false;
          description
            "Indicates the current status of this scan.";
        }
        leaf ErrorDetails {
          type string {
            length "0..256";
          }
          config false;
          description
            "Provides more detail when the {{param|ScanStatus}} is
             either {{enum|Error|ScanStatus}} or
             {{enum|Error_TIMEOUT|ScanStatus}}.";
        }
        leaf LastScanTime {
          type yang:date-and-time;
          config false;
          description
            "The time of the last LTE system radio environment
             measurement.";
        }
        leaf MaxCellEntries {
          type uint32;
          config false;
          description
            "The maximum number of entries available in the
             {{object|.REM.LTE.Cell.{i}.}} table.";
        }
        leaf MaxCarrierMeasEntries {
          type uint32;
          config false;
          description
            "The maximum number of entries available in the
             {{object|.REM.LTE.CarrierMeas.{i}.}} table.";
        }

        list Cell {
          config false;
          description
            "Table indicating the components of the discovered
             cells.";

          container RF {
            description
              "Table indicating the RF aspect of the discovered
               cells.";
            leaf EUTRACarrierARFCN {
              type uint32 {
                range "0..65535";
              }
              description
                "Indicates the ARFCN of this carrier frequency.
                 Corresponds to parameter dl-CarrierFreq in SIB5
                 in {{bibref|3GPP-TS.36.331|Section 6.3.1}}, and
                 parameter NDL in {{bibref|3GPP-TS.36.101|Section
                 5.7.3}}.";
            }
            leaf PhyCellID {
              type uint32 {
                range "0..503";
              }
              description
                "Physical cell ID of the detected EUTRAN cell, as
                 specified in {{bibref|3GPP-TS.36.101|Section
                 5.6}}.";
            }
            leaf RSRP {
              type int32 {
                range "-140..-44";
              }
              description
                "Received RSRP level of the detected EUTRA cell,
                 specified in {{units}}, as specified in
                 {{bibref|3GPP-TS.36.214|Section 5.1.1}}.  The
                 reporting range is specified in
                 {{bibref|3GPP-TS.36.133|Section 9.1.4}}.";
            }
            leaf RSRQ {
              type int32 {
                range "-240..0";
              }
              description
                "Received RSRQ level of the detected EUTRA cell,
                 specified in {{units}}, as specified in
                 {{bibref|3GPP-TS.36.214|Section 5.1.3}}.  Actual
                 measured values range between -24.0 {{units}}
                 and 0.0 {{units}} in steps of 0.5 {{units}}.
                 The value of {{param}} divided by 10 yields the
                 actual measured value.  Only values in multiple
                 of 5 are valid.";
            }
            leaf RSSI {
              type int32 {
                range "-110..-19";
              }
              description
                "E-UTRA Carrier Received Signal Strength Indicator
                 (RSSI), specified in {{units}}, as specified in
                 {{bibref|3GPP-TS.36.214|Section 5.1.3}}.  It
                 comprises the linear average of the total
                 received power (in [W]) observed only in OFDM
                 symbols containing reference symbols for antenna
                 port 0, in the measurement bandwidth, over N
                 number of resource blocks by the UE from all
                 sources, including co-channel serving and
                 non-serving cells, adjacent channel
                 interference, thermal noise etc.";
            }
          }

          container BCCH {
            description
              "Table containing the system information broadcast in
               the BCCH logical channel.";
            leaf DLBandwidth {
              type uint32 {
                range "6 | 15 | 25 | 50 | 75 | 100";
              }
              description
                "Downlink transmission bandwidth, specified in
                 number of {{units}}.  Corresponds to parameter
                 dl_Bandwidth in Master Information Block in
                 {{bibref|3GPP-TS.36.331|Section 6.2.2}}.  and to
                 parameter NRB in {{bibref|3GPP-TS.36.101|Table
                 5.6-1}}.";
            }
            leaf ULBandwidth {
              type uint32 {
                range "6 | 15 | 25 | 50 | 75 | 100";
              }
              description
                "Uplink transmission bandwidth, specified in number
                 of {{units}}.  Corresponds to parameter
                 ul_Bandwidth in SIB2 in
                 {{bibref|3GPP-TS.36.331|Section 6.3.1}}.  and to
                 parameter NRB in {{bibref|3GPP-TS.36.101|Table
                 5.6-1}}.";
            }
            leaf RSTxPower {
              type int32 {
                range "-60..50";
              }
              description
                "The downlink reference-signal transmit power,
                 specified in {{units}}.  Defined as the linear
                 average over the power contributions (in W) of
                 all resource elements that carry cell-specific
                 reference signals within the operating system
                 bandwidth.  Corresponds to parameter
                 referenceSignalPower in SIB4 as a part of
                 PDSCH-Config IE in
                 {{bibref|3GPP-TS.36.331|Section 6.3.2}}.";
            }
            leaf TAC {
              type uint32 {
                range "min..65535";
              }
              description
                "Tracking Area Code that is common for all the PLMNs
                 listed.  Corresponds to trackingAreaCode as
                 specified in SIB1 in
                 {{bibref|3GPP-TS.36.331|Section 6.2.2}}.";
            }
            leaf CellID {
              type uint32 {
                range "min..268435455";
              }
              description
                "Defines the cell identify, defines as a 28-bit
                 binary number.  Corresponds to cellIdentity as
                 specified in SIB1 in
                 {{bibref|3GPP-TS.36.331|Section 6.2.2 and
                 Section 6.3.4}}.";
            }
            leaf CellBarred {
              type boolean;
              description
                "Indicates whether the cell is barred or not.  If
                 {{true}}, the cell is barred.  If {{false}}, the
                 cell is not barred.  Corresponds to cellBarred
                 as specified in SIB1 in
                 {{bibref|3GPP-TS.36.331|Section 6.2.2}} and
                 {{bibref|3GPP-TS.36.304}}.";
            }
            leaf CSGIndication {
              type boolean;
              description
                "Indicates whether CSG is used in this cell or not.
                 If {{true}}, the UE is only allowed to access
                 the cell if the CSG identity matches an entry in
                 the allowed CSG list that the UE has stored.
                 Corresponds to csg-Indication as specified in
                 SIB1 in {{bibref|3GPP-TS.36.331|Section 6.2.2}}.";
            }
            leaf CSGIdentity {
              type uint32 {
                range "0..134217727";
              }
              description
                "Defines the CSG ID value if {{param|CSGIndication}}
                 parameter indicates that CSG is used in this
                 cell.  Corresponds to csg-Identity as specified
                 in SIB1 in {{bibref|3GPP-TS.36.331|Section
                 6.2.2}}.";
            }
            leaf MaxPLMNListEntries {
              type uint32;
              description
                "The maximum number of entries available in the
                 {{object|.REM.LTE.Cell.{i}.BCCH.PLMNList.{i}.}}
                 table.";
            }

            list PLMNList {
              key "PLMNID";
              description
                "Table containing the PLMN list in the system
                 information broadcast in the BCCH logical
                 channel.  Correspnds to plmn-IdentityList as
                 specified in SIB1 in
                 {{bibref|3GPP-TS.36.331|Section 6.2.2}}.  Each
                 instance in this object is a PLMN-IdentityInfo
                 which consists of plmn-Identity and
                 cellReservedForOperatorUse IEs.";
              leaf PLMNID {
                type string {
                  length "0..6";
                }
                description
                  "PLMN ID consists of Mobile Country Code (MCC) and
                   Mobile Network Code (MNC)
                   {{bibref|3GPP-TS.23.003}},
                   {{bibref|3GPP-TS.24.008}}.
                
                   Mobile Country Code consists of three digits
                   and uniquely identifies the country of
                   domicile of the subscriber.  Mobile Network
                   Code consists of two or three digits and
                   identifies the Home PLMN within a country.
                   For a 2-digit MNC the total string length of
                   {{param}} is 5.";
              }
              leaf CellReservedForOperatorUse {
                type boolean;
                description
                  "Indicates whether the cell is reserved for
                   operator use or not.  If {{true}}, it is
                   reserved.  If {{false}}, it is not reserved.
                   Corresponds to \"reserved\" \"notReserved\"
                   respectively as defined in PLMN-IdentityInfo
                   in {{bibref|3GPP-TS.36.331|Section 6.2.2}}.";
              }
            }
          }
        }

        list CarrierMeas {
          key "CarrierARFCNDL CarrierChWidth";
          description
            "Table indicating the measurement of the discovered
             carrier.  The information stored in this object is
             strictly in the physical layer level and may not
             necessarily be associated with any particular
             E-UTRAN cell (e.g.  interference level generated by
             sources other than E-UTRAN cell).";
          leaf Enable {
            type boolean;
            default "false";
            description
              "Enables or disables the CarrierMeas entry.";
          }
          leaf CarrierARFCNDL {
            type int32 {
              range "min..65535";
            }
            description
              "Lower bound of the EUTRA ARFCN as specified in
               {{bibref|3GPP-TS.36.101|Section 5.7.3}} in the DL
               direction that is requested to measure.  Unit in
               {{units}}.";
          }
          leaf CarrierChWidth {
            type int32 {
              range "min..750";
            }
            description
              "Number of {{units}} in DL direction, as specified in
               {{bibref|3GPP-TS.36.101|Section 5.6}}, that is
               requested to measure.  The range bounded by
               {{param|CarrierARFCNDL}} as the lower bound and
               the value of ({{param|CarrierARFCNDL}} +
               {{param}}) as the upper bound expresses the total
               carrier frequency range to be measured.";
          }
          leaf CarrierRSSI {
            type int32 {
              range "-100..-25";
            }
            config false;
            description
              "Received Signal Strength Indicator (RSSI) as
               specified in {{bibref|3GPP-TS.36.214|Sec 5.1.3}}
               over the carrier frequency range from
               {{param|CarrierARFCNDL}} as the lower bound and
               the value of ({{param|CarrierARFCNDL}} +
               {{param|CarrierChWidth}}) as the upper bound.";
          }
        }
      }

      container CDMA2000 {
        description
          "This object contains parameters relating to radio
           environment measurement capabilities for the CDMA2000
           system.";
        leaf InServiceHandling {
          type enumeration {
            enum "Immediate";
            enum "Delayed";
          }
          description
            "FAP REM behavior with respect to ongoing active
             connections.  {{enum}}";
        }
        leaf ScanOnBoot {
          type boolean;
          description
            "Enables or disables Radio Environment Measurement
             during the FAP start up.";
        }
        leaf ScanNow {
          type boolean;
          description
            "Directs FAP to perform radio environment measurements
             immediately (but respecting the setting of
             {{param|InServiceHandling}}) and report back.  After
             performing the action, the FAP resets the ScanNow
             value to \"0\" ({{false}}).";
        }
        leaf ReturnTimer {
          type uint32 {
            range "1..max";
          }
          description
            "Time in {{units}} within which the action should be
             performed by the FAP.  Only applies if
             {{param|InServiceHandling}} is set to Delayed.";
        }
        leaf ScanPeriodically {
          type boolean;
          description
            "Enables periodic reporting of radio environment
             measurements.";
        }
        leaf PeriodicInterval {
          type uint32 {
            range "1..max";
          }
          description
            "When {{param|ScanPeriodically}} is {{true}}, this value
             indicates the interval in {{units}} which REM is
             performed while the FAP service is enabled.";
        }
        leaf PeriodicTime {
          type yang:date-and-time;
          description
            "An absolute time reference in UTC to determine when the
             CPE will initiate the periodic REM.  Each REM MUST
             occur at (or as soon as possible after) this
             reference time plus or minus an integer multiple of
             the {{param|PeriodicInterval}}.
          
             {{param}} is used only to set the \"phase\" of the
             REM.  The actual value of {{param}} can be
             arbitrarily far into the past or future.
          
             For example, if {{param|PeriodicInterval}} is 86400
             (a day) and if {{param}} is set to UTC midnight on
             some day (in the past, present, or future) then
             periodic REMs will occur every day at UTC midnight.
             These MUST begin on the very next midnight, even if
             {{param}} refers to a day in the future.
          
             The Unknown Time value defined in
             {{bibref|TR-106a2|Section 3.2}} indicates that no
             particular time reference is specified.  That is,
             the CPE MAY locally choose the time reference, and
             needs only to adhere to the specified
             PeriodicInformInterval.
          
             If absolute time is not available to the CPE, its
             periodic REM behavior MUST be the same as if
             {{param}} parameter was set to the Unknown Time
             value.";
        }
        leaf ReportOverheads {
          type enumeration {
            enum "All";
            enum "OneX";
            enum "HRPD";
            enum "None";
          }
          description
            "If {{param}} is set to {{enum|All}}, the FAP shall
             report the overheads from the sectors as well.";
        }
        leaf ScanTimeout {
          type uint32;
          description
            "Specifies the time-out value in {{units}}, measured
             from the start of the REM scan, before the REM scan
             will time out.";
        }
        leaf ScanStatus {
          type enumeration {
            enum "Indeterminate";
            enum "InProgress";
            enum "Success";
            enum "Error";
            enum "Error_TIMEOUT";
          }
          config false;
          description
            "Indicates the current status of this scan.";
        }
        leaf ErrorDetails {
          type string {
            length "0..256";
          }
          config false;
          description
            "Provides more detail when the {{param|ScanStatus}} is
             either \"Error\" or \"Error_TIMEOUT\".";
        }
        leaf LastScanTime {
          type yang:date-and-time;
          config false;
          description
            "The time of the last system radio environment
             measurement.";
        }

        container OneX {
          description
            "This object contains parameters relating to radio
             environment measurement capabilities for the 1x
             system.";
          leaf MaxCellEntries {
            type uint32;
            config false;
            description
              "The maximum number of entries available in the
               {{object|.REM.CDMA2000.OneX.Cell.{i}.}} table.";
          }
          leaf MaxChannelEntries {
            type uint32;
            config false;
            description
              "The maximum number of entries available in the
               {{object|.REM.CDMA2000.OneX.Channel.{i}.}} table.";
          }

          list Channel {
            key "SniffingBandClass SniffingChannelNumber PNList";
            description
              "REM specific configuration and reporting.";
            leaf Enable {
              type boolean;
              default "false";
              description
                "Enables or disables the {{object}} entry.";
            }
            leaf SniffingBandClass {
              type uint32 {
                range "0..31";
              }
              default "0";
              description
                "Config parameter to set band class.  Reference -
                 {{bibref|3GPP2-C.S0057}}, Band Class
                 Specification for CDMA2000 Spread Spectrum
                 Systems.";
            }
            leaf SniffingChannelNumber {
              type uint32 {
                range "0..2016";
              }
              default "0";
              description
                "The Radio Frequency Channel Number (RFCN) in the
                 forward direction.";
            }
            leaf PNList {
              type string {
                length "0..256";
              }
              default "";
              description
                "{{list}} Each item is a (single value) PN offset in
                 units of 64 PN chips or PNrange expressed in the
                 following format:
                 <Start-value>\"..\"<End-value>:<Increment> If an
                 empty string, then no specific PNList is
                 provided, meaning that the FAP is required to
                 pick a PN list to scan on its own.";
            }
          }

          list Cell {
            config false;
            description
              "Table indicating the components of the discovered
               cells.";

            container RF {
              description
                "RF REM results for each detected cell.";
              leaf Band {
                type int32;
                description
                  "CDMA band for the reported cell.";
              }
              leaf RFCNFL {
                type uint32 {
                  range "0..2016";
                }
                description
                  "The Radio Frequency Channel Number (RFCN) in the
                   FL direction for the reported cell.";
              }
              leaf Io {
                type int32 {
                  range "-105..-25";
                }
                description
                  "The total received power spectral density in
                   {{units}}, including signal and interference.";
              }
              leaf PIlotPN {
                type uint32 {
                  range "0..511";
                }
                description
                  "Pilot PN Offset (in units of {{units}}).";
              }
              leaf PIlotPNPhase {
                type uint32;
                description
                  "Pilot PN phase in {{units}}.";
              }
              leaf PilotStrengthEcp {
                type int32 {
                  range "-130..-25";
                }
                description
                  "The strength estimate of the received pilot
                   energy per chip, Ecp, in {{units}}.";
              }
              leaf PilotStrengthEcpIo {
                type int32 {
                  range "-25..0";
                }
                description
                  "The strength estimate of the received pilot
                   energy per chip, Ecp, to total received
                   spectral density, Io (signal and noise) in
                   {{units}}.";
              }
              leaf OverheadsAvailable {
                type boolean;
                description
                  "If set to {{true}}, the overhead messages for
                   this particular cell is included in
                   {{object|.REM.CDMA2000.OneX.Cell.{i}.ControlChannel.}}.";
              }
            }

            container ControlChannel {
              description
                "Table containing information broadcast on control
                 channel.";
              leaf SID {
                type int32;
                description
                  "System identification.  Refer to
                   {{bibref|3GPP2-C.S0005}}.";
              }
              leaf NID {
                type int32;
                description
                  "Network identification.  Refer to
                   {{bibref|3GPP2-C.S0005}}.";
              }
              leaf REGZONE {
                type int32;
                description
                  "Registration Zone.  Refer to
                   {{bibref|3GPP2-C.S0005}}.";
              }
              leaf BASELAT {
                type int32 {
                  range "-2147483648..2147483647";
                }
                description
                  "Basestation latitude.  Refer to
                   {{bibref|3GPP2-C.S0005}}.";
              }
              leaf BASELONG {
                type int32 {
                  range "-2147483648..2147483647";
                }
                description
                  "Basestation longtitude.  Refer to
                   {{bibref|3GPP2-C.S0005}}.";
              }
              leaf MCC {
                type int32;
                description
                  "Mobile Country Code.  Refer to
                   {{bibref|3GPP2-C.S0005}}.";
              }
              leaf MNCIMSI1112 {
                type int32;
                description
                  "the 11th and 12th digits of IMSI, i.e., Mobile
                   Network Code.  Refer to
                   {{bibref|3GPP2-C.S0005}}.";
              }
              leaf BASEID {
                type int32;
                description
                  "Basestation identification.  Refer to
                   {{bibref|3GPP2-C.S0005}}.";
              }
              leaf APID {
                type string {
                  length "0..32";
                }
                description
                  "Access Point Identification.  Set to empty string
                   if not available.  Refer to
                   {{bibref|3GPP2-C.S0005}}.";
              }
              leaf APIDMASK {
                type int32;
                description
                  "Access Point Identification Mask.  Set to zero if
                   not available.  Refer to
                   {{bibref|3GPP2-C.S0005}}.";
              }
              leaf APIDTEXT {
                type string {
                  length "0..256";
                }
                description
                  "Access Point Identification Text.  Set to empty
                   string if not available.  Refer to
                   {{bibref|3GPP2-C.S0005}}.";
              }
            }
          }
        }

        container HRPD {
          description
            "This object contains parameters relating to radio
             environment measurement capabilities for the HRPD
             system.";
          leaf MaxCellEntries {
            type uint32;
            config false;
            description
              "The maximum number of entries available in the
               {{object|.REM.CDMA2000.HRPD.Cell.{i}.}} table.";
          }
          leaf MaxChannelEntries {
            type uint32;
            config false;
            description
              "The maximum number of entries in
               {{object|.REM.CDMA2000.HRPD.Channel.{i}.}} table.";
          }

          list Channel {
            key "SniffingBandClass SniffingChannelNumber PNList";
            description
              "REM specific configuration and reporting.";
            leaf Enable {
              type boolean;
              default "false";
              description
                "Enables or disables the {{object}} entry.";
            }
            leaf SniffingBandClass {
              type uint32 {
                range "0..31";
              }
              default "0";
              description
                "Config parameter to set band class.  Reference -
                 {{bibref|3GPP2-C.S0057}}, Band Class
                 Specification for CDMA2000 Spread Spectrum
                 Systems.";
            }
            leaf SniffingChannelNumber {
              type uint32 {
                range "0..2016";
              }
              default "0";
              description
                "The Radio Frequency Channel Number (RFCN) in the FL
                 direction.";
            }
            leaf PNList {
              type string {
                length "0..256";
              }
              default "";
              description
                "{{list}} Each item is a (single value) PN offset in
                 units of 64 PN chips or PNrange expressed in the
                 following format:
                 <Start-value>\"..\"<End-value>:<Increment>.  If
                 an empty string, then no specific PNList is
                 provided, meaning that the FAP is required to
                 pick a PN list to scan on its own.";
            }
          }

          list Cell {
            config false;
            description
              "Table indicating the components of the discovered
               cells.";

            container RF {
              description
                "RF REM results for each detected cell.";
              leaf Band {
                type int32;
                description
                  "CDMA band for the reported cell.";
              }
              leaf RFCNFL {
                type uint32 {
                  range "0..2016";
                }
                description
                  "The Radio Frequency Channel Number (RFCN) in the
                   FL direction for the reported cell.";
              }
              leaf Io {
                type int32 {
                  range "-105..-25";
                }
                description
                  "The total received power spectral density in
                   {{units}}, including signal and interference.";
              }
              leaf PIlotPN {
                type uint32 {
                  range "0..511";
                }
                description
                  "Pilot PN Offset (in units of {{units}}).";
              }
              leaf PIlotPNPhase {
                type uint32;
                description
                  "Pilot PN phase in {{units}}.";
              }
              leaf PilotStrengthEcp {
                type int32 {
                  range "-130..-25";
                }
                description
                  "The strength estimate of the received pilot
                   energy per chip in {{units}}.";
              }
              leaf PilotStrengthEcpIo {
                type int32 {
                  range "-25..0";
                }
                description
                  "The strength estimate of the received pilot
                   energy per chip, Ecp, to total received
                   spectral density, Io (signal and noise) in
                   {{units}}.";
              }
              leaf OverheadsAvailable {
                type boolean;
                description
                  "If set to {{true}}, the overhead messages for
                   this particular cell is included in
                   {{object|.REM.CDMA2000.HRPD.Cell.{i}.ControlChannel.}}.";
              }
            }

            container ControlChannel {
              description
                "Table containing information braodcast on control
                 channel.";
              leaf ColorCode {
                type int32;
                description
                  "The color code of the measured sector as defined
                   in {{bibref|3GPP2-C.S0024}}.";
              }
              leaf SectorID {
                type yang:hex-string {
                  length "16";
                }
                description
                  "The sector ID of the measured sector as defined
                   in {{bibref|3GPP2-C.S0024}}.";
              }
              leaf SubnetMask {
                type int32 {
                  range "0..104";
                }
                description
                  "The length of the subnet mask in {{units}} for
                   the measured sector as defined in
                   {{bibref|3GPP2-C.S0024}}.";
              }
              leaf CountryCode {
                type int32;
                description
                  "The country code of the measured sector as
                   defined in {{bibref|3GPP2-C.S0024}}.";
              }
              leaf Latitude {
                type int32 {
                  range "-1296000..1296000";
                }
                description
                  "The reported lattitude of the cell in units of
                   {{units}}, expressed as a two's complement
                   signed number with positive numbers signifying
                   North latitudes in the range -1296000 to
                   1296000 inclusive corresponding to a range of
                   -90 to +90) Refer to {{bibref|3GPP2-C.S0024}}.";
              }
              leaf Longitude {
                type int32 {
                  range "-2592000..2592000";
                }
                description
                  "The reported longitude of the cell in units of
                   {{units}}, expressed as a two's complement
                   signed number with positive numbers signifying
                   East longitude in the range -2592000 to
                   2592000 inclusive (corresponding to a range of
                   -180 to +180).  Refer to
                   {{bibref|3GPP2-C.S0024}}.";
              }
            }
          }
        }

        container MacroTiming {
          description
            "Parameters for controlling CDMA2000 system timing
             derived from macro system sniffing.";
          leaf AdminState {
            type uint32 {
              range "0..1";
            }
            description
              "This is the Admin State of Macro Timing.  Lock means
               MacroTiming feature is Enabled.  Unlock means
               MacroTiming feature is disabled.  0 - Lock
               (Enabled), 1 - Unlock (Disabled).";
          }
          leaf TrackingChannelNumber {
            type uint32;
            config false;
            description
              "Channel number of Macro Base Station currently used
               for MacroTiming.";
          }
          leaf TrackingBandClass {
            type uint32 {
              range "0..31";
            }
            config false;
            description
              "BandClass of Macro Base Station currently used for
               MacroTiming.";
          }
          leaf TrackingPNOffset {
            type string {
              length "0..256";
            }
            config false;
            description
              "{{list}} Each item is a (single value) PN offset in
               units of 64 PN chips of a Macro Base Station
               currently used for MacroTiming.";
          }
          leaf TimingSource {
            type uint32 {
              range "0..1";
            }
            config false;
            description
              "This parameter indicates the timing source for the
               FAP:
            
               0 - GPS
            
               1 - Macro Timing
            
               The other read-only parameters in this object only
               have valid values when timingsource is set to 1.";
          }

          list Channel {
            key "BandClass ChannelNumber";
            description
              "Object used to configure list of channels to be used
               for Macto Timing.";
            leaf Enable {
              type boolean;
              default "false";
              description
                "Enables or disables the {{object}} entry.";
            }
            leaf AirInterfaceType {
              type uint32 {
                range "0..1";
              }
              default "0";
              description
                "Air interface type of the configured Band class and
                 Channel.  0 - 1x, 1 - HRPD.";
            }
            leaf BandClass {
              type uint32 {
                range "0..31";
              }
              default "0";
              description
                "Bandclass of the Macro timing channel.";
            }
            leaf ChannelNumber {
              type uint32;
              default "0";
              description
                "Macro timing acquisition channel.";
            }
            leaf Priority {
              type uint32;
              default "0";
              description
                "Priority of the channle to use for acquisition.
                 FAP should prioritize lower values over higher.";
            }
            leaf PNList {
              type string {
                length "0..256";
              }
              default "";
              description
                "{{list}} Each item is a (single value) PN offset in
                 units of 64 PN chips or PNrange expressed in the
                 following format:
              
                 <Start-value>\"..\"<End-value>:<Increment>
              
                 If an empty string, then no specific PNList is
                 provided, meaning that the FAP is required to
                 pick a PN list to scan on its own.";
            }
          }
        }
      }
    }

    container Transport {
      description
        "This object contains parameters relating to the transport.";

      container SIP {
        description
          "This object contains parameters relating to SIP as a
           transport protocol.
        
           SIP is defined in {{bibref|RFC3261}}.";
        leaf Enable {
          type boolean;
          description
            "Enables or disables the whole SIP object and allows the
             setup or release of SIP associations and their
             related streams.";
        }

        container FCS {
          description
            "This object models SIP Femtocell Convergence Server
             (FCS) parameters.";
          leaf FCSURI {
            type string {
              length "0..256";
            }
            description
              "The request URI for MESSAGE method sent to Femtocell
               Convergence Server (FCS).  The string MUST contain
               a URI as defined in {{bibref|RFC3986}}.
            
               The device MUST support SIP URI and MAY support
               other URI schemes.";
          }
          leaf OutGoingProxyURI {
            type string {
              length "0..256";
            }
            description
              "The request URI for Outgoing Proxy.  The string MUST
               contain a URI as defined in {{bibref|RFC3986}}.
            
               The device MUST support SIP URI and MAY support
               other URI schemes.";
          }
          leaf PAccessNetInfoHeader {
            type string {
              length "0..256";
            }
            config false;
            description
              "This string will be populated as the value for
               P-Access-Network-Info header.
            
               This header is generated by the device.  See
               {{bibref|3GPP2-X.S0059}} and {{bibref|RFC3455}}.";
          }
          leaf Realm {
            type string {
              length "0..64";
            }
            description
              "The FQDN or IP Address representing the Home Domain
               of the device.
            
               The request URI for REGISTER will be formed by
               prefixing \"sip:\" to this value.";
          }
          leaf IMPU {
            type string {
              length "0..256";
            }
            description
              "The \"IP Multimedia Public User\" (IMPU) Identity.";
          }
          leaf IMPI {
            type string {
              length "0..256";
            }
            description
              "The \"IP Multimedia Private Identity\" (IMPI).
            
               This value is ignored when {{param|SIPAuthMethod}}
               is set to {{enum|TNA|SIPAuthMethod}}.";
          }
          leaf SIPPassword {
            type string {
              length "0..32";
            }
            description
              "Password to Authenticate the IMS core.
            
               This value is ignored when {{param|SIPAuthMethod}}
               is set to {{enum|TNA|SIPAuthMethod}}.";
          }
          leaf SIPAuthCapability {
            type enumeration {
              enum "TNA";
              enum "SIPDigest";
            }
            config false;
            description
              "Represents the SIP authentication mechanisms
               supported by this device.";
          }
          leaf SIPAuthMethod {
            type string {
              length "0..256";
            }
            description
              "Represents the authentication method used by this
               device for SIP registration.
            
               If value is {{enum|SIPDigest}}, the
               {{param|SIPPassword}} MUST not be {{empty}}.
            
               If value is {{enum|TNA}}, {{param|SIPPassword}}
               and {{param|IMPI}} are ignored.";
          }
          leaf SIPLocalPort {
            type uint32 {
              range "min..65535";
            }
            description
              "Local port number for initiating SIP traffic.";
          }
          leaf RTPPortLowLimit {
            type uint32 {
              range "min..65535";
            }
            description
              "The low limit of port number for originating and
               receiving RTP/RTCP traffic.";
          }
          leaf RTPPortHighLimit {
            type uint32 {
              range "min..65535";
            }
            description
              "The high limit of port number for originating and
               receiving RTP/RTCP traffic.";
          }
          leaf SIPRegExpiry {
            type uint32;
            description
              "SIP registration expiry value, as defined in
               {{bibref|RFC3261}}.";
          }
          leaf SIPSessionExpiry {
            type uint32 {
              range "90..max";
            }
            default "1800";
            description
              "SIP session timer expiry value, in {{units}}, as
               defined in {{bibref|RFC4028}}.";
          }
          leaf EmergencyNumbersList {
            type string {
              length "0..64";
            }
            description
              "Indicates the dialed digit pattern matching strings
               used to determine if the call is an emergency call
               that MAY bypass access control and receive
               priority treatment.";
          }
          leaf TimerT1 {
            type uint32 {
              range "1..max";
            }
            description
              "Value of SIP timer T1, in {{units}}, as defined in
               {{bibref|RFC3261}}.";
          }
          leaf TimerT2 {
            type uint32 {
              range "1..max";
            }
            description
              "Value of SIP timer T2, in {{units}}, as defined in
               {{bibref|RFC3261}}.";
          }
          leaf TimerT4 {
            type uint32 {
              range "1..max";
            }
            description
              "Value of SIP timer T4, in {{units}}, as defined in
               {{bibref|RFC3261}}.";
          }
          leaf T3210 {
            type uint32 {
              range "1..20";
            }
            description
              "This value specifies how much time to wait, in
               {{units}}, before time out on location update
               accept/reject.  See {{bibref|3GPP2-A.S0014}}.";
          }
        }
      }

      container SCTP {
        description
          "This object contains parameters relating to SCTP as a
           transport protocol.
        
           SCTP is defined in {{bibref|RFC4960}} and
           {{bibref|RFC3873}}.";
        leaf Enable {
          type boolean;
          description
            "Enables or disables the whole SCTP object and allows
             the setup or release of SCTP associations and their
             related streams.";
        }
        leaf HBInterval {
          type uint32 {
            range "1..max";
          }
          default "30";
          description
            "Heartbeat interval in {{units}}.";
        }
        leaf MaxAssociationRetransmits {
          type uint32;
          default "10";
          description
            "Maximum number of consecutive retransmissions to a peer
             before an endpoint considers that the peer is
             unreachable and closes the association.";
        }
        leaf MaxInitRetransmits {
          type uint32;
          default "8";
          description
            "Number of retransmission per connection-attempt.";
        }
        leaf MaxPathRetransmits {
          type uint32;
          default "5";
          description
            "Maximum retransmission per destination address.";
        }
        leaf RTOInitial {
          type uint32;
          default "3000";
          description
            "Initial value for Retransmit timeout in {{units}}.  A
             retransmission time value of zero means immediate
             retransmission.";
        }
        leaf RTOMax {
          type uint32;
          default "6000";
          description
            "Maximum value for Retransmit timeout in {{units}}.  A
             retransmission time value of zero means immediate
             retransmission.";
        }
        leaf RTOMin {
          type uint32;
          default "1000";
          description
            "Minimum value for Retransmit timeout in {{units}}.  A
             retransmission time value of zero means immediate
             retransmission.
          
             The value of this parameter MUST be lower than or
             equal to {{param|RTOMax}}.";
        }
        leaf ValCookieLife {
          type uint32;
          default "60000";
          description
            "Valid cookie life in the 4-way start-up handshake
             procedure in {{units}}.";
        }
        leaf OutOfBlues {
          type uint32;
          config false;
          description
            "The number of correctly formed SCTP packets, including
             the proper checksum, but for which the receiver was
             unable to identify an appropriate association.";
        }
        leaf ChecksumErrors {
          type uint32;
          config false;
          description
            "The number of SCTP packets received with an invalid
             checksum.";
        }
        leaf OutCtrlChunks {
          type uint32;
          config false;
          description
            "The number of SCTP control chunks sent (retransmissions
             are not included).";
        }
        leaf OutOrderChunks {
          type uint32;
          config false;
          description
            "The number of SCTP ordered data chunks sent
             (retransmissions are not included).";
        }
        leaf OutUnorderChunks {
          type uint32;
          config false;
          description
            "The number of SCTP unordered chunks (data chunks in
             which the U bit is set to 1) sent (retransmissions
             are not included).";
        }
        leaf InCtrlChunks {
          type uint32;
          config false;
          description
            "The number of SCTP control chunks received (no
             duplicate chunks included).";
        }
        leaf InOrderChunks {
          type uint32;
          config false;
          description
            "The number of SCTP ordered data chunks received (no
             duplicate chunks included).";
        }
        leaf InUnorderChunks {
          type uint32;
          config false;
          description
            "The number of SCTP unordered chunks (data chunks in
             which the U bit is set to 1) received (no duplicate
             chunks included).";
        }
        leaf FragUsrMsgs {
          type uint32;
          config false;
          description
            "The number of user messages that have been sent
             fragmented.";
        }
        leaf ReasmUsrMsgs {
          type uint32;
          config false;
          description
            "The number of user messages that have been received
             fragmented and submitted to the reassembly process.";
        }
        leaf OutSCTPPacks {
          type uint32;
          config false;
          description
            "The number of SCTP packets sent.  Retransmitted DATA
             chunks are included.";
        }
        leaf InSCTPPacks {
          type uint32;
          config false;
          description
            "The number of SCTP packets received.  Duplicates are
             included.";
        }
        leaf Discontinuity {
          type yang:date-and-time;
          config false;
          description
            "The time of the last discontinuity.";
        }

        list Assoc {
          key "PrimaryPeerAddress LocalPort";
          config false;
          description
            "SCTP Association Table";
          leaf Status {
            type enumeration {
              enum "Disabled";
              enum "Active";
              enum "Progressing";
              enum "ShuttingDown";
              enum "Error";
            }
            description
              "The status of this SCTP association entry.";
          }
          leaf PrimaryPeerAddress {
            type types:IPAddress;
            description
              "The primary IP address of the peer SCTP association
               entity.";
          }
          leaf LocalPort {
            type uint32 {
              range "0..63999";
            }
            description
              "The local SCTP port number used for this SCTP
               association.";
          }
          leaf InStreams {
            type uint32;
            description
              "The number of Inbound Streams according to the
               negotiation at association start-up.";
          }
          leaf OutStreams {
            type uint32;
            description
              "The number of Outbound Streams according to the
               negotiation at association start-up.";
          }
          leaf StartTime {
            type yang:date-and-time;
            description
              "The start Time for the present SCTP association.";
          }
          leaf Discontinuity {
            type yang:date-and-time;
            description
              "The time of the last discontinuity.";
          }
        }
      }

      container RealTime {
        description
          "This object contains parameters relating to Real Time
           Transport using RTP.";
        leaf RTCPEnable {
          type boolean;
          description
            "Enable or disable RTCP.";
        }
        leaf SentPackets {
          type uint32;
          config false;
          description
            "The number of sent RTP packets.";
        }
        leaf RcvPackets {
          type uint32;
          config false;
          description
            "The number of received RTP packets.";
        }
        leaf BytesSent {
          type uint32;
          config false;
          description
            "Total number of RTP payload bytes sent.";
        }
        leaf BytesReceived {
          type uint32;
          config false;
          description
            "Total number of RTP payload bytes received.";
        }

        container Perf {
          config false;
          description
            "This object contains performances relating to Real Time
             Transport using RTP.";
          leaf LostRcvPackets {
            type uint32;
            description
              "The number of Lost RTP packets in reception.";
          }
          leaf LostFarEndPackets {
            type uint32;
            description
              "The number of Far End Lost RTP packets.";
          }
          leaf Overruns {
            type uint32;
            description
              "Total number of times the receive jitter buffer has
               overrun.";
          }
          leaf Underruns {
            type uint32;
            description
              "Total number of times the receive jitter buffer has
               underrun for a CS-domain RAB.";
          }
          leaf MeanRTT {
            type uint32;
            description
              "The mean Round Trip Time in {{units}} as computed by
               the source.  {{bibref|RFC3550}}";
          }
          leaf MaxRTT {
            type uint32;
            description
              "The maximum Round Trip Time in {{units}} as computed
               by the source.  {{bibref|RFC3550}}";
          }
          leaf MeanReceiveJitter {
            type uint32;
            description
              "The mean receive jitter in {{units}} as computed by
               the source.  {{bibref|RFC3550}}";
          }
          leaf MaxReceiveJitter {
            type uint32;
            description
              "The maximum receive jitter in {{units}} as computed
               by the source.  {{bibref|RFC3550}}";
          }
          leaf MeanFarEndJitter {
            type uint32;
            description
              "The mean far end jitter in {{units}} as computed by
               the source.  {{bibref|RFC3550}}";
          }
          leaf MaxFarEndJitter {
            type uint32;
            description
              "The maximum far end jitter in {{units}} as computed
               by the source.  {{bibref|RFC3550}}";
          }
        }
      }

      container Packet {
        description
          "This object contains parameters relating to Packet
           Transport using GTP-U.";
        leaf EchoInterval {
          type uint32;
          description
            "Echo interval in {{units}}.  An Echo interval value of
             zero means echo is disabled.";
        }
        leaf SentPackets {
          type uint32;
          config false;
          description
            "The number of sent GTP-U packets.";
        }
        leaf RcvPackets {
          type uint32;
          config false;
          description
            "The number of received GTP-U packets.";
        }
      }

      container Security {
        description
          "This object contains parameters relating to Security.";

        list Secret {
          key "UICCCardID";
          description
            "Shared Secret Table.  This table gathers information
             about all types of shared secret-based credentials
             (UICC).";
          leaf Enable {
            type boolean;
            description
              "Enable or disable this Shared Secret entry";
          }
          leaf Type {
            type enumeration {
              enum "SIM";
              enum "USIM";
            }
            config false;
            description
              "The type of this Shared Secret entry.";
          }
          leaf Status {
            type enumeration {
              enum "Present";
              enum "Not_present";
              enum "Error";
            }
            config false;
            description
              "The status of this Shared Secret entry.";
          }
          leaf UICCCardID {
            type string {
              length "0..19";
            }
            config false;
            description
              "The UICC Card Identifier (UICCID), only numeric
               values are allowed.  {{bibref|ITU-E.118}}";
          }
        }
      }
    }
  }
}
