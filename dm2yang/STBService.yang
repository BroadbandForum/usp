module STBService {
  namespace "urn:tbd";
  prefix TBD;
  
  import ietf-yang-types {
    prefix yang;
  }
  
  import tr-106-types {
    prefix types;
  }
  
  organization
    "TBD";
  
  contact
    "TBD";
  
  description
    "";
  
  revision 1970-01-01 {
    description
      "TBD";
    reference
      "TBD";
  }

  list STBService {
    key "Alias";
    description
      "The top-level object for an STB CPE.";
    leaf Enable {
      type boolean;
      description
        "Enables or disables this {{object}} instance.";
    }

    container Capabilities {
      config false;
      description
        "The overall capabilities of the STB CPE.  This is a
         constant read-only object, meaning that only a firmware
         update will cause these values to be altered.";
      leaf MaxActiveAVStreams {
        type int32 {
          range "-1..max";
        }
        description
          "Maximum number of simultaneously active AV streams
           supported by the STB.
        
           A value of -1 indicates no specific limit on the
           number of active streams.
        
           A value of 0, while not strictly illegal, would
           indicate an STB that doesn't support AV streams, which
           is extremely unlikely.";
      }
      leaf MaxActiveAVPlayers {
        type int32 {
          range "-1..max";
        }
        description
          "Maximum number of simultaneously active AV players
           supported by the STB.  An AV player is associated with
           a presentation device (such as a TV set).
        
           Note that this is the strict maximum but, depending on
           the AV streams to be decoded, a given STB may not
           always have the resources to run all of these AV
           players, e.g.  it might be able to decode one main
           picture and one PIP in standard definition, but just a
           main picture and no PIP in high definition.
        
           A value of -1 indicates no specific limit on the
           number of active players.
        
           A value of 0, while not strictly illegal, would
           indicate an STB that doesn't support AV players, which
           is extremely unlikely.";
      }

      container FrontEnd {
        description
          "Front-end capabilities.";

        container DVBT {
          description
            "Capabilities of the DVB-T receiver.";
          leaf MaxActiveDVBTStreams {
            type int32 {
              range "-1..max";
            }
            description
              "Maximum number of simultaneous active AV streams
               supported by the DVB-T FrontEnd.
            
               A value of -1 indicates no specific limit on the
               number of active streams.";
          }
          leaf MaxLogicalChannels {
            type int32 {
              range "-1..max";
            }
            description
              "Maximum number of logical channels that can be
               contained in a Service List Database.
            
               A value of -1 indicates no specific limit on the
               number of logical channels.";
          }
        }

        container IP {
          description
            "IP front-end capabilities.";
          leaf MaxActiveIPStreams {
            type int32 {
              range "-1..max";
            }
            description
              "Maximum number of simultaneous active AV streams
               supported by the IP FrontEnd.
            
               A value of -1 indicates no specific limit on the
               number of active streams.";
          }
          leaf MaxActiveInboundIPStreams {
            type int32 {
              range "-1..max";
            }
            description
              "Maximum number of simultaneous active Inbound AV
               streams supported by the IP FrontEnd.
            
               A value of -1 indicates no specific limit on the
               number of active streams.";
          }
          leaf MaxActiveOutboundIPStreams {
            type int32 {
              range "-1..max";
            }
            description
              "Maximum number of simultaneous active Outbound AV
               streams supported by the IP FrontEnd.
            
               A value of -1 indicates no specific limit on the
               number of active streams.";
          }
          leaf StreamingControlProtocols {
            type enumeration {
              enum "RTSP";
              enum "IGMP";
              enum "IGMPv2";
              enum "IGMPv3";
              enum "DSM-CC";
            }
            description
              "Supported streaming control protocols.";
          }
          leaf StreamingTransportProtocols {
            type enumeration {
              enum "UDP";
              enum "TCP";
              enum "SCTP";
              enum "DCCP";
              enum "RTP";
              enum "HTTP";
            }
            description
              "Network protocols supported for AV streaming.";
          }
          leaf StreamingTransportControlProtocols {
            type enumeration {
              enum "RTCP";
              enum "ARQ";
              enum "AL-FEC";
            }
            description
              "Transport control protocols supported for AV
               streaming in combination with RTP.";
          }
          leaf DownloadTransportProtocols {
            type enumeration {
              enum "HTTP";
              enum "HTTPS";
              enum "FTP";
              enum "FTPS";
              enum "SFTP";
              enum "TFTP";
            }
            description
              "Network protocols supported for AV download.";
          }
          leaf MultiplexTypes {
            type enumeration {
              enum "None";
              enum "MPEG1-SYS";
              enum "MPEG2-PS";
              enum "VOB";
              enum "MPEG2-TS";
            }
            description
              "AV multiplex types supported by the front end.";
          }
          leaf MaxDejitteringBufferSize {
            type int32 {
              range "-1..max";
            }
            description
              "Describes the maximum de-jittering buffer size, in
               {{units}}, supported by the STB.
            
               A value of -1 indicates no specific limit on the
               buffer size.";
          }
        }
      }

      container PVR {
        description
          "PVR capabilities.";
        leaf MaxIOStreams {
          type int32 {
            range "-1..max";
          }
          description
            "Maximum number of AV streams that the PVR can
             simultaneously record and playback.  For example a
             time shift, consisting of a record and a play back
             is considered as 2 streams.
          
             A value of -1 indicates no specific limit on the
             number of streams.";
        }
        leaf MaxRecordingStreams {
          type int32 {
            range "-1..max";
          }
          description
            "Maximum number of AV streams that the PVR can
             simultaneously record.
          
             A value of -1 indicates no specific limit on the
             number of streams.";
        }
        leaf MaxPlaybackStreams {
          type int32 {
            range "-1..max";
          }
          description
            "Maximum number of AV streams that the PVR can
             simultaneously play back.
          
             A value of -1 indicates no specific limit on the
             number of streams.";
        }
        leaf MaxTimeDelay {
          type int32 {
            range "-1..max";
          }
          description
            "Maximum time delay, in {{units}}, that the PVR
             time-shift mode can support.
          
             A value of -1 indicates no specific limit on the
             time delay.";
        }
      }

      container AudioDecoder {
        description
          "Audio decoder capabilities.";
        leaf AudioStandards {
          type enumeration {
            enum "MPEG1-Part3-Layer2";
            enum "MPEG1-Part3-Layer3";
            enum "MPEG2-Part3 -Layer2";
            enum "MPEG2-Part3-Layer3";
            enum "MPEG2.5";
            enum "MP3-PRO";
            enum "MP3-Surround";
            enum "MPEG2-AAC-LC";
            enum "MPEG4-AAC-LC";
            enum "MPEG4-AAC-MP";
            enum "MPEG4-BSAC";
            enum "MPEG4-AAC-HE-v2";
            enum "MPEG-Surround";
            enum "DOLBY-AC3";
            enum "DOLBY-DD+";
            enum "DTS";
            enum "DTS-HD";
          }
          description
            "Audio standards supported by this STB.";
        }
      }

      container VideoDecoder {
        description
          "Video decoder capabilities.";
        leaf VideoStandards {
          type enumeration {
            enum "MPEG2-Part2";
            enum "MPEG4-Part2";
            enum "MPEG4-Part10";
            enum "SMPTE-VC-1";
          }
          description
            "Video standards supported by this STB.";
        }

        container MPEG2Part2 {
          description
            "Object describing the set of supported MPEG2 profiles
             and levels for this STB.  It also describes the set
             of audio standards supported when MPEG2 Part 2 is
             used as the video standard.";
          leaf AudioStandards {
            type string;
            description
              "Audio Standards supported by the Player when
               associated with MPEG2 Part 2 Video.";
          }

          list ProfileLevel {
            key "Profile Level";
            description
              "Table to describe the set of profiles and levels
               combinations supported by the STB when MPEG2 Part
               2 is used as video standard.
            
               {{keys}} The table MUST include a distinct entry
               for each supported combination of these
               parameters.";
            leaf Profile {
              type enumeration {
                enum "SP";
                enum "MP";
                enum "SNR";
                enum "Spt";
                enum "HP";
                enum "4:2:2";
              }
              description
                "Identifier of the MPEG2 Part 2 profile.";
            }
            leaf Level {
              type enumeration {
                enum "LL";
                enum "ML";
                enum "H-14";
                enum "HL";
              }
              description
                "Identifier of the MPEG2 part 2 level.";
            }
            leaf MaximumDecodingCapability {
              type uint32;
              description
                "The maximum decoding capability for this video
                 standard in {{units}}.  This strictly depends on
                 the profile and level selected.";
            }
          }
        }

        container MPEG4Part2 {
          description
            "Object describing the set of supported profiles and
             levels for this STB.  It also describes the set of
             audio standards supported when MPEG4 Part 2 is used
             as the video standard.";
          leaf AudioStandards {
            type string;
            description
              "Audio Standards supported by the Player when
               associated with MPEG4 Part 2 video.";
          }

          list ProfileLevel {
            key "Profile Level";
            description
              "Table to describe the set of profiles and levels
               combinations supported by the STB when MPEG4 Part
               2 is used as video standard.
            
               {{keys}} The table MUST include a distinct entry
               for each supported combination of these
               parameters.";
            leaf Profile {
              type enumeration {
                enum "SIMPLE";
                enum "SIMPLE SCALABLE";
                enum "CORE";
                enum "CORE SCALABLE";
                enum "ADVANCED CORE";
                enum "MAIN";
                enum "N-BIT";
                enum "ADVANCED REAL TIME SIMPLE";
                enum "ADVANCED CODING EFFICIENCY";
                enum "SIMPLE STUDIO";
                enum "CORE STUDIO";
                enum "ADVANCED SIMPLE";
                enum "FINE GRANULARITY SCALABLE";
                enum "ADVANCED SCALABLE TEXTURE";
                enum "ANIMATED 2D MESH";
                enum "BASIC ANIMATED TEXTURE";
                enum "STILL SCALABLE TEXTURE";
                enum "SIMPLE FACE";
                enum "SIMPLE FBA";
              }
              description
                "Identifier of the MPEG4 Part 2 profile.";
            }
            leaf Level {
              type enumeration {
                enum "L5";
                enum "L4";
                enum "L4a";
                enum "L3b";
                enum "L3";
                enum "L2";
                enum "L1";
                enum "L0";
              }
              description
                "Identifier of the MPEG4 Part 2 level.";
            }
            leaf MaximumDecodingCapability {
              type uint32;
              description
                "The maximum decoding capability for this video
                 standard in {{units}}.  This strictly depends on
                 the profile and level selected.";
            }
          }
        }

        container MPEG4Part10 {
          description
            "Object describing the set of supported profiles and
             levels for this STB.  It also describes the set of
             audio standards supported when MPEG4 Part 10 is used
             as the video standard.";
          leaf AudioStandards {
            type string;
            description
              "Audio Standards supported by the Player when
               associated with MPEG4 Part 10 video.";
          }

          list ProfileLevel {
            key "Profile Level";
            description
              "Table to describe the set of profiles and levels
               combinations supported by the STB when MPEG4 Part
               10 is used as video standard.
            
               {{keys}} The table MUST include a distinct entry
               for each supported combination of these
               parameters.";
            leaf Profile {
              type enumeration {
                enum "BASELINE";
                enum "MAIN";
                enum "EXTENDED";
                enum "HIGH";
                enum "HIGH 10";
                enum "HIGH 4:2:2";
                enum "HIGH 4:4:4";
              }
              description
                "Supported MPEG4 Part 10 profiles.";
            }
            leaf Level {
              type enumeration {
                enum "1";
                enum "1b";
                enum "1.1";
                enum "1.2";
                enum "1.3";
                enum "2";
                enum "2.1";
                enum "2.2";
                enum "3";
                enum "3.1";
                enum "3.2";
                enum "4";
                enum "4.1";
                enum "4.2";
                enum "5";
                enum "5.1";
              }
              description
                "Supported MPEG4 Part 10 Levels.";
            }
            leaf MaximumDecodingCapability {
              type uint32;
              description
                "The maximum decoding capability for this video
                 standard in {{units}}.  This strictly depends on
                 the profile and level selected.";
            }
          }
        }

        container SMPTEVC1 {
          description
            "Object describing the set of supported SMPTE-VC-1
             profiles and levels for this STB.  It also describes
             the set of audio standards supported when SMPTE-VC-1
             is used as the video standard.";
          leaf AudioStandards {
            type string;
            description
              "Audio Standards supported by the Player when
               associated with SMPTE-VC-1 video.";
          }

          list ProfileLevel {
            key "Profile Level";
            description
              "Table to describe the set of profiles and levels
               combinations supported by the STB when SMPTE-VC-1
               is used as video standard.
            
               {{keys}} The table MUST include a distinct entry
               for each supported combination of these
               parameters.";
            leaf Profile {
              type enumeration {
                enum "SP";
                enum "MP";
                enum "AP";
              }
              description
                "Identifier of the SMPTE-VC-1 profile.";
            }
            leaf Level {
              type enumeration {
                enum "LL";
                enum "ML";
                enum "HL";
                enum "L0";
                enum "L1";
                enum "L2";
                enum "L3";
                enum "L4";
              }
              description
                "Identifier of the SMPTE-VC-1 level.";
            }
            leaf MaximumDecodingCapability {
              type uint32;
              description
                "The maximum decoding capability for this video
                 standard in {{units}}.  This strictly depends on
                 the profile and level selected.";
            }
          }
        }
      }

      container AudioOutput {
        description
          "Audio output capabilities.  The audio output stage may
           include selecting output formats, selecting output
           connectors, and copy protection.";
        leaf AudioFormats {
          type enumeration {
            enum "ANALOG-MONO";
            enum "ANALOG-2-CHANNELS";
            enum "ANALOG-5.1-CHANNELS";
            enum "DIGITAL-OPTICAL-SP/DIF";
            enum "DIGITAL-COAXIAL-SP/DIF";
            enum "HDMI";
            enum "RF";
          }
          description
            "Supported audio output formats.  {{enum}}
          
             Note that these refer to supported output formats
             and not to physical connectors.";
        }
      }

      container VideoOutput {
        description
          "Video output capabilities.  The video output stage may
           include selecting output formats, selecting output
           connectors, and copy protection.";
        leaf CompositeVideoStandards {
          type enumeration {
            enum "NTSC-J";
            enum "NTSC-M";
            enum "PAL-B";
            enum "PAL-D";
            enum "PAL-G";
            enum "PAL-H";
            enum "PAL-I";
            enum "PAL-N";
            enum "PAL-M";
            enum "SECAM-B";
            enum "SECAM-G";
            enum "SECAM-H";
            enum "SECAM-D";
            enum "SECAM-K";
            enum "SECAM-K1";
            enum "SECAM-L";
          }
          description
            "Analog composite video standards supported for video
             output.  This applies only to CVBS video output.";
        }
        leaf VideoFormats {
          type enumeration {
            enum "CVBS";
            enum "S-Video";
            enum "YPrPb";
            enum "RGsB";
            enum "RGB";
            enum "HDMI";
            enum "DVI";
            enum "RF";
          }
          description
            "Supported video output formats.  {{enum}}
          
             Note that these refer to supported output formats
             and not to physical connectors.";
        }
        leaf Macrovision {
          type string {
            length "0..32";
          }
          description
            "Supported version of Macrovision digital content
             protection standard.";
        }
        leaf HDCP {
          type string {
            length "0..32";
          }
          description
            "Supported version of HDCP digital content protection
             standard.";
        }
        leaf DisplayFormats {
          type string {
            pattern "\d+:\d+";
          }
          description
            "Each entry is a supported display format and MUST be in
             the form of “x:y”, such as for example “4:3, 16:9,
             14:9\".  {{nopattern}}";
        }
      }

      container HDMI {
        description
          "This object describes the characteristics of the HDMI
           interface, if any.";
        leaf SupportedResolutions {
          type enumeration {
            enum "640x480p/60Hz";
            enum "1280x720p/60Hz";
            enum "1920x1080i/60Hz";
            enum "720x480p/60Hz";
            enum "720(1440)x480i/60Hz";
            enum "1280x720p/50Hz";
            enum "1920x1080i/50Hz";
            enum "720x576p/50Hz";
            enum "720(1440)x240p/60Hz";
            enum "2880x480i/60Hz";
            enum "2880x240p/60Hz";
            enum "1440x480p/60Hz";
            enum "1920x1080p/60Hz";
            enum "720(1440)x288p/50Hz";
            enum "2880x576i/50Hz";
            enum "2880x288p/50Hz";
            enum "1440x576p/50Hz";
            enum "1920x1080p/50Hz";
            enum "1920x1080p/24Hz";
            enum "1920x1080p/25Hz";
            enum "1920x1080p/30Hz";
            enum "2880x480p/60Hz";
            enum "2880x576p/50Hz";
            enum "1920x1080i (1250 total)/50Hz";
            enum "720(1440)x480i/120Hz";
            enum "720x480p/120Hz";
            enum "1920x1080i/120Hz";
            enum "1280x720p/120Hz";
            enum "720(1440)x480i/240Hz";
            enum "720x480p/240Hz";
            enum "720(1440)x576i/100Hz";
            enum "720x576p/100Hz";
            enum "1920x1080i/100Hz";
            enum "1280x720p/100Hz";
            enum "720(1440)x576i/200Hz";
            enum "720x576p/200Hz";
            enum "1280x720p/24Hz";
            enum "1280x720p/25Hz";
            enum "1280x720p/30Hz";
            enum "1920x1080p/120Hz";
            enum "1920x1080p/100Hz";
          }
          description
            "Video resolutions supported for the HDMI video output.
             {{enum}}";
        }
        leaf CECSupport {
          type boolean;
          description
            "Indicates whether the STB is supporting HDMI-CEC
             features as described in {{bibref|HDMI}}.";
        }
        leaf HDMI3D {
          type boolean;
          description
            "Indicates whether the STB is supporting the 3D video
             formats mandated by {{bibref|HDMI}}.";
        }
      }

      container CDS {
        description
          "This object describes the characteristics of the Content
           Download System, if any.";
        leaf PushCapable {
          type boolean;
          description
            "Capability of providing a CDS Push service for the
             operator initiated download of content items to
             local storage via a broadband IP connection.";
        }
        leaf PullCapable {
          type boolean;
          description
            "Capability of providing a CDS Pull service for the user
             initiated download of content items to a local
             storage via a broadband IP connection.";
        }
      }

      container CA {
        description
          "This object describes the characteristics of the
           Conditional Access, if any.";
        leaf CASystems {
          type string;
          description
            "Unique identifiers (e.g.  commercial names) of
             supported CA systems.";
        }
      }

      container DRM {
        description
          "This object describes the characteristics of the Digital
           Rights Management, if any.";
        leaf DRMSystems {
          type string;
          description
            "Unique identifiers (e.g.  commercial names) of
             supported DRM systems.";
        }
      }

      container ServiceMonitoring {
        description
          "This object describes the capabilities of the
           {{object|.ServiceMonitoring}} object.";
        leaf ServiceTypes {
          type enumeration {
            enum "IPTV";
            enum "VoD";
            enum "IP";
            enum "TEST";
            enum "IP-All";
            enum "CAB";
            enum "DTT";
            enum "SAT";
            enum "PVR";
          }
          description
            "Supported service types, each of which relates to an AV
             stream source.  {{enum}}
          
             Note that none of the standard service types cover
             LAN-sourced IP streams.";
        }
        leaf MaxEventsPerSampleInterval {
          type int32 {
            range "-1..max";
          }
          description
            "Maximum number of events of each applicable statistic
             that the STB is able to store for each sample
             interval.
          
             A value of -1 indicates no specific maximum number
             of events.";
        }
        leaf MaxActiveMainStreams {
          type int32 {
            range "-1..max";
          }
          description
            "Maximum number of AV Main streams for which the STB can
             simultaneously collect statistics.
          
             A value of -1 indicates no specific limit on the
             number of active streams.";
        }
        leaf MinSampleInterval {
          type int32 {
            range "-1..max";
          }
          description
            "Minimum sample interval in {{units}} that the STB MUST
             be able to support.
          
             A value of -1 indicates no specific minimum sample
             interval.";
        }
        leaf MaxReportSamples {
          type int32 {
            range "-1..max";
          }
          description
            "Maximum number of samples of each statistic that the
             STB is able to store and report.
          
             A value of -1 indicates no specific maximum number
             of samples.";
        }
        leaf HighLevelMetricNames {
          type string;
          description
            "The names of the supported high-level metrics.  If a
             metric produces several different scores (e.g.  an
             audio, a video, and an audiovisual score), then they
             MUST be explicitly named.  Example (using \"XYZ\" as
             the name of the base metric):
          
             \"XYZAudio,XYZVideo,XYZAudiovisual\".";
        }
        leaf MaxMainStreamEventLogEntries {
          type uint32;
          description
            "Maximum number of event log entries that the STB is
             able to record for a MainStream object instance.";
        }
      }

      container AudienceStats {
        description
          "This object describes the capabilities of the
           {{object|.Applications.AudienceStats}} object.";
        leaf MaxAudienceStatsChannels {
          type int32 {
            range "-1..max";
          }
          description
            "Maximum number of channels that the STB MUST support in
             the {{object|.Applications.AudienceStats}} object
          
             A value of -1 indicates no specific limit on the
             number of channels.";
        }
      }
    }

    container Components {
      description
        "Details of STB logical or physical internal components.
         Unlike the {{object|.Capabilities}} object, which is
         read-only and which doesn't describe individual
         instances, this object contains some writeable
         parameters.";

      list FrontEnd {
        key "Name";
        description
          "FrontEnd instance table.  Each front-end instance,
           including vendor-specific front-end types, will
           normally have a sub-object that corresponds to the
           front-end type (e.g.  DVB-T or IP).";
        leaf Enable {
          type boolean;
          description
            "Enables or disables this front-end.";
        }
        leaf Status {
          type enumeration {
            enum "Disabled";
            enum "Enabled";
            enum "Error";
          }
          config false;
          description
            "The status of this front-end.  {{enum}}
          
             The {{enum|Error}} value MAY be used by the CPE to
             indicate a locally defined error condition.";
        }
        leaf Name {
          type string {
            length "0..256";
          }
          config false;
          description
            "Human-readable name associated with this front-end.";
        }

        container DVBT {
          description
            "DVB-T front-end details.  This object will normally be
             present if and only if this front-end is a DVB-T
             front-end.
          
             Parameters are taken from the DGTVi D-Book
             {{bibref|D-Book}}.";

          container Modulation {
            description
              "DVB-T modulation details.";
            leaf Frequency {
              type uint32;
              description
                "Indicates the current frequency in {{units}}.
              
                 The value of this parameter is undefined while
                 installing the service list (see
                 {{object|.Components.FrontEnd.{i}.DVBT.Install}}).";
            }
            leaf ChannelBandwidth {
              type enumeration {
                enum "8MHz";
                enum "7MHz";
                enum "6MHz";
              }
              description
                "Indicates the channel bandwidth in use.";
            }
            leaf Constellation {
              type enumeration {
                enum "QPSK";
                enum "16QAM";
                enum "64QAM";
              }
              description
                "Indicates the current constellation in use.";
            }
            leaf HierarchicalInformation {
              type enumeration {
                enum "0";
                enum "1";
                enum "2";
                enum "4";
              }
              description
                "Hierarchical parameter alpha.  The higher the value
                 of alpha, the more noise-immune the High
                 Priority Modulation is.";
            }
            leaf CodeRateHP {
              type enumeration {
                enum "1/2";
                enum "2/3";
                enum "3/4";
                enum "5/6";
                enum "7/8";
              }
              description
                "Indicates the current code rate in use.  Code rate
                 applies to HP in case of hierarchical coding.";
            }
            leaf CodeRateLP {
              type enumeration {
                enum "0";
                enum "1/2";
                enum "2/3";
                enum "3/4";
                enum "5/6";
                enum "7/8";
              }
              description
                "Indicates the current code rate in use.  Code rate
                 applies to LP in case of hierarchical coding.";
            }
            leaf GuardInterval {
              type enumeration {
                enum "1/32";
                enum "1/16";
                enum "1/8";
                enum "1/4";
              }
              description
                "Indicates the current guard interval in use.";
            }
            leaf TransmissionMode {
              type enumeration {
                enum "2k";
                enum "8k";
              }
              description
                "Indicates the number of carriers in an OFDM frame.";
            }
            leaf SNR {
              type uint32;
              config false;
              description
                "Signal/Noise ratio in the carrier band, measured in
                 {{units}}.";
            }
            leaf BER {
              type uint32;
              config false;
              description
                "Bit Error Ratio before correction, expressed in
                 multiples of 1e-6.";
            }
            leaf CBER {
              type uint32;
              config false;
              description
                "Bit Error Ratio after correction, expressed in
                 multiples of 1e-9.";
            }
            leaf Locked {
              type boolean;
              config false;
              description
                "Indicates whether or not the tuner is locked on a
                 frequency.";
            }
          }

          container Service {
            config false;
            description
              "DVB-T Current service details.";
            leaf CurrentLogicalChannel {
              type string {
                length "0..256";
              }
              description
                "It represents the logical channel object instance
                 for the current service, For example:
                 ''.Components.FrontEnd.1.DVBT.-ServiceListDatabase.LogicalChannel.12''.";
            }
            leaf CurrentService {
              type string {
                length "0..256";
              }
              description
                "It represents the service object instance for the
                 current service.  For example:
                 ''.Components.FrontEnd.1.DVBT.ServiceListDatabase.LogicalChannel.12.Service.1''.";
            }
          }

          container Install {
            description
              "DVB-T service list database installation.  Supports
               maintenance of the service list database by
               scanning frequencies in order to detect services.
            
               The service list database is in
               {{object|.Components.FrontEnd.{i}.DVBT.ServiceListDatabase}}.";
            leaf Start {
              type boolean;
              description
                "Starts (when set to {{true}}) or stops (when set to
                 {{false}}) scanning for services.  The value is
                 not saved in device state and is always
                 {{false}} when read.
              
                 Discovered services are merged with those
                 already present in the service list database.
                 This supports cases where the frequency spectrum
                 is not continuous.
              
                 In order to force a re-install, the service list
                 database needs to be reset (see
                 {{param|.Components.FrontEnd.{i}.DVBT.ServiceListDatabase.Reset}}).";
            }
            leaf Status {
              type enumeration {
                enum "Disabled";
                enum "Enabled";
                enum "Error";
              }
              config false;
              description
                "Indicates the status of the scanning process.
                 {{enum}}
              
                 The {{enum|Error}} value MAY be used by the CPE
                 to indicate a locally defined error condition.";
            }
            leaf Progress {
              type uint32 {
                range "0..100";
              }
              config false;
              description
                "Progression in {{units}} of the current scan.  The
                 value is undefined when a scan is not in
                 progress.";
            }
            leaf StartFrequency {
              type uint32;
              description
                "Frequency (in {{units}}) at which to start the
                 scanning process.";
            }
            leaf StopFrequency {
              type uint32;
              description
                "Frequency (in {{units}}) at which to stop the
                 scanning process.";
            }
          }

          container ServiceListDatabase {
            description
              "DVB-T service list database.";
            leaf Reset {
              type boolean;
              description
                "When set to {{true}}, resets the service list
                 database.  Setting it to {{false}} has no
                 effect.  The value is not saved in device state
                 and is always {{false}} when read.";
            }
            leaf TotalServices {
              type uint32;
              config false;
              description
                "Total number of services defined in the service
                 list database, i.e.  the number of different
                 DvbIds in the database.";
            }

            list LogicalChannel {
              key "LogicalChannelNumber";
              description
                "DVB-T logical channel information.";
              leaf LogicalChannelNumber {
                type uint32;
                config false;
                description
                  "Logical channel number.";
              }

              list Service {
                key "DvbId";
                description
                  "DVB-T service information.";
                leaf Name {
                  type string {
                    length "0..256";
                  }
                  config false;
                  description
                    "Human-readable name associated with this
                     service, e.g.  read from the DVB service
                     information metadata.";
                }
                leaf DvbId {
                  type string {
                    length "0..12";
                  }
                  config false;
                  description
                    "DVB Triplet {{bibref|TS102034}} that uniquely
                     identifies the service in the service list
                     database.
                  
                     The DVB Triplet is a 12-byte string that is
                     a concatenation of 4 hexadecimal characters
                     for each of the following: Original Network
                     Id, Transport Stream Id, Service Id.  For
                     example:
                  
                     * OriginalNetworkId = 8442 = 0x20FA
                  
                     * TransportStreamId = 4 = 0x0004
                  
                     * ServiceId = 257 = 0x0101
                  
                     -> DvbId = ''20FA00040101''";
                }
                leaf Frequency {
                  type uint32;
                  config false;
                  description
                    "Transmitter frequency (in {{units}}) for this
                     service.";
                }
                leaf BER {
                  type uint32;
                  config false;
                  description
                    "Bit Error Ratio before correction, expressed in
                     multiples of 1e-6 (indicates the quality of
                     this service).";
                }
                leaf CBER {
                  type uint32;
                  config false;
                  description
                    "Bit Error Ratio after correction, expressed in
                     {{units}} (indicates the quality of this
                     service).";
                }
                leaf SNR {
                  type uint32;
                  config false;
                  description
                    "Signal/Noise ratio in the carrier band,
                     measured in {{units}} (indicates the quality
                     of this service).";
                }
                leaf Preferred {
                  type boolean;
                  description
                    "When set to {{true}}, identifies this as the
                     preferred service for this logical channel
                     and automatically sets {{param}} to
                     {{false}} for other services associated with
                     this logical channel.
                  
                     When set to {{false}}, cancels this
                     service's preferred status and causes the
                     service with the lowest {{param|BER}} (best
                     received quality) to become the preferred
                     service for this logical channel.
                  
                     Whenever frequencies are re-scanned, all
                     {{param}} parameters are implicitly reset to
                     {{false}}, i.e.  a re-scan will always use
                     the {{param|BER}} to determine preferred
                     services, and will discard any past explicit
                     overrides.";
                }
              }
            }
          }

          container LogicalChannelConnect {
            description
              "Connect to a DVB-T logical channel.";
            leaf LogicalChannelNumber {
              type uint32;
              description
                "Logical channel number to connect to (the logical
                 channel's preferred service will be connected
                 to).
              
                 If a {{object|.ServiceMonitoring.MainStream}}
                 instance with ''ServiceType'' = ''DTT'' is
                 currently enabled, the STB MUST ensure that
                 performance data for this service is collected
                 in that instance.
              
                 The value is not saved in device state.  The
                 value when read is not specified and need not be
                 the value that was most recently written.";
            }
          }

          container ServiceConnect {
            description
              "Connect to a DVB-T service.";
            leaf DvbId {
              type string {
                length "0..12";
              }
              description
                "DvbId of the service to connect to.
              
                 If a {{object|.ServiceMonitoring.MainStream}}
                 instance with ''ServiceType'' = ''DTT'' is
                 currently enabled, the STB MUST ensure that
                 performance data for this service is collected
                 in that instance.
              
                 The value is not saved in device state.  The
                 value when read is not specified and need not be
                 the value that was most recently written.";
            }
          }
        }

        container IP {
          description
            "IP front-end details.  This object will normally be
             present if and only if the front-end is an IP
             front-end.";
          leaf ActiveInboundIPStreams {
            type uint32;
            config false;
            description
              "Number of {{object|Inbound}} AV streams currently
               active (i.e.  with ''Status'' != ''Disabled'',
               which means audio or AV data are being processed).";
          }
          leaf ActiveOutboundIPStreams {
            type uint32;
            config false;
            description
              "Number of {{object|Outbound}} AV streams currently
               active (i.e.  with ''Status'' != ''Disabled'',
               which means audio or AV data are being processed).";
          }

          container RTCP {
            description
              "Parameters related to RTCP receiver report generation
               as defined in {{bibref|RFC3550}}.";
            leaf Enable {
              type boolean;
              description
                "Enables or disables RTCP receiver report
                 generation.";
            }
            leaf Status {
              type enumeration {
                enum "Disabled";
                enum "Enabled";
                enum "Error";
              }
              config false;
              description
                "The status of RTCP receiver report generation.
                 {{enum}}
              
                 The {{enum|Error}} value MAY be used by the CPE
                 to indicate a locally defined error condition.";
            }
            leaf TxRepeatInterval {
              type uint32 {
                range "1..max";
              }
              description
                "Transmission repeat interval, in {{units}}.";
            }
          }

          container RTPAVPF {
            description
              "Parameters related to RTP AVPF configuration as
               defined in {{bibref|RFC4585}} and
               {{bibref|RFC4588}}.";
            leaf Enable {
              type boolean;
              description
                "Enables or disables RTP/AVPF receiver report
                 generation.
              
                 When set to {{true}}, enables the error
                 correction operation, immediately
                 ({{enum|Forced|OperationMode}} mode) or
                 automatically when necessary
                 ({{enum|Auto|OperationMode}} mode).
              
                 When set to {{false}}, disables the error
                 correction operation.";
            }
            leaf OperationMode {
              type enumeration {
                enum "Auto";
                enum "Forced";
              }
              description
                "The operation mode of the Error Correction
                 mechanism.  {{enum}}
              
                 In {{enum|Auto}} mode, when Error Correction is
                 enabled, the STB decides whether or not to run
                 the Error Correction operation (e.g.  after an
                 error analysis).
              
                 In {{enum|Forced}} mode, when Error Correction
                 is enabled the STB MUST run the Error Correction
                 operation.";
            }
            leaf ECOperationStatus {
              type enumeration {
                enum "Disabled";
                enum "Auto mode EC On";
                enum "Auto mode EC Off without buffering";
                enum "Auto mode EC Off with buffering";
                enum "Forced mode EC On";
                enum "Error";
              }
              config false;
              description
                "The status of RTP/AVPF operation.  {{enum}}
              
                 The {{enum|Error}} value MAY be used by the CPE
                 to indicate a locally defined error condition.";
            }
            leaf Status {
              type enumeration {
                enum "Disabled";
                enum "Enabled";
                enum "Error";
              }
              config false;
              description
                "The status of RTP/AVPF receiver report generation.
                 {{enum}}
              
                 The {{enum|Error}} value MAY be used by the CPE
                 to indicate a locally defined error condition.";
            }
            leaf RetransmitTimeout {
              type uint32;
              description
                "Time in {{units}} the receiver shall wait for a
                 retransmitted packet before considering it to be
                 lost.";
            }
            leaf MinLossPackets {
              type uint32;
              description
                "Minimum number of lost packets the receiver shall
                 wait for before generating a retransmission
                 request.";
            }
            leaf MaxReportTime {
              type uint32;
              description
                "Maximum time in {{units}} the receiver shall wait
                 between a lost packet and the generation of a
                 retransmission request.";
            }
            leaf MaxLossBurst {
              type uint32;
              description
                "Maximum number of consecutive lost packets for
                 which the receiver shall attempt recovery.";
            }
          }

          container FEC {
            description
              "Parameters related to AL-FEC configuration as defined
               in {{bibref|SMPTE20022-1}}.";
            leaf Enable {
              type boolean;
              description
                "Enables or disables FEC decoder operation.
              
                 When set to {{true}}, enables the FEC decoder
                 operation, immediately
                 ({{enum|Forced|OperationMode}} mode) or
                 automatically when necessary
                 ({{enum|Auto|OperationMode}} mode).
              
                 When set to {{false}}, disables the FEC decoder
                 operation.";
            }
            leaf OperationMode {
              type enumeration {
                enum "Auto";
                enum "Forced";
              }
              description
                "The operation mode of the FEC decoder.  {{enum}}
              
                 In {{enum|Auto}} mode, when Error Correction is
                 enabled the STB decides whether or not to run
                 the AL_FEC decoding (e.g.  after an error
                 analysis).
              
                 In {{enum|Forced}} mode, when Error Correction
                 is enabled the STB MUST run the FEC decoding.";
            }
            leaf ECOperationStatus {
              type enumeration {
                enum "Disabled";
                enum "Auto mode EC On";
                enum "Auto mode EC Off without buffering";
                enum "Auto mode EC Off with buffering";
                enum "Forced mode EC On";
                enum "Error";
              }
              config false;
              description
                "The status of FEC decoder operation.  {{enum}}
              
                 The {{enum|Error}} value MAY be used by the CPE
                 to indicate a locally defined error condition.";
            }
          }

          container IGMP {
            description
              "Parameters that are specific to IGMP clients when
               changing channels.";
            leaf Enable {
              type boolean;
              description
                "Enables or disables all IGMP support on the
                 receiver side of the CPE.";
            }
            leaf Status {
              type enumeration {
                enum "Disabled";
                enum "Enabled";
                enum "Error";
              }
              config false;
              description
                "Status of IGMP support on the receiver side of the
                 CPE.  {{enum}}
              
                 The {{enum|Error}} value MAY be used by the CPE
                 to indicate a locally defined error condition.";
            }
            leaf MaximumNumberOfConcurrentGroups {
              type uint32;
              config false;
              description
                "Maximum number of group memberships allowed
                 simultaneously.
              
                 For example, this would need to be at least 2 in
                 order to support a Multicast-delivered main
                 picture and a Multicast-delivered PIP.";
            }
            leaf MaximumNumberOfTrackedGroups {
              type uint32;
              config false;
              description
                "Maximum number of groups for which statistics will
                 be tracked.
              
                 This relates only to the maintenance of
                 statistics, and does not affect the operation of
                 the STB.";
            }
            leaf LoggingEnable {
              type boolean;
              description
                "Controls logging of IGMP traffic.
              
                 The CPE MAY choose to throttle log entries, e.g.
                 if joins and leaves are occurring at an
                 excessive rate.";
            }
            leaf DSCPMark {
              type uint32 {
                range "0..63";
              }
              description
                "Diffserv code point to be used for outgoing IGMP
                 packets.";
            }
            leaf VLANIDMark {
              type int32 {
                range "-1..max";
              }
              description
                "VLAN ID (as defined in 802.1Q) to be used for
                 outgoing IGMP packets.  A value of -1 indicates
                 the default value is to be used.
              
                 If either the {{param}} or
                 {{param|EthernetPriorityMark}} is greater than
                 zero, then the outgoing frames MUST be tagged.
                 Otherwise, the outgoing frames MAY be tagged or
                 untagged.";
            }
            leaf EthernetPriorityMark {
              type int32 {
                range "-1..max";
              }
              description
                "Ethernet priority code (as defined in 802.1D) to be
                 used for outgoing IGMP packets.  A value of -1
                 indicates the default value is to be used.
              
                 If either the {{param|VLANIDMark}} or {{param}}
                 are greater than zero, then the outgoing frames
                 MUST be tagged.  Otherwise, the outgoing frames
                 MAY be tagged or untagged.";
            }
            leaf ClientVersion {
              type enumeration {
                enum "v1";
                enum "v2";
                enum "v3";
              }
              config false;
              description
                "The highest IGMP version supported by the IGMP
                 Client.";
            }
            leaf ClientRobustness {
              type uint32;
              description
                "Robustness is a way of indicating how vulnerable
                 the network is to lost packets.  IGMP can
                 recover from robustness minus 1 lost IGMP
                 packets.
              
                 RFC 3376 specifies a default of 2.";
            }
            leaf ClientUnsolicitedReportInterval {
              type uint32 {
                range "1..25";
              }
              description
                "The number of {{units}} between repetitions of a
                 host's initial report of membership in a group.
              
                 RFC 3376 specifies a default of 1s.";
            }

            list ClientGroup {
              key "GroupAddress";
              config false;
              description
                "IGMP Group table.  This is the database that is
                 maintained by the IGMP client to reflect the
                 current group membership.
              
                 The CPE MUST support at least
                 ''MaximumNumberOfConcurrentGroups'' table
                 entries.";
              leaf GroupAddress {
                type types:IPAddress;
                description
                  "The IP multicast group address for which this
                   entry contains information.";
              }
              leaf UpTime {
                type uint32;
                description
                  "Time elapsed in {{units}} since the multicast
                   group has been a member on this interface.";
              }
            }

            list ClientGroupStats {
              key "GroupAddress";
              config false;
              description
                "IGMP Group statistics table.  This stores per-group
                 historical statistical data.
              
                 The CPE MUST support at least
                 ''MaximumNumberOfTrackedGroups'' table entries.
                 The CPE MAY reclaim entries based on the oldest
                 membership reports.";
              leaf GroupAddress {
                type types:IPAddress;
                description
                  "The IP multicast group address for which this
                   entry contains information.";
              }
              leaf TotalStart {
                type uint32;
                description
                  "Number of {{units}} since the beginning of the
                   period used for collection of {{object|Total}}
                   statistics.
                
                   Statistics SHOULD continue to be accumulated
                   across CPE reboots, though this may not always
                   be possible.";
              }
              leaf CurrentDayStart {
                type uint32;
                description
                  "Number of {{units}} since the beginning of the
                   period used for collection of
                   {{object|CurrentDay}} statistics.
                
                   The CPE MAY align the beginning of each
                   {{object|CurrentDay}} interval with days in
                   the UTC time zone, but is not required to do
                   so.
                
                   Statistics SHOULD continue to be accumulated
                   across CPE reboots, though this may not always
                   be possible.";
              }
              leaf QuarterHourStart {
                type uint32;
                description
                  "Number of {{units}} since the beginning of the
                   period used for collection of
                   {{object|QuarterHour}} statistics.
                
                   The CPE MAY align the beginning of each
                   {{object|QuarterHour}} interval with real-time
                   quarter-hour intervals, but is not required to
                   do so.
                
                   Statistics SHOULD continue to be accumulated
                   across CPE reboots, though this may not always
                   be possible.";
              }

              container Total {
                description
                  "Total statistics for this multicast group.";
                leaf NumberOfJoins {
                  type uint32;
                  description
                    "Number of IGMP joins during this period.";
                }
                leaf NumberOfLeaves {
                  type uint32;
                  description
                    "Number of IGMP leaves during this period.";
                }
                leaf MaxJoinDelay {
                  type uint32;
                  description
                    "Maximum latency delay, in {{units}}, from the
                     sending of a Join message for this group to
                     the arrival of the first IP packet for this
                     group during this period.";
                }
              }

              container CurrentDay {
                description
                  "Current day statistics for this multicast group.";
                leaf NumberOfJoins {
                  type uint32;
                  description
                    "Number of IGMP joins during this period.";
                }
                leaf NumberOfLeaves {
                  type uint32;
                  description
                    "Number of IGMP leaves during this period.";
                }
                leaf MaxJoinDelay {
                  type uint32;
                  description
                    "Maximum latency delay, in {{units}}, from the
                     sending of a Join message for this group to
                     the arrival of the first IP packet for this
                     group during this period.";
                }
              }

              container QuarterHour {
                description
                  "Current quarter hour statistics for this
                   multicast group.";
                leaf NumberOfJoins {
                  type uint32;
                  description
                    "Number of IGMP joins during this period.";
                }
                leaf NumberOfLeaves {
                  type uint32;
                  description
                    "Number of IGMP leaves during this period.";
                }
                leaf MaxJoinDelay {
                  type uint32;
                  description
                    "Maximum latency delay, in {{units}}, from the
                     sending of a Join message for this group to
                     the arrival of the first IP packet for this
                     group during this period.";
                }
              }
            }
          }

          container Dejittering {
            description
              "Parameters related to the de-jittering buffer
               configuration for all inbound IP streams.";
            leaf BufferSize {
              type uint32;
              description
                "De-jittering buffer size, measured in {{units}}, on
                 the receiver side of the CPE.  The STB is
                 responsible for converting this into the actual
                 buffer size in ''bytes''.";
            }
            leaf BufferInitialLevel {
              type uint32;
              description
                "Describes the number of {{units}} worth of data
                 that should be in the receiver side dejittering
                 buffer before play-out can start.  Typically
                 this would be half of the buffer size.";
            }
          }

          list Inbound {
            key "Name";
            config false;
            description
              "Inbound IP streams currently entering the STB via
               this front-end.";
            leaf Status {
              type enumeration {
                enum "Disabled";
                enum "Enabled";
                enum "Error";
              }
              description
                "The status of this Inbound stream.  {{enum}}
              
                 The {{enum|Error}} value MAY be used by the CPE
                 to indicate a locally defined error condition.";
            }
            leaf Name {
              type string {
                length "0..256";
              }
              description
                "Unique human-readable name associated with this
                 inbound IP instance.";
            }
            leaf StreamingControlProtocol {
              type string;
              description
                "Network protocol currently used for controlling
                 streaming of the source content, or {{empty}} if
                 the content is not being streamed or is being
                 streamed but is not being controlled.";
            }
            leaf StreamingTransportProtocol {
              type string;
              description
                "Network protocol currently used for streaming the
                 source content, or an empty string if the
                 content is not being streamed.";
            }
            leaf StreamingTransportControlProtocol {
              type string;
              description
                "Transport control protocol currently used for
                 streaming the source content, or an empty string
                 if the content is not being streamed.";
            }
            leaf MultiplexType {
              type string;
              description
                "AV multiplex type currently used for the source
                 content, or an empty string if the content is
                 not being demultiplexed.";
            }
            leaf DownloadTransportProtocol {
              type string;
              description
                "Network protocol currently used for downloading the
                 source content, or an empty string if the
                 content is not being downloaded.";
            }
            leaf SourceAddress {
              type types:IPAddress;
              description
                "IP address of the source of the current stream
                 content.";
            }
            leaf SourcePort {
              type uint32 {
                range "0..65535";
              }
              description
                "TCP or UDP port number of the source of the current
                 stream content, or 0 if the content is not being
                 delivered via IP or if not applicable.";
            }
            leaf DestinationAddress {
              type types:IPAddress;
              description
                "IP address of the destination of the current stream
                 content, or {{empty}} if the content is not
                 being delivered via IP.";
            }
            leaf DestinationPort {
              type uint32 {
                range "0..65535";
              }
              description
                "TCP or UDP port number of the destination of the
                 current stream content, or 0 if the content is
                 not being delivered via IP or if not applicable.";
            }
            leaf URI {
              type string {
                length "0..256";
              }
              description
                "RFC 3986 URI that indicates the current source
                 (possibly including Multicast group and port, if
                 relevant) of the stream content, or {{empty}} if
                 the source is not known or cannot be represented
                 as a URI.
              
                 For example, for a WAN-delivered stream this
                 might be a content provider's URL, or for a
                 LAN-delivered stream it might be an UPnP AV URN.
              
                 If specified, the URI MUST be consistent with
                 the other source-related parameters.";
            }
          }

          list Outbound {
            key "Name";
            config false;
            description
              "Parameters related to an outbound IP stream.";
            leaf Status {
              type enumeration {
                enum "Disabled";
                enum "Enabled";
                enum "Error";
              }
              description
                "The status of this Outbound stream.  {{enum}}
              
                 The {{enum|Error}} value MAY be used by the CPE
                 to indicate a locally defined error condition.";
            }
            leaf Name {
              type string {
                length "0..256";
              }
              description
                "Unique human-readable name associated with this
                 outbound IP instance.";
            }
            leaf MultiplexType {
              type string;
              description
                "AV multiplex type currently used for the
                 destination content, or an empty string if the
                 content is not being demultiplexed.";
            }
            leaf URI {
              type string {
                length "0..256";
              }
              description
                "RFC 3986 URI that indicates the current destination
                 (possibly including Multicast group and port, if
                 relevant) of the stream content, or an empty
                 string if the destination is not known or cannot
                 be represented as a URI.
              
                 For example, this might be an UPnP AV URN.";
            }
          }

          container ServiceConnect {
            description
              "Parameters used to force connection to a dedicated IP
               stream for test purposes.";
            leaf URI {
              type string {
                length "0..256";
              }
              description
                "RFC 3986 URI that describes the service to connect
                 to in the form:
              
                 *
                 <trsp>://<addr>:<port>?StrCtrl=<strctrl>?StrTrspCtrl=<trspctrl>?MuxType=<muxtype>
              
                 where:
              
                 * '''<addr>''' is the IP address of the service
                 source (for Unicast) or IGMP group (for
                 Multicast).
              
                 * '''<port>''' is the associated TCP/UDP port.
                 If not specified, the STB is assumed to know and
                 use an appropriate default port.
              
                 * '''<trsp>''' is the streaming transport
                 protocol and MUST be one of the values in
                 {{param|.Capabilities.FrontEnd.IP.StreamingTransportProtocols}},
                 which SHOULD be converted to lower-case.
              
                 * '''<strctrl>''' is the streaming control
                 protocol and MUST be one of the values in
                 {{param|.Capabilities.FrontEnd.IP.StreamingControlProtocols}}.
                 If not specified, no streaming control protocol
                 is to be used.
              
                 * '''<trspctrl>''' is the streaming transport
                 control protocol and MUST be one of the values
                 in
                 {{param|.Capabilities.FrontEnd.IP.StreamingTransportControlProtocols}}.
                 If not specified, no streaming transport control
                 protocol is to be used.
              
                 * '''<muxtype>''' is the multiplex type and MUST
                 be one of the values in
                 {{param|.Capabilities.FrontEnd.IP.MultiplexTypes}}.
                 This tells the STB which multiplex type to
                 expect.  If not specified, the STB is assumed to
                 know, or to be able to determine, the multiplex
                 type.
              
                 Note that download protocols are not supported
                 by the above syntax.  However, the specified
                 syntax is just a baseline, and STBs MAY support
                 an extended syntax.
              
                 Example of Multicast MPEG2-TS over RTP with no
                 transport control:
              
                 *
                 rtp://224.112.15.18:3257?StrCtrl=IGMP?MuxType=MPEG2-TS
              
                 Example of Multicast MPEG2-TS over RTP with
                 AL-FEC transport control:
              
                 *
                 rtp://224.112.15.18:3257?StrCtrl=IGMP?StrTrspCtrl=AL-FEC?MuxType=MPEG2-TS
              
                 Example of Unicast MPEG2-TS over UDP with RTSP
                 transport control:
              
                 *
                 udp://174.146.35.12:3257?StrCtrl=RTSP?MuxType=MPEG2-TS
              
                 Example of Unicast raw AV over RTP with RTCP
                 control and RTSP transport control:
              
                 *
                 rtp://174.146.35.12:3257?StrCtrl=RTSP?StrTrspCtrl=RTCP?MuxType=None
              
                 If a {{object|.ServiceMonitoring.MainStream}}
                 instance with ''ServiceType'' = ''IP'' or
                 ''IPTV'' (or ''VoD'' if the URI accesses a VoD
                 service) is currently enabled, the STB MUST
                 ensure that performance data for this service is
                 collected in that instance.
              
                 The value is not saved in device state.  The
                 value when read is not specified and need not be
                 the value that was most recently written.";
            }
          }

          container ForceMonitor {
            description
              "Parameters used to describe the force monitoring
               operation.
            
               When running in the force monitoring mode, the STB
               MUST automatically connect to a test URI defined
               by the {{param|URI}} parameter whenever it detects
               that the IP tuner is not not receiving any data
               from the WAN.
            
               When running in normal mode, the STB does not
               perform any action when it does not receive any
               data from the IP tuner coming from the WAN.
            
               The force monitor mode allows to maintain an
               active stream coming from the network so as to
               keep collecting statistics.";
            leaf Enable {
              type boolean;
              description
                "When set to {{true}}, forces the operation mode in
                 ForceMonitor mode
              
                 When set to {{false}}, forces operation mode in
                 Normal mode.";
            }
            leaf Status {
              type enumeration {
                enum "Normal";
                enum "Force Monitor";
              }
              config false;
              description
                "Indicates the status of the statistic mode of
                 operation.  {{enum}}";
            }
            leaf URI {
              type string {
                length "0..256";
              }
              description
                "describes the service to connect to for force
                 monitoring purposes with the same syntaxt as
                 {{param|#.ServiceConnect.URI}}
              
                 If a {{object|.ServiceMonitoring.MainStream}}
                 instance with ''ServiceType'' = ''TEST'' or
                 ''IP-All'' is currently enabled, the STB MUST
                 ensure that performance data for this service is
                 collected in that instance.
              
                 The value when read is not specified and need
                 not be the value that was most recently written.";
            }
          }
        }
      }

      container PVR {
        config false;
        description
          "PVR details.  This is a read-only object that exists only
           to reference PVR storage objects.";

        list Storage {
          key "Name";
          description
            "PVR storage table.  There MUST be an instance for each
             storage object that can be accessed by the PVR.
             Entries MAY be dynamically created and deleted as
             storage devices become available and unavailable.";
          leaf Name {
            type string {
              length "0..256";
            }
            description
              "Unique human-readable name associated with this
               storage instance.";
          }
          leaf Reference {
            type string {
              length "0..256";
            }
            description
              "References the corresponding ''StorageService''
               {{bibref|TR-140}} instance, or an object contained
               within such an instance, e.g.  a
               ''PhysicalMedium'', ''LogicalVolume'' or
               ''Folder'' instance.
            
               The value is the full hierarchical name of the
               corresponding object.  Example:
               ''Device.Services.StorageService.1''";
          }
        }
      }

      list AudioDecoder {
        key "Name";
        description
          "Audio decoder instance table.  It contains data
           representing the current status of the Audio decoder.";
        leaf Enable {
          type boolean;
          description
            "Enables or disables this audio decoder.";
        }
        leaf Status {
          type enumeration {
            enum "Disabled";
            enum "Enabled";
            enum "Error";
          }
          config false;
          description
            "The status of this audio decoder.  {{enum}}
          
             The {{enum|Error}} value MAY be used by the CPE to
             indicate a locally defined error condition.";
        }
        leaf Name {
          type string {
            length "0..256";
          }
          config false;
          description
            "Human-readable name associated with this audio decoder.";
        }
        leaf AudioStandard {
          type string;
          config false;
          description
            "Audio standard currently being processed by this audio
             decoder, or an empty string if no audio standard is
             currently being processed.";
        }
      }

      list VideoDecoder {
        key "Name";
        description
          "Video decoder instance table.  It contains data
           representing the current status of the video decoder.";
        leaf Enable {
          type boolean;
          description
            "Enables or disables this video decoder.";
        }
        leaf Status {
          type enumeration {
            enum "Disabled";
            enum "Enabled";
            enum "Error";
          }
          config false;
          description
            "The status of this video decoder.  {{enum}}
          
             The {{enum|Error}} value MAY be used by the CPE to
             indicate a locally defined error condition.";
        }
        leaf Name {
          type string {
            length "0..256";
          }
          config false;
          description
            "Human-readable name associated with this video decoder.";
        }
        leaf MPEG2Part2 {
          type string {
            length "0..256";
          }
          config false;
          description
            "MPEG2 Part 2 profile and level object instance, or
             {{empty}} if MPEG2 Part 2 is not used.  For example:
          
             ''.Capabilities.VideoDecoder.MPEG2Part2.ProfileLevel.2''";
        }
        leaf MPEG4Part2 {
          type string {
            length "0..256";
          }
          config false;
          description
            "MPEG4 Part 2 profile and level object instance, or
             {{empty}} if MPEG4 Part 2 is not used).  For
             example:
          
             ''.Capabilities.VideoDecoder.MPEG4Part2.ProfileLevel.2''";
        }
        leaf MPEG4Part10 {
          type string {
            length "0..256";
          }
          config false;
          description
            "MPEG4 Part 10 profile and level object instance, or
             {{empty}} if MPEG4 Part 10 is not used.  For
             example:
          
             ''.Capabilities.VideoDecoder.MPEG4Part10.ProfileLevel.2''";
        }
        leaf SMPTEVC1 {
          type string {
            length "0..256";
          }
          config false;
          description
            "SMPTE-VC-1 profile and level object instance, or
             {{empty}} if SMPTE-VC-1 is not used.  For example:
          
             ''.Capabilities.VideoDecoder.SMPTEVC1.ProfileLevel.2''";
        }
        leaf ContentAspectRatio {
          type enumeration {
            enum "4:3";
            enum "16:9";
          }
          config false;
          description
            "Indicates the native aspect ratio of the content
             available at this decoder.";
        }
      }

      list AudioOutput {
        key "Name";
        description
          "Audio output instance table.";
        leaf Enable {
          type boolean;
          description
            "Enables or disables this audio output.";
        }
        leaf Status {
          type enumeration {
            enum "Disabled";
            enum "Enabled";
            enum "Muted";
            enum "Error";
          }
          config false;
          description
            "The status of this audio output.  {{enum}}
          
             The {{enum|Error}} value MAY be used by the CPE to
             indicate a locally defined error condition.";
        }
        leaf Name {
          type string {
            length "0..256";
          }
          config false;
          description
            "Human-readable name associated with this audio output.";
        }
        leaf AudioFormat {
          type string;
          config false;
          description
            "Currently active audio output format, or {{empty}} if
             no audio output format is currently active.
          
             Note that this parameter refers to output formats
             and not to physical connectors.";
        }
        leaf AudioLevel {
          type uint32 {
            range "0..100";
          }
          description
            "The audio level on this audio output in {{units}} (0 is
             quietest and 100 is loudest).  This setting is
             independent of the mute status.
          
             For some audio formats, the audio level is not
             meaningful, in which case this parameter SHOULD have
             a fixed value of 0.";
        }
        leaf CancelMute {
          type boolean;
          description
            "When set to {{true}}, cancels this audio output's mute
             status.  Setting it to {{false}} has no effect.  The
             value is not saved in device state and is always
             {{false}} when read.";
        }
        leaf SCARTs {
          type string;
          config false;
          description
            "SCART object instances associated with this audio
             output, or {{empty}} if not associated with any
             SCART object instances.  For example:
          
             * ''.Components.SCART.2''
          
             * ''.Components.SCART.2,.Components.SCART.3''";
        }
      }

      list SPDIF {
        key "Name";
        description
          "S/PDIF output instance table configuration.  This object,
           if present, is connected to the audio ouput instance
           currently delivering S/PDIF audio format as described
           in {{bibref|SPDIF}}.";
        leaf Enable {
          type boolean;
          description
            "Enables or disables the S/PDIF output.";
        }
        leaf Status {
          type enumeration {
            enum "Disabled";
            enum "Enabled";
            enum "Error";
          }
          config false;
          description
            "The status of this S/PDIF output.  {{enum}}
          
             The {{enum|Error}} value MAY be used by the CPE to
             indicate a locally defined error condition.";
        }
        leaf Name {
          type string {
            length "0..256";
          }
          config false;
          description
            "Human-readable name associated with this output.";
        }
        leaf ForcePCM {
          type boolean;
          description
            "When set to {{true}}, forces the audio format over
             S/PDIF to be in PCM mode.
          
             When set to {{false}}, let the compressed audio
             format be carried over S/PDIF (passthrough).";
        }
        leaf Passthrough {
          type boolean;
          config false;
          description
            "When in Passthrough mode, the STB sends the audio
             stream over S/PDIF without decoding it.";
        }
        leaf AudioDelay {
          type uint32;
          config false;
          description
            "Audio delay value, in {{units}}, currently being
             applied to the audio stream on the S/PDIF interface.
             The audio delay is entered by the user via his local
             UI, when necessary for correcting the lipsync.";
        }
      }

      list VideoOutput {
        key "Name";
        description
          "Video output instance table.";
        leaf Enable {
          type boolean;
          description
            "Enables or disables this video output.";
        }
        leaf Status {
          type enumeration {
            enum "Disabled";
            enum "Enabled";
            enum "ColorbarEnabled";
            enum "Error";
          }
          config false;
          description
            "The status of this video output.  {{enum}}
          
             The {{enum|Error}} value MAY be used by the CPE to
             indicate a locally defined error condition.";
        }
        leaf ColorbarEnable {
          type boolean;
          description
            "Enables or disables the color bar display.
          
             When set to {{true}}, the CPE MUST suspend the
             running service currently using the video output
             (e.g.  IPTV broadcast reception) and MUST display
             the color bar.
          
             When set to {{false}}, the CPE MUST resume the
             previousely running service.
          
             This parameter MUST be always initialized with the
             value {{false}} on STB boot.";
        }
        leaf Name {
          type string {
            length "0..256";
          }
          config false;
          description
            "Human-readable name associated with this Video output.";
        }
        leaf CompositeVideoStandard {
          type string;
          config false;
          description
            "The type of analog video standard currently in use or
             {{empty}} if no analog video standard is currently
             in use.
          
             Note that this parameter applies only to the CVBS
             output format.";
        }
        leaf VideoFormat {
          type string;
          description
            "Currently active video output format, or {{empty}} if
             no video output format is currently active.
          
             Note that this parameter refers to output formats
             and not to physical connectors.";
        }
        leaf AspectRatioBehaviour {
          type enumeration {
            enum "None";
            enum "Letterbox";
            enum "16:9 Letterbox";
            enum "14:9 Letterbox";
            enum "CenterCutOut";
            enum "Combined";
            enum "Combined 16:9 Letterbox and CenterCutOut";
            enum "Combined 14:9 Letterbox and CenterCutOut";
          }
          config false;
          description
            "Indicates the aspect ratio behaviour for display on
             monitors with an aspect ratio different from that of
             the content, which is specified in
             {{param|.Components.VideoDecoder.{i}.ContentAspectRatio}}.";
        }
        leaf DisplayFormat {
          type string;
          description
            "Display format being connected to this VideoOutput.
          
             This parameter is used by the STB to determine
             whether an aspect ratio conversion is required.";
        }
        leaf Macrovision {
          type boolean;
          config false;
          description
            "Indicates whether Macrovision analog protection is
             being used on this video output.
          
             The Macrovision version supported is indicated in
             {{param|.Capabilities.VideoOutput.Macrovision}}.";
        }
        leaf HDCP {
          type boolean;
          config false;
          description
            "Indicates whether HDCP is being used on this video
             output.
          
             The HDCP version supported is indicated in
             {{param|.Capabilities.VideoOutput.HDCP}}.";
        }
        leaf SCARTs {
          type string;
          config false;
          description
            "SCART object instances associated with this video
             output, or {{empty}} if not associated with any
             SCART object instances.  For example:
          
             * ''.Components.SCART.2''
          
             * ''.Components.SCART.2,.Components.SCART.3''";
        }
      }

      list SCART {
        key "Name";
        description
          "SCART configuration.  This object allows configuration of
           the STB's AV switching.";
        leaf Enable {
          type boolean;
          description
            "Enables or disables this SCART connector.";
        }
        leaf Status {
          type enumeration {
            enum "Disabled";
            enum "Enabled";
            enum "Error";
          }
          config false;
          description
            "The status of this SCART connector.  {{enum}}
          
             The {{enum|Error}} value MAY be used by the CPE to
             indicate a locally defined error condition.";
        }
        leaf Name {
          type string {
            length "0..256";
          }
          config false;
          description
            "Human-readable name associated with this connector.";
        }
        leaf Presence {
          type boolean;
          description
            "Enables or disables the Presence control signal (pin 8
             of the SCART connector), an output from the STB to
             control the display device connected to the SCART.
          
             When enabled (set to {{true}}) the STB MUST drive
             pin 8 to the appropriate level to indicate the
             output video format (SD or HD) to the connected
             device.
          
             When disabled (set to {{false}}) the STB MUST NOT
             drive pin 8.";
        }
      }

      list HDMI {
        key "Name";
        description
          "HDMI instance table.  This object allows configuration of
           the STB’s HDMI output.";
        leaf Enable {
          type boolean;
          description
            "Enables or disables the HDMI output.";
        }
        leaf Status {
          type enumeration {
            enum "Disabled";
            enum "Enabled";
            enum "Error";
          }
          config false;
          description
            "The status of HDMI output.  {{enum}}
          
             The {{enum|Error}} value MAY be used by the CPE to
             indicate a locally defined error condition.";
        }
        leaf Name {
          type string {
            length "0..256";
          }
          config false;
          description
            "Human-readable name associated with this output.";
        }
        leaf ResolutionMode {
          type enumeration {
            enum "Auto";
            enum "Manual";
          }
          description
            "The resolution mode of the HDMI output.
          
             In {{enum|Auto}} mode, the resolution is
             automatically set at the best format via HDMI
             protocols.
          
             In {{enum|Manual}} mode, the resolution to be
             applied to the HDMI output is given by the
             ResolutionValue parameter.";
        }
        leaf ResolutionValue {
          type string;
          description
            "When {{param|ResolutionMode}} is set to
             {{enum|Manual|ResolutionMode}} mode, a write action
             configures the resolution to be applied to the HDMI
             output,
          
             When {{param|ResolutionMode}} is set to
             {{enum|Auto|ResolutionMode}}, a write action as no
             effect.
          
             A read action provides the current resolution of the
             HDMI output.";
        }

        container DisplayDevice {
          config false;
          description
            "HDMI connected display device configuration.  This
             object provides parameters from the HDMI connected
             device if any.";
          leaf Status {
            type enumeration {
              enum "Present";
              enum "None";
              enum "Error";
            }
            description
              "The status of the connected HDMI Display device.
               {{enum}}
            
               The {{enum|Error}} value MAY be used by the CPE to
               indicate a locally defined error condition.";
          }
          leaf Name {
            type string {
              length "0..256";
            }
            description
              "Human-readable name associated with this display
               device.";
          }
          leaf EEDID {
            type yang:hex-string {
              length "0..256";
            }
            description
              "Enhanced Extended Display Information Data (E-EDID)
               retrieved from the connected HDMI device.";
          }
          leaf SupportedResolutions {
            type string;
            description
              "Each entry is a supported resolution of the connected
               HDMI device and MUST be one element of
               {{param|.Capabilities.HDMI.SupportedResolutions}}.";
          }
          leaf PreferredResolution {
            type string;
            description
              "Preferred connected HDMI device resolution format.";
          }
          leaf VideoLatency {
            type uint32;
            description
              "Video latency, in {{units}}, being applied in the
               connected HDMI device.  This parameter is
               extracted from the E-EDID and can be used to
               compensate the video latency to preserve lipsync.";
          }
          leaf CECSupport {
            type boolean;
            description
              "When set to {{true}}, indicates the connected HDMI
               device is supporting HDMI-CEC features.
            
               When set to {{false}}, indicates the connected
               HDMI device does not support HDMI CEC.";
          }
          leaf AutoLipSyncSupport {
            type boolean;
            description
              "When set to {{true}}, indicates the connected display
               device supports auto lip synchronization.  This
               mode consists in communicating over HDMI, the
               delay to be applied by the STB to the audio in
               order to preserve the lip sync.";
          }
          leaf HDMI3DPresent {
            type boolean;
            description
              "When set to {{true}}, indicates the connected display
               device supports the 3D video formats mandated by
               {{bibref|HDMI}}.";
          }
        }
      }

      list CA {
        key "Name";
        description
          "This object describes the characteristics of the
           Conditional Access, if any.";
        leaf Enable {
          type boolean;
          description
            "Enables or disables this CA system.";
        }
        leaf Status {
          type enumeration {
            enum "Disabled";
            enum "Enabled";
            enum "Error";
          }
          config false;
          description
            "The status of this CA system.  {{enum}}
          
             The {{enum|Error}} value MAY be used by the CPE to
             indicate a locally defined error condition.";
        }
        leaf Name {
          type string {
            length "0..256";
          }
          config false;
          description
            "Indicates a unique identifier (e.g.  the commercial
             name: ''La 7 piu'', ''Mediaset Premium'') for this
             CA system.";
        }
        leaf SmartCardReader {
          type string {
            length "0..256";
          }
          config false;
          description
            "Path name of the smart card reader object instance
             containing the smart card (if any) associated with
             this CA system.
          
             The value MUST be {{empty}} (if not associated with
             a smart card) or else be the full path name of the
             corresponding smart card reader object.  For
             example:
          
             ''Device.SmartCardReader.1''";
        }
      }

      list DRM {
        key "Name";
        description
          "This object describes the characteristics of the Digital
           Rights Management, if any.";
        leaf Enable {
          type boolean;
          description
            "Enables or disables this DRM system.";
        }
        leaf Status {
          type enumeration {
            enum "Disabled";
            enum "Enabled";
            enum "Error";
          }
          config false;
          description
            "The status of this DRM system.  {{enum}}
          
             The {{enum|Error}} value MAY be used by the CPE to
             indicate a locally defined error condition.";
        }
        leaf Name {
          type string {
            length "0..256";
          }
          config false;
          description
            "Indicates a unique identifier (e.g.  the commercial
             name: ''La 7 piu'', ''Mediaset Premium'') for this
             DRM system.";
        }
        leaf SmartCardReader {
          type string {
            length "0..256";
          }
          config false;
          description
            "Path name of the smart card reader object instance
             containing the smart card (if any) associated with
             this DRM system.
          
             The value MUST be {{empty}} (if not associated with
             a smart card) or else be the full path name of the
             corresponding smart card reader object.  For
             example:
          
             ''Device.SmartCardReader.1''";
        }
      }
    }

    container AVStreams {
      config false;
      description
        "AV Streams object.  If more than one AV stream can be
         active at a time, it may contain several
         {{object|AVStream}} instances.";
      leaf ActiveAVStreams {
        type uint32;
        description
          "Number of AV streams currently active (i.e.  with
           ''Status'' != ''Disabled'', which means audio or AV
           data are being processed).";
      }

      list AVStream {
        key "Name";
        description
          "Details of each AVStream.  AV streams are created
           statically.  Each AV stream corresponds to a valid
           ''{FrontEnd, AudioDecoder, VideoDecoder}'' instance
           combination (although if the PVR is active for this
           stream, only ''{FrontEnd}'' or ''{AudioDecoder,
           VideoDecoder}'' will be in use).";
        leaf Status {
          type enumeration {
            enum "Disabled";
            enum "Enabled";
            enum "Error_PVRWriteFailure";
            enum "Error_PVRReadFailure";
            enum "Error";
          }
          description
            "The status of this AV stream.  {{enum}}
          
             An AV stream is disabled if any of the referenced
             objects are disabled.
          
             If an AV stream is disabled then the values of other
             AV stream parameters are not significant.
          
             The {{enum|Error}} value MAY be used by the CPE to
             indicate a locally defined error condition.";
        }
        leaf Name {
          type string {
            length "0..256";
          }
          description
            "Human-readable name associated with this stream, e.g.
             read from the DVB service information metadata.";
        }
        leaf PVRState {
          type enumeration {
            enum "Disabled";
            enum "Stopped";
            enum "Play";
            enum "Paused";
            enum "FastForward";
            enum "Rewind";
          }
          description
            "Indicates whether this stream is using the PVR and, if
             so, the PVR state.  {{enum}}
          
             PVR record state can be inferred from whether the
             stream has an input FrontEnd: if so and {{param}} is
             not {{enum|Disabled}}, the PVR is recording.";
        }
        leaf FrontEnd {
          type string {
            length "0..256";
          }
          description
            "Input FrontEnd object instance associated with this AV
             stream, or {{empty}} if not associated with a
             FrontEnd object).  For example:
          
             ''.Components.FrontEnd.2''";
        }
        leaf Inbound {
          type string {
            length "0..256";
          }
          description
            "Inbound IP stream object instance associated with the
             FrontEnd for this AV stream, or {{empty}} if the
             inbound stream is not delivered over IP.  For
             example:
          
             ''.Components.FrontEnd.2.IP.Inbound.3''";
        }
        leaf Outbound {
          type string {
            length "0..256";
          }
          description
            "Outbound IP stream object instance associated with the
             output FrontEnd for this AV stream (which is always
             the IP FrontEnd), or {{empty}} if the outbound
             stream is not delivered over IP.  For example:
          
             ''.Components.FrontEnd.2.IP.Outbound.3''";
        }
        leaf AudioDecoder {
          type string {
            length "0..256";
          }
          description
            "Audio Decoder object instance associated with this AV
             stream, or {{empty}} if not associated with an Audio
             Decoder object.  For example:
          
             ''.Components.AudioDecoder.2''";
        }
        leaf VideoDecoder {
          type string {
            length "0..256";
          }
          description
            "Video Decoder object instance associated with this AV
             stream, or {{empty}} if not associated with a Video
             Decoder object.  For example:
          
             ''.Components.VideoDecoder.2''";
        }
        leaf CA {
          type string {
            length "0..256";
          }
          description
            "CA system object instance associated with this AV
             stream, or {{empty}} if not associated with a CA
             object.  For example:
          
             ''.Components.CA.2''";
        }
        leaf DRM {
          type string {
            length "0..256";
          }
          description
            "DRM system object instance associated with this AV
             stream, or {{empty}} if not associated with a DRM
             object.  For example:
          
             ''.Components.DRM.2''";
        }
      }
    }

    container AVPlayers {
      description
        "AV Players object.  If more than one AV player can be
         active at a time, it may contain several
         {{object|AVPlayer}} instances.
      
         AV players are created statically.  Each AV player
         corresponds to a combination of several AV streams (one
         main screen video, several PIP, one audio) being
         connected to an AV presentation device (such as a TV
         set).
      
         There is no guarantee that the STB has the resources to
         enable all of its AV players at the same time.";
      leaf ActiveAVPlayers {
        type uint32;
        config false;
        description
          "Number of AV players currently active (i.e.  with
           ''Status'' != ''Disabled'', which means the
           {{object|AVPlayer}} is processing an audio or AV
           stream).";
      }
      leaf PreferredAudioLanguage {
        type string {
          length "0..64";
        }
        description
          "Human-readable string, as specified in
           {{bibref|RFC3066}}, describing the audio language that
           SHOULD be used by the STB when receiving a
           multi-language audio multiplex.
        
           {{empty}} indicates that there is no preferred audio
           language.";
      }
      leaf PreferredSubtitlingLanguage {
        type string {
          length "0..64";
        }
        description
          "Human-readable string, as specified in
           {{bibref|RFC3066}}, describing the subtitling language
           that SHOULD be used by the STB when receiving
           multi-language subtitling.
        
           A value of ''None'' indicates that no subtitling is
           required.
        
           {{empty}} indicates that there is no preferred
           subtitling language.";
      }
      leaf PreferredBehaviour {
        type string {
          length "0..64";
        }
        description
          "Aspect ratio behaviour preference for display on monitor.
        
           If non-empty, the string MUST be one of the
           .Components.VideoOutput.{i}.  AspectRatioBehaviour
           values.";
      }
      leaf ResetPINCode {
        type boolean;
        description
          "When set to {{true}}, the master PIN code for the STB is
           set to 0000.  Setting it to {{false}} has no effect.
           The value is not saved in device state and is always
           {{false}} when read.  It is not recommended that this
           be set to true without the user's permission.  No data
           on the device such as PVR recordings are to be cleared
           as a result of resetting the PIN code.";
      }

      list AVPlayer {
        key "Name";
        description
          "List of AV Player objects.  Each item is one particular
           AV player being processed by the STB.";
        leaf Enable {
          type boolean;
          description
            "Enables or disables this AV player.";
        }
        leaf Status {
          type enumeration {
            enum "Disabled";
            enum "Enabled";
            enum "Error";
          }
          config false;
          description
            "The status of this AV player.  {{enum}}
          
             If an AV player is disabled then the values of other
             AV player parameters are not significant.
          
             The {{enum|Error}} value MAY be used by the CPE to
             indicate a locally defined error condition.";
        }
        leaf Name {
          type string {
            length "0..256";
          }
          config false;
          description
            "Human-readable name associated with this AV player.";
        }
        leaf AudioLanguage {
          type string {
            length "0..64";
          }
          config false;
          description
            "Human-readable string, as specified in
             {{bibref|RFC3066}}, describing the audio language
             being currently processed by the AV player.";
        }
        leaf SubtitlingStatus {
          type enumeration {
            enum "Disabled";
            enum "Enabled";
            enum "Error";
          }
          config false;
          description
            "The status of subtitling for this AV player.  {{enum}}
          
             Subtitles are assumed to be shown only on the main
             screen.
          
             The {{enum|Error}} value MAY be used by the CPE to
             indicate a locally defined error condition.";
        }
        leaf SubtitlingLanguage {
          type string {
            length "0..64";
          }
          config false;
          description
            "Human-readable string, as specified in
             {{bibref|RFC3066}}, describing the subtitling
             language being currently processed by the AV player.
          
             Subtitles are assumed to be shown only on the main
             screen.";
        }
        leaf AudioOutputs {
          type string;
          config false;
          description
            "Audio output object instances associated with this AV
             player, or {{empty}} if not associated with any
             audio output object instances.  For example:
          
             ''.Components.AudioOutput.2''";
        }
        leaf VideoOutputs {
          type string;
          config false;
          description
            "Video output object instances associated with this AV
             player, or {{empty}} if not associated with any
             video output object instances.  For example:
          
             ''.Components.VideoOutput.2''";
        }
        leaf MainStream {
          type string {
            length "0..256";
          }
          config false;
          description
            "AV stream object instance associated with this AV
             player that is being sent to the main screen, or
             {{empty}} if not associated with an AV stream
             object.  For example:
          
             ''.AVStreams.AVStream.2''";
        }
        leaf PIPStreams {
          type string;
          config false;
          description
            "AV stream object instances associated with this AV
             player that are being displayed as Picture In
             Picture (PIP), or {{empty}} if not associated with
             any PIP AV stream objects.  For example:
          
             * ''.AVStreams.AVStream.2''
          
             * ''.AVStreams.AVStream.2,.AVStreams.AVStream.3''";
        }
      }
    }

    container ServiceMonitoring {
      description
        "Records events and collects QoS / QoE related statistics
         for Main AV streams.
      
         These statistics are broken down into categories, e.g.
         de-jittering and RTP, and for each category there are
         two types of statistics:
      
         * '''Total''' statistics, which count the number of
         occurrences of something.
      
         * '''Sample''' statistics, which are measured over a
         sample interval, and are made available to the ACS as a
         list of the most recent n samples.
      
         Total statistics are always collected (collection cannot
         be disabled, but the values can be reset).
      
         For Sample statistics, an STB uses a single sample
         interval and number of samples (n) for all
         {{object|MainStream}} instances.  The sample interval
         can be aligned with absolute time.
      
         When Sample statistics collection is enabled, statistics
         collection MUST proceed regardless of whether there are
         any active Main AV streams.  For example, even when the
         STB is not receiving any data, sample intervals will
         continue to be timed as normal.
      
         Refer to {{bibref|TR-135|I.3}} for non-normative
         explanation of the operation of the
         ''ServiceMonitoring'' object.";
      leaf SampleEnable {
        type boolean;
        description
          "Enables or disables collection of Sample statistics.
        
           When collection of Sample statistics is enabled, any
           stored samples are discarded, and the first sample
           interval begins immediately.";
      }
      leaf SampleState {
        type enumeration {
          enum "Disabled";
          enum "Enabled";
          enum "Trigger";
        }
        config false;
        description
          "Indicates availability of Sample statistics.  {{enum}}
        
           The {{enum|Trigger}} value is only used for triggering
           the ACS to fetch the collected data and can only be
           used when {{param|FetchSamples}} is in the range
           [1:{{param|ReportSamples}}].
        
           The transition from {{enum|Enabled}} ->
           {{enum|Trigger}} -> {{enum|Enabled}} MUST be
           instantaneous and so will result in only a single
           value change for notification purposes.";
      }
      leaf SampleInterval {
        type uint32 {
          range "1..max";
        }
        description
          "The sample interval in {{units}}.  Each statistic is
           measured over this sample interval.
        
           The STB MAY reject a request to set {{param}} to less
           than
           {{param|.Capabilities.ServiceMonitoring.MinSampleInterval}}.
        
           Sample intervals MUST begin every {{param}} seconds,
           with no delay between samples.
        
           If {{param}} is changed while collection of Sample
           statistics is enabled, any stored samples are
           discarded, and the first sample interval begins
           immediately.
        
           For example, if {{param|ReportSamples}} is 24 and
           {{param}} is 3600 (an hour), the STB can store up to a
           day's worth of samples for each statistic.";
      }
      leaf ReportSamples {
        type uint32 {
          range "1..max";
        }
        description
          "The number of samples that the STB can store and report
           for each statistic.
        
           The STB MUST permit {{param}} to be set to any value
           in the range from 1 to
           {{param|.Capabilities.ServiceMonitoring.MaxReportSamples}}.
        
           If {{param}} is changed while collection of Sample
           statistics is enabled, the STB will truncate or extend
           its statistics buffers as appropriate, but statistics
           collection MUST NOT otherwise be affected.
        
           For example, if {{param}} is 24 and
           {{param|SampleInterval}} is 3600 (an hour), the STB
           can store up to a day's worth of samples for each
           statistic.";
      }
      leaf EventsPerSampleInterval {
        type uint32 {
          range "1..max";
        }
        description
          "The number of event measurements of each applicable
           statistic that the STB is able to store for each
           sample interval.
        
           The STB MUST permit {{param}} to be set to any value
           in the range from 1 to
           {{param|.Capabilities.ServiceMonitoring.MaxEventsPerSampleInterval}}.
        
           If {{param}} is changed while collection of Sample
           statistic is enabled, the STB will truncate or extend
           its event measurement buffers as appropriate, but
           event measurement collection MUST NOT otherwise be
           affected.
        
           For example, if {{param|ReportSamples}} is 24 and
           {{param|SampleInterval}} is 3600 (an hour), and
           {{param}} is 60, the STB can store up 60 event
           measurements per hour, or in total 1440 event
           measurements per day.";
      }
      leaf FetchSamples {
        type uint32;
        description
          "If collection of Sample statistics is enabled and
           {{param}} is in the range [1:{{param|ReportSamples}}]
           then {{param|SampleState}} MUST transition from
           {{enum|Enabled|SampleState}} ->
           {{enum|Trigger|SampleState}} ->
           {{enum|Enabled|SampleState}} on completion of every
           {{param}} sample intervals.  Otherwise, this
           transition MUST NOT occur.
        
           For example, if {{param|ReportSamples}} is 25 and
           {{param}} is 24, then the STB will store 25 values for
           each statistic and the above {{param|SampleState}}
           transition will occur every 24 sample intervals, which
           means that the ACS could delay for up to two sample
           intervals before reading the stored values and would
           still not miss any samples (see also
           {{param|ForceSample}}).";
      }
      leaf TimeReference {
        type yang:date-and-time;
        description
          "An absolute time reference in UTC to determine when
           sample intervals will complete.  Each sample interval
           MUST complete at this reference time plus or minus an
           integer multiple of {{param|SampleInterval}}.
        
           This time reference also determines when the
           {{param|SampleState}} {{enum|Enabled|SampleState}} ->
           {{enum|Trigger|SampleState}} ->
           {{enum|Enabled|SampleState}} transitions that are
           controlled by {{param|FetchSamples}} will occur.  If
           collection of Sample statistics is enabled and
           {{param|FetchSamples}} is in the range
           [1:{{param|ReportSamples}}] then each such
           {{param|SampleState}} transition MUST occur at this
           reference time plus or minus an integer multiple of
           {{param|FetchSamples}} * {{param|SampleInterval}} (the
           fetch interval).
        
           {{param}} is used only to set the \"phase\" of the
           sample and fetch intervals.  The actual value of
           {{param}} can be arbitrarily far into the past or
           future.
        
           If {{param}} is changed while collection of Sample
           statistics is enabled, any stored samples are
           discarded, and the first sample interval begins
           immediately.
        
           The Unknown Time value defined in {{bibref|TR-106a1}}
           indicates that no particular time reference is
           specified.  That is, the STB MAY locally choose the
           time reference, and is required only to adhere to the
           specified sample and fetch intervals.
        
           If absolute time is not available to the STB, its
           sample and fetch interval behavior MUST be the same as
           if the {{param}} parameter was set to the Unknown Time
           value.
        
           For example, if {{param|SampleInterval}} is 3600 (an
           hour) and if {{param}} is set to UTC midnight on some
           day (in the past, present, or future) then sample
           intervals will complete on each UTC hour (00:00,
           01:00, 02:00 etc).
        
           If, in addition, {{param|FetchSamples}} is 24, then
           the fetch interval is 86400 (a day) and
           {{param|SampleState}} {{enum|Enabled|SampleState}} ->
           {{enum|Trigger|SampleState}} ->
           {{enum|Enabled|SampleState}} transitions will occur
           every day at UTC midnight.
        
           Note that, if {{param}} is set to a time other than
           the Unknown Time, the first sample interval (which has
           to begin immediately) will almost certainly be shorter
           than {{param|SampleInterval}}).  This is why {{param}}
           is defined in terms of when sample intervals complete
           rather than start.";
      }
      leaf ForceSample {
        type boolean;
        description
          "When set to {{true}}, forces statistics for the current
           sample to be calculated and updated in the data model.
           Setting it to {{false}} has no effect.  The value is
           not saved in device state and is always {{false}} when
           read.
        
           If this is the first time that {{param}} has been set
           to true during the current sample interval, this MUST
           cause a new value to be added to each of the Sample
           statistics comma-separated list parameters, and the
           {{param|ReportEndTime}} and all ''SampleSeconds''
           parameters MUST be updated accordingly.
        
           If this is not the first time that {{param}} has been
           set to {{true}} during the current sample interval,
           then the new values that were added as described in
           the previous paragraph, and the
           {{param|ReportEndTime}} and all ''SampleSeconds''
           parameters, MUST be updated accordingly.
        
           Note that {{param}} just provides a ''sneak preview''
           of the current sample.  It does not create a new
           sample and it does not interfere with the sample
           interval schedule.
        
           At the end of each sample interval, if {{param}} was
           set to {{true}} during the sample interval then the
           new values that were added as described above, and the
           {{param|ReportEndTime}} and all ''SampleSeconds''
           parameters, will be updated accordingly.  In other
           words, the partial sample data that was created when
           {{param}} was set to {{true}} will be updated one last
           time at the end of the sample interval.";
      }
      leaf ReportStartTime {
        type yang:date-and-time;
        config false;
        description
          "The absolute time at which the sample interval for the
           first stored sample (for each statistic) started.";
      }
      leaf ReportEndTime {
        type yang:date-and-time;
        config false;
        description
          "The absolute time at which the sample interval for the
           last stored sample (for each statistic) ended.
        
           If {{param|ForceSample}} has been used to force
           statistics for the current sample to be calculated and
           updated in the data model, then {{param}} MUST be
           updated to reflect the actual time over which stored
           data was collected.";
      }
      leaf EventCollectionEnable {
        type boolean;
        description
          "Enables or disables the collection of the events for all
           main streams.
        
           When the collection of events is enabled, any
           previously collected events are discarded and the
           collection of new events begins immediately.";
      }

      container GlobalOperation {
        config false;
        description
          "Global operations statistics.";

        container Total {
          description
            "Global operations total statistics.";
          leaf ServiceAccessTime {
            type uint32;
            description
              "The time period in, {{units}}, between the first
               message (e.g.  DHCP Discover) sent by the STB
               during boot-up and the first multicast I-frame for
               the default channel displayed by the STB.";
          }
          leaf MinimumPortalResponse {
            type uint32;
            description
              "Minimum portal latency defined as the minimum time
               period, in {{units}}, between the instant of
               transmitting TCP SYN (the three way handshake)
               prior to first HTTP message, and receiving the
               last HTTP message carrying the information.";
          }
          leaf MaximumPortalResponse {
            type uint32;
            description
              "Maximum portal latency defined as the maximum time
               period, in {{units}}, between the instant of
               transmitting TCP SYN (the three way handshake)
               prior to first HTTP message, and receiving the
               last HTTP message carrying the information.";
          }
        }

        container Sample {
          description
            "Global operations sample statistics.";
          leaf MinimumPortalResponse {
            type uint32;
            description
              "Each entry is the minimum portal latency defined as
               the minimum time period, in {{units}}, between the
               instant of transmitting TCP SYN (the three way
               handshake) prior to first HTTP message, and
               receiving the last HTTP message carrying the
               information during the sample interval.";
          }
          leaf MaximumPortalResponse {
            type uint32;
            description
              "Each entry is the maximum portal latency defined as
               the maximum time period, in {{units}}, between the
               instant of transmitting TCP SYN (the three way
               handshake) prior to first HTTP message, and
               receiving the last HTTP message carrying the
               information during the sample interval.";
          }
          leaf PortalResponse {
            type string {
              pattern "(\d+(:\d+)*)?";
            }
            description
              "Each entry is a colon separated list of time periods
               (in milliseconds) between the instant of
               transmitting TCP SYN (the three way handshake)
               prior to first HTTP message, and receiving the
               last HTTP message carrying the information.
            
               A comma separates measurements made in different
               sample intervals, while a colon separates
               individual measurements within a specific sample
               interval.
            
               If no PortalResponse measurements were made during
               a specific sample interval then this MUST be
               represented by an empty string.
            
               Example: ,837:453:1234,759,,,923:698,,,1284
            
               Here there were no measurements during first
               sample interval, three during the second, one
               during the third, etc.
            
               The statistics values in this list MUST be in time
               order, with the oldest one first and the most
               recent one last.  This applies both to sample
               intervals and to individual measurements during a
               specific sample interval.  {{nopattern}}";
          }
        }
      }

      list MainStream {
        key "ServiceType";
        description
          "List of Main AV stream objects.  Each instance is
           associated with a specified service type and will
           collect statistics only for the main stream that
           matches that service type.
        
           Note that this means that streams that do not match an
           instance's service type MUST NOT contribute to the
           instance's Total and Sample statistics.
        
           It is up to the STB to determine which AV stream
           should be regarded as the Main AV stream for a given
           service type at any given time.  For example, if two
           active streams are associated with the same service
           type, the STB might prefer streams that are associated
           with an AV player, or if more than one stream is
           associated with an AV player, the STB might prefer a
           player that is outputting a DVI stream to a player
           that is outputting an RF stream.
        
           Note that some parameters, e.g.
           {{param|.Components.FrontEnd.{i}.IP.ServiceConnect.URI}},
           include requirements that restrict the STB's freedom
           to determine which AV stream should be regarded as the
           Main AV stream for a given service.";
        leaf Enable {
          type boolean;
          description
            "Enables or disables collection of Total and Sample
             statistics and events for this object instance.
          
             The collection of events requires the value of this
             parameter to be {{true}} and the value of the
             {{param|##.ServiceMonitoring.EventCollectionEnable}}
             to be {{true}}.";
        }
        leaf Status {
          type enumeration {
            enum "Disabled";
            enum "Enabled";
            enum "Error";
          }
          config false;
          description
            "Total and Sample statistics and event collection status
             for this object instance.  {{enum}}
          
             The {{enum|Error}} value MAY be used by the CPE to
             indicate a locally defined error condition.";
        }
        leaf SessionId {
          type yang:uuid;
          config false;
          description
            "Time based UUID {{bibref|RFC4122|Section 4.2}} that is
             the identifier for the associated {{param|AVStream}}
             parameter when available to the device.";
        }
        leaf ServiceType {
          type string;
          description
            "Service type associated with this main stream instance,
             or {{empty}} if this instance is disabled.
          
             The STB MUST reject a request that would result in a
             given AV stream contributing to more than one
             {{object|.ServiceMonitoring.MainStream}} instance,
             e.g.  it would reject a request to enable
             simultaneous collection of both IPTV and IP
             statistics, or to collect IPTV statistics on more
             than one instance.";
        }
        leaf AVStream {
          type string {
            length "0..256";
          }
          config false;
          description
            "Main AV stream object instance currently associated
             with this ''ServiceMonitoring'' main stream
             instance.  For example:
          
             ''.AVStreams.AVStream.2''
          
             Note that, during the period of time over which
             Sample statistics are stored, this
             ''ServiceMonitoring'' main stream instance might be
             associated with many different ''AVStream''
             instances.  This parameter just provides information
             about which ''AVStream'' is currently being
             monitored.";
        }
        leaf Gmin {
          type uint32;
          description
            "Minimum number of consecutive received packets after
             the end of an RTP Loss Event.  A Loss Event is
             defined as as a sequence of lost packets, possibly
             including islands of received packets.  Each island
             consists of up to
          
             ({{param}} - 1) received packets (a sequence of
             {{param}} received packets terminates the Loss
             Event, and so is not an island).";
        }
        leaf SevereLossMinDistance {
          type uint32;
          description
            "The minimum distance required between error events
             before an RTP Loss Event is considered severe.  Used
             in the calculation of ''SevereLossIndexCount'' and
             ''SevereLossIndexCountBeforeEC''.";
        }
        leaf SevereLossMinLength {
          type uint32;
          description
            "The minimum value for the count of lost packets per RTP
             Loss Event before the count of lost packets is
             considered severe.  Used in the calculation of
             ''SevereLossLengthCount'' and
             ''SevereLossLengthCountBeforeEC''.";
        }
        leaf ChannelChangeFailureTimeout {
          type uint32;
          description
            "Time period, in {{units}}, between a user channel
             change request (defined as the instant of
             transmission of the relevant control protocol
             message (IGMP JOIN or RTSP SETUP) or a tuner command
             in case of DTT), and the display of the first I
             frame for the current AVStream, above which a
             channel change is considered as failed.";
        }
        leaf PacketsLostByEventHistogramIntervals {
          type uint32 {
            range "1..max";
          }
          description
            "{{list}} Definition of the histogram intervals for
             counting loss events according to their size (in
             {{units}}).  Each value indicates the maximum value
             of the interval.  For example, \"1,2,4,8,\" defines
             the five intervals: 1 packet lost, 2 packets, 3 or 4
             packets, 5 to 8 packets and 9 or more packets.  (No
             value after the last comma means no upper bound.)
          
             If this parameter is set to an empty string, no
             PacketsLostByEvent stats will be collected.";
        }
        leaf DelayBetweenLossEventsHistogramIntervals {
          type uint32 {
            range "1..max";
          }
          description
            "{{list}} Definition of the histogram intervals for
             counting loss events according to their delay (in
             {{units}}) after the preceding loss event.  Each
             value indicates the maximum value of the interval.
             For example, \"10,20,50,100,1000,60000,3600000,\"
             defines the intervals up to 10 ms, to 20 ms, to 50
             ms, to 100 ms, to 1 s, to 1 mn, to 1 h and more than
             1 h.  (No value after the last comma means no upper
             bound.)
          
             If this parameter is set to an empty string, no
             DelayBetweenLossEvents stats will be collected.";
        }
        leaf DurationSevereLossEventsHistogramIntervals {
          type uint32 {
            range "1..max";
          }
          description
            "{{list}} Definition of the histogram intervals for
             counting severe loss events according to their
             duration (in {{units}}).  Each value indicates the
             maximum value of the interval.  For example,
             \"50,100,500,1000,2000,5000,10000,120000,\" defines
             the intervals up to 50 ms, to 100 ms, to 500 ms, to
             1 s, to 2 s etc.  (No value after the last comma
             means no upper bound.)
          
             If this parameter is set to an empty string, no
             DurationSevereLossEvents stats will be collected.";
        }

        container EventLog {
          description
            "This object represents the log entries of events
             recorded by the MainStream object instance.
          
             When the number of log entries in the EventLog
             exceeds the value of the
             {{param|###.Capabilities.ServiceMonitoring.MaxMainStreamEventLogEntries}}
             parameter, the Entry object with the lowest
             SequenceNumber value is replaced by the new EventLog
             Entry object.
          
             Log entries are persisted across reboots of the CPE.";
          leaf Reset {
            type boolean; /* command */
            description
              "When set to true, clears the events from the event
               log and the value of
               {{param|Entry.{i}.SequenceNumber}} parameter is
               reset to the parameter's minimum value.";
          }

          list Entry {
            key "SequenceNumber";
            config false;
            description
              "This object represents an entry (e.g., start session,
               channel change) in the event log.";
            leaf SequenceNumber {
              type uint32 {
                range "1..max";
              }
              description
                "The sequence number of the event within the
                 EventLog.
              
                 This parameter is incremented by one (1) for
                 each entry within the EventLog.
              
                 When the value of the parameter exceeds the
                 maximium range, the lowest value of this
                 parameter that is not contained in current
                 EventLog entries is used.";
            }
            leaf Type {
              type string;
              description
                "Type of the event.  The values for this parameter
                 are vendor specific.";
            }
            leaf Time {
              type yang:date-and-time;
              description
                "Timestamp of the event.";
            }

            list Parameter {
              description
                "This object represents an instance of a parameter
                 that is associated with the Entry object
                 Instance.";
              leaf Name {
                type string;
                description
                  "Name of the parameter (vendor-specific).";
              }
              leaf Value {
                type string;
                description
                  "Value of the parameter.";
              }
            }
          }
        }

        container Total {
          description
            "Total statistics since this ''ServiceMonitoring'' main
             stream instance was last enabled or Total statistics
             were last reset.";
          leaf TotalSeconds {
            type uint32;
            config false;
            description
              "The number of seconds during which data was collected
               for this AV stream since last reset
            
               Each statistics category (Dejittering, RTP etc)
               has its own {{param}} parameter, which indicates
               the number of seconds during which data was
               collected for that statistics category since last
               reset.
            
               Individual {{param}} values can be less than the
               {{param|ResetTime}}, for several reasons,
               including the STB was not receiving any data
               (Standby mode without force monitoring).";
          }
          leaf Reset {
            type boolean;
            description
              "When set to {{true}}, resets Total statistics for
               this ''ServiceMonitoring'' main stream instance.
               Setting it to {{false}} has no effect.  The value
               is not saved in device state and is always
               {{false}} when read.";
          }
          leaf ResetTime {
            type uint32;
            config false;
            description
              "Number of seconds since the Total statistics were
               last enabled or reset for this
               ''ServiceMonitoring'' main stream instance.";
          }

          container DejitteringStats {
            config false;
            description
              "Total de-jittering statistics for this
               ''ServiceMonitoring'' main stream instance.";
            leaf TotalSeconds {
              type uint32;
              description
                "The number of seconds during which data was
                 collected for this AV stream since last reset
              
                 Each statistics category (Dejittering, RTP etc)
                 has its own {{param}} parameter, which indicates
                 the number of seconds during which data was
                 collected for that statistics category since
                 last reset.
              
                 Individual {{param}} values can be less than
                 {{param|.ServiceMonitoring.MainStream.{i}.Total.ResetTime}},
                 for several reasons, including:
              
                 * Any of the reasons for which the {{param}}
                 values might be less than
                 {{param|.ServiceMonitoring.MainStream.{i}.Total.ResetTime}}.
              
                 * De-jittering data collection is not
                 appropriate or possible for this AV stream.";
            }
            leaf EmptyBufferTime {
              type uint32;
              description
                "Total time, in {{units}}, for which the playout was
                 stopped due to buffer issues (empty or too low
                 level) for this AV stream.";
            }
            leaf Overruns {
              type uint32;
              description
                "Total number of times the receive jitter buffer has
                 overrun for this AV stream.";
            }
            leaf Underruns {
              type uint32;
              description
                "Total number of times the receive jitter buffer has
                 underrun for this AV stream.";
            }
          }

          container TCPStats {
            config false;
            description
              "Total TCP statistics for this ServiceMonitoring main
               stream instance.";
            leaf TotalSeconds {
              type uint32;
              description
                "The number of seconds during which data was
                 collected for this AV stream since last reset
              
                 Each statistics category (Dejittering, RTP etc)
                 has its own {{param}} parameter, which indicates
                 the number of seconds during which data was
                 collected for that statistics category since
                 last reset.
              
                 Individual {{param}} values can be less than
                 {{param|.ServiceMonitoring.MainStream.{i}.Total.ResetTime}},
                 for several reasons, including:
              
                 * Any of the reasons for which the {{param}}
                 values might be less than
                 {{param|.ServiceMonitoring.MainStream.{i}.Total.ResetTime}}.
              
                 * TCP data collection is not appropriate or
                 possible for this AV stream.";
            }
            leaf PacketsReceived {
              type uint32;
              description
                "Total number of TCP packets correctly received for
                 this AV stream.";
            }
            leaf PacketsRetransmitted {
              type uint32;
              description
                "Total number of TCP packets being retransmitted for
                 this AV stream.";
            }
            leaf BytesReceived {
              type uint32;
              description
                "Total number of bytes received for this AV stream.";
            }
          }

          container RTPStats {
            config false;
            description
              "Total RTP statistics for this ''ServiceMonitoring''
               main stream instance.
            
               If no EC is applied the ''BeforeEC'' statistics
               provide the same values as the corresponding
               statistics, e.g.  when there is no EC,
               {{param|PacketsReceivedBeforeEC}} =
               {{param|PacketsReceived}}.";
            leaf TotalSeconds {
              type uint32;
              description
                "The number of seconds during which data was
                 collected for this AV stream since last reset
              
                 Each statistics category (Dejittering, RTP etc)
                 has its own {{param}} parameter, which indicates
                 the number of seconds during which data was
                 collected for that statistics category since
                 last reset.
              
                 Individual {{param}} values can be less than
                 {{param|.ServiceMonitoring.MainStream.{i}.Total.ResetTime}},
                 for several reasons, including:
              
                 * Any of the reasons for which the {{param}}
                 values might be less than
                 {{param|.ServiceMonitoring.MainStream.{i}.Total.ResetTime}}.
              
                 * RTP data collection is not appropriate or
                 possible for this AV stream.";
            }
            leaf PacketsExpected {
              type uint32;
              description
                "Total number of RTP packets expected for this AV
                 stream as described in {{bibref|RFC3550|A.3}}.";
            }
            leaf PacketsDiscarded {
              type uint32;
              description
                "Total number of packets discarded at the RTP layer
                 for this AV stream because they were too late
                 for playout, regardless of their being out of
                 sequence or not.
              
                 These statistics are collected when no EC is
                 applied or after any EC if available.";
            }
            leaf PacketsOutOfSequence {
              type uint32;
              description
                "Total number of packets out of sequence at the RTP
                 level for this AV stream, regardless of their
                 being too late for playout or not.
              
                 These statistics are collected when no EC is
                 applied or after any EC if available.";
            }
            leaf PacketsReceived {
              type uint32;
              description
                "Total number of RTP packets received for this AV
                 stream.
              
                 These statistics are collected when no EC is
                 applied or after any EC if available.";
            }
            leaf PacketsReceivedBeforeEC {
              type uint32;
              description
                "Total number of RTP packets received for this AV
                 stream.
              
                 These statistics are collected before any EC, if
                 available, is applied.";
            }
            leaf PacketsLost {
              type uint32;
              description
                "Total number of RTP packets lost for this stream.
              
                 These statistics are collected when no EC is
                 applied or after any EC if available.";
            }
            leaf PacketsLostBeforeEC {
              type uint32;
              description
                "Total number of RTP packets lost for this stream.
              
                 These statistics are collected before any EC, if
                 available, is applied.";
            }
            leaf PacketsLostByEventHistogram {
              type uint32;
              description
                "{{list}} Total number of loss events counted by
                 their length in packets (1 packet, 2 packets,
                 etc.) according to the intervals defined by
                 {{param|##.PacketsLostByEventHistogramIntervals}}.
              
                 These statistics are collected when no EC is
                 applied or after any EC if available.";
            }
            leaf PacketsLostByEventHistogramBeforeEC {
              type uint32;
              description
                "{{list}} Total number of loss events counted by
                 their length in packets (1 packet, 2 packets,
                 etc.) according to the intervals defined by
                 {{param|##.PacketsLostByEventHistogramIntervals}}.
              
                 These statistics are collected before any EC, if
                 available, is applied.";
            }
            leaf LossEvents {
              type uint32;
              description
                "Total number of Loss Events for this stream.
              
                 These statistics are collected when no EC is
                 applied or after any EC if available.";
            }
            leaf LossEventsBeforeEC {
              type uint32;
              description
                "Total number of Loss Events for this stream.
              
                 These statistics are collected before any EC, if
                 available, is applied.";
            }
            leaf DelayBetweenLossEventsHistogram {
              type uint32;
              description
                "{{list}} Total number of times that the delay (in
                 milliseconds) between two consecutive loss
                 events belongs to each time interval defined by
                 {{param|##.DelayBetweenLossEventsHistogramIntervals}}.
              
                 These statistics are collected when no EC is
                 applied or after any EC if available.";
            }
            leaf DelayBetweenLossEventsHistogramBeforeEC {
              type uint32;
              description
                "{{list}} Total number of times that the delay (in
                 milliseconds) between two consecutive loss
                 events belongs to each time interval defined by
                 {{param|##.DelayBetweenLossEventsHistogramIntervals}}.
              
                 These statistics are collected before any EC, if
                 available, is applied.";
            }
            leaf SevereLossIndexCount {
              type uint32;
              description
                "Total number of Loss Events closer than
                 ''SevereLossMinDistance''.
              
                 These statistics are collected when no EC is
                 applied or after any EC if available.";
            }
            leaf SevereLossIndexCountBeforeEC {
              type uint32;
              description
                "Total number of Loss Events closer than
                 ''SevereLossMinDistance''.
              
                 These statistics are collected before any EC, if
                 available, is applied.";
            }
            leaf SevereLossLengthCount {
              type uint32;
              description
                "Total number of Loss Events longer than
                 ''SevereLossMinLength''.
              
                 These statistics are collected when no EC is
                 applied or after any EC if available.";
            }
            leaf SevereLossLengthCountBeforeEC {
              type uint32;
              description
                "Total number of Loss Events longer than
                 ''SevereLossMinLength''.
              
                 These statistics are collected before any EC, if
                 available, is applied.";
            }
            leaf DurationSevereLossEventsHistogram {
              type uint32;
              description
                "{{list}} Total number of severe loss events counted
                 by their duration (in milliseconds) according to
                 the intervals defined by
                 {{param|##.DurationSevereLossEventsHistogramIntervals}}.
              
                 These statistics are collected when no EC is
                 applied or after any EC if available.";
            }
            leaf DurationSevereLossEventsHistogramBeforeEC {
              type uint32;
              description
                "{{list}} Total number of severe loss events counted
                 by their duration (in milliseconds) according to
                 the intervals defined by
                 {{param|##.DurationSevereLossEventsHistogramIntervals}}.
              
                 These statistics are collected before any EC, if
                 available, is applied.";
            }
            leaf RetransmitTimeouts {
              type uint32;
              description
                "Total number of RTP/AVPF retransmission timeouts
                 ({{bibref|RFC4585}}, {{bibref|RFC4588}})
              
                 If RTP/AVPF is not used this parameter does not
                 increment";
            }
          }

          container MPEG2TSStats {
            config false;
            description
              "Total MPEG2-TS statistics for this
               ''ServiceMonitoring'' main stream instance.";
            leaf TotalSeconds {
              type uint32;
              description
                "The number of seconds during which data was
                 collected for this AV stream since last reset
              
                 Each statistics category (Dejittering, RTP etc)
                 has its own {{param}} parameter, which indicates
                 the number of seconds during which data was
                 collected for that statistics category since
                 last reset.
              
                 Individual {{param}} values can be less than
                 {{param|.ServiceMonitoring.MainStream.{i}.Total.ResetTime}},
                 for several reasons, including:
              
                 * Any of the reasons for which the {{param}}
                 values might be less than
                 {{param|.ServiceMonitoring.MainStream.{i}.Total.ResetTime}}.
              
                 * MPEG2 TS data collection is not appropriate or
                 possible for this AV stream.";
            }
            leaf TSPacketsReceived {
              type uint32;
              description
                "Total number of MPEG2-TS packets received for this
                 AV stream.";
            }
            leaf TSSyncByteErrorCount {
              type uint32;
              description
                "Total number of MPEG2-TS packets with an invalid
                 transport sync byte received for this AV stream.
              
                 Not meaningful when MPEG2-TS is transported over
                 IP.";
            }
            leaf TSSyncLossCount {
              type uint32;
              description
                "Total number of MPEG2-TS Loss of Synchronization
                 Events for this AV stream.
              
                 Not meaningful when MPEG2-TS is transported over
                 IP.";
            }
            leaf PacketDiscontinuityCounter {
              type uint32;
              description
                "Total number of MPEG2-TS Discontinuity errors that
                 have been captured for this AV stream.  This
                 parameter accumulates all of the discontinuities
                 observed for all currently monitored PIDs.
              
                 These statistics are collected when no CA
                 decryption scheme is in use or after any CA
                 decryption if in use.";
            }
            leaf PacketDiscontinuityCounterBeforeCA {
              type uint32;
              description
                "Total number of MPEG2-TS Discontinuity errors that
                 have been captured for this AV stream.  This
                 parameter accumulates all of the discontinuities
                 observed for all currently monitored PIDs.
              
                 These statistics are collected before any CA
                 decryption scheme, if used, is applied.";
            }
          }

          container VideoDecoderStats {
            config false;
            description
              "Total video decoder application layer statistics for
               this ''ServiceMonitoring'' main stream instance.";
            leaf TotalSeconds {
              type uint32;
              description
                "The number of seconds during which data was
                 collected for this AV stream since last reset
              
                 Each statistics category (Dejittering, RTP etc)
                 has its own {{param}} parameter, which indicates
                 the number of seconds during which data was
                 collected for that statistics category since
                 last reset.
              
                 Individual {{param}} values can be less than
                 {{param|.ServiceMonitoring.MainStream.{i}.Total.ResetTime}},
                 for several reasons, including:
              
                 * Any of the reasons for which the {{param}}
                 values might be less than
                 {{param|.ServiceMonitoring.MainStream.{i}.Total.ResetTime}}.
              
                 * Video Decoder data collection is not
                 appropriate or possible for this AV stream.";
            }
            leaf FrameRate {
              type uint32;
              description
                "The latest frame rate at which the STB played out
                 the video content for this AV stream.  Also the
                 reported rate will be rounded off to the nearest
                 integer.";
            }
            leaf DecodedFrames {
              type uint32;
              description
                "The number of video frames that were decoded
                 completely (errorless frames) or partially
                 (corrupted frames) for this AV stream.";
            }
            leaf LostFrames {
              type uint32;
              description
                "The number of video frames that could not be
                 reproduced by the STB for this AV stream.";
            }
            leaf ConcealedFrames {
              type uint32;
              description
                "The number of video frames that were reproduced by
                 the STB for which some information was missing
                 and loss concealment was applied for this AV
                 stream.";
            }
            leaf IDecodedFrames {
              type uint32;
              description
                "The number of I frames that were decoded completely
                 (errorless frames) or partially (corrupted
                 frames) for this AV stream.";
            }
            leaf ILostFrames {
              type uint32;
              description
                "The number of I frames that could not be reproduced
                 by the STB for this AV stream.";
            }
            leaf IConcealedFrames {
              type uint32;
              description
                "The number of I frames that were reproduced by the
                 STB for which some information was missing and
                 loss concealment applied for this AV stream.";
            }
            leaf PDecodedFrames {
              type uint32;
              description
                "The number of P frames that were decoded completely
                 (errorless frames) or partially (corrupted
                 frames) for this AV stream.";
            }
            leaf PLostFrames {
              type uint32;
              description
                "The number of P frames that could not be reproduced
                 by the STB for this AV stream.";
            }
            leaf PConcealedFrames {
              type uint32;
              description
                "The number of P frames that were reproduced by the
                 STB for which some information was missing and
                 loss concealment applied for this AV stream.";
            }
            leaf BDecodedFrames {
              type uint32;
              description
                "The number of B frames that were decoded completely
                 (errorless frames) or partially (corrupted
                 frames) for this AV stream.";
            }
            leaf BLostFrames {
              type uint32;
              description
                "The number of B frames that could not be reproduced
                 by the STB for this AV stream.";
            }
            leaf BConcealedFrames {
              type uint32;
              description
                "The number of B frames that were reproduced by the
                 STB for which some information was missing and
                 loss concealment applied for this AV stream.";
            }
            leaf AVResynchCounter {
              type uint32;
              description
                "The number of AV resynchronizations that were
                 performed by the STB for this AV stream.";
            }
          }

          container AudioDecoderStats {
            config false;
            description
              "Total audio decoder application layer statistics for
               this ''ServiceMonitoring'' main stream instance.";
            leaf TotalSeconds {
              type uint32;
              description
                "The number of seconds during which data was
                 collected for this AV stream since last reset
              
                 Each statistics category (Dejittering, RTP etc)
                 has its own {{param}} parameter, which indicates
                 the number of seconds during which data was
                 collected for that statistics category since
                 last reset.
              
                 Individual {{param}} values can be less than
                 {{param|.ServiceMonitoring.MainStream.{i}.Total.ResetTime}},
                 for several reasons, including:
              
                 * Any of the reasons for which the {{param}}
                 values might be less than
                 {{param|.ServiceMonitoring.MainStream.{i}.Total.ResetTime}}.
              
                 * Audio Decoder data collection is not
                 appropriate or possible for this AV stream.";
            }
            leaf DecodedFrames {
              type uint32;
              description
                "The number of audio frames that were decoded
                 completely (errorless frames) or partially
                 (corrupted frames) for this AV stream.";
            }
            leaf DecodingErrors {
              type uint32;
              description
                "The number of audio decoding errors detected for
                 this AV stream.";
            }
          }

          container VideoResponseStats {
            config false;
            description
              "Total video response statistics for this
               ''ServiceMonitoring'' main stream instance.";
            leaf TotalSeconds {
              type uint32;
              description
                "The number of seconds during which data was
                 collected for this AV stream since last reset
              
                 Each statistics category (Dejittering, RTP etc)
                 has its own {{param}} parameter, which indicates
                 the number of seconds during which data was
                 collected for that statistics category since
                 last reset.
              
                 Individual {{param}} values can be less than
                 {{param|.ServiceMonitoring.MainStream.{i}.Total.ResetTime}},
                 for several reasons, including:
              
                 * Any of the reasons for which the {{param}}
                 values might be less than
                 {{param|.ServiceMonitoring.MainStream.{i}.Total.ResetTime}}.
              
                 * Video response data collection is not
                 appropriate or possible for this AV stream.";
            }
            leaf ChannelChangeFailures {
              type uint32;
              description
                "Number of channel change failures.  A channel
                 change is considered as failed when the time
                 period between a user channel change request and
                 the display of the first I frame for this
                 AVStream is above
                 {{param|.ServiceMonitoring.MainStream.{i}.ChannelChangeFailureTimeout}}.";
            }
            leaf ChannelFailures {
              type string;
              description
                "Each entry represents a channel for which a channel
                 change failed.  Channels MAY be described as IP
                 address, URL or Service names as appropriate.
                 Only last 10 failures are required to be
                 reported.";
            }
            leaf MinimumVoDControlResponse {
              type uint32;
              description
                "Minimum time period, in {{units}}, between the
                 instant of transmitting a RTSP PLAY command to
                 start playing stream, and displaying the first I
                 frame of unicast stream.  Only measured when
                 started from a non-play state, i.e.  either idle
                 or paused.";
            }
            leaf MaximumVoDControlResponse {
              type uint32;
              description
                "Maximum time period, in {{units}}, between the
                 instant of transmitting a RTSP PLAY command to
                 start playing stream, and displaying the first
                 I-frame of unicast stream.  Only measured when
                 started from a non-play state, i.e.  either idle
                 or paused.";
            }
            leaf RequestedTransactions {
              type uint32;
              description
                "Total number of RTSP protocol requests to start a
                 VoD program display.
              
                 Only meaningful for VoD.";
            }
            leaf AccessSuccesses {
              type uint32;
              description
                "Total number of successful VoD attempts.  An
                 attempt is considered successful when the first
                 I-frame is displayed by the client.
              
                 Only meaningful for VoD.";
            }
            leaf CompletionCount {
              type uint32;
              description
                "Total number of completed VoD requests.  An attempt
                 is defined successful if it continues until a
                 RTSP protocol request to end the session is sent
                 by the STB.
              
                 Only meaningful for VoD.";
            }
            leaf MinimumVideoSystemResponse {
              type uint32;
              description
                "Minimum time period (in {{units}}) between the
                 instant of transmitting an IGMP JOIN command or
                 an RTSP SETUP command, and the display of the
                 first I frame for this AV stream.";
            }
            leaf MaximumVideoSystemResponse {
              type uint32;
              description
                "Maximum time period (in {{units}}) between the
                 instant of transmitting an IGMP JOIN command or
                 an RTSP SETUP command, and the display of the
                 first I frame for this AV stream.";
            }
          }
        }

        container Sample {
          description
            "Sample statistics collected since collection was last
             enabled or reset.
          
             Most of the parameters in this object are
             comma-separated lists of individual statistics
             values, each of which corresponds to a sample
             interval.
          
             The statistics values in these comma-separated lists
             MUST be in time order, with the oldest one first and
             the most recent one last.
          
             Each comma-separated list can contain up to
             {{param|##.ReportSamples}} statistics values.  When
             the list is full, each new value causes the oldest
             one to be discarded.
          
             Some comma-separated lists contain terms that are
             comma-separated lists themselves and are used to
             store measurements on an event basis.  These
             sub-lists can contain up to
             {{param|.Capabilities.ServiceMonitoring.MaxEventsPerSampleInterval}}
             values.
          
             If no data was collected for a statistic during a
             sample interval then the value for that sample
             interval MUST be zero unless otherwise specified in
             the description of the individual statistics
             parameter.";
          leaf SampleSeconds {
            type uint32;
            config false;
            description
              "Each entry is the number of seconds during which data
               was collected for this AV stream during the sample
               interval.  Each statistics category (Dejittering,
               RTP etc) has its own ''SampleSeconds'' parameter,
               which indicates the number of seconds during which
               data was collected for that statistics category
               during the sample interval.
            
               Individual ''SampleSeconds'' values can be less
               than the ''SampleInterval'', for several reasons,
               including:
            
               * The STB was not receiving any data for the
               corresponding ServiceType for all or part of the
               sample interval.
            
               * ''TimeReference'' has been set to a time other
               than the Unknown Time and the current sample
               interval started part of the way through a
               scheduled sample interval.
            
               * ''ForceSample'' has been used to force
               statistics for the current sample to be calculated
               and updated in the data model.";
          }
          leaf SignificantChanges {
            type uint32;
            config false;
            description
              "Each entry is the total number of times that a
               channel change (or other potentially disruptive
               event) occurred for this AV stream during the
               sample interval.";
          }
          leaf PVRTimeShift {
            type boolean;
            config false;
            description
              "Each entry is a Boolean that indicates whether the
               PVR, with a non-zero time-shift, was used at any
               time for this AV stream during the sample
               interval.";
          }

          container DejitteringStats {
            config false;
            description
              "De-jittering Sample statistics for this
               ''ServiceMonitoring'' main stream instance.";
            leaf SampleSeconds {
              type uint32;
              description
                "Each entry is the number of seconds during which
                 de-jittering data was collected for this AV
                 stream during the sample interval.
              
                 Individual {{param}} values can be less than the
                 sample interval, for several reasons, including:
              
                 * Any of the reasons for which the
                 {{param|.ServiceMonitoring.MainStream.{i}.Sample.SampleSeconds}}
                 values might be less than the sample interval.
              
                 * De-jittering data collection is not
                 appropriate or possible for this AV stream.";
            }
            leaf Overruns {
              type uint32;
              description
                "Each entry is the total number of times the receive
                 jitter buffer has overrun for this AV stream
                 during the sample interval.";
            }
            leaf Underruns {
              type uint32;
              description
                "Each entry is the total number of times the receive
                 jitter buffer has underrun for this AV stream
                 during the sample interval.";
            }
            leaf EmptyBufferTime {
              type uint32;
              description
                "Each entry is the time period, in {{units}}, for
                 which the playout was stopped due to buffer
                 issues (empty or too low level) for this AV
                 stream during the sample interval.";
            }
          }

          container TCPStats {
            config false;
            description
              "TCP sample statistics for this ''ServiceMonitoring''
               main stream instance.";
            leaf SampleSeconds {
              type uint32;
              description
                "Each entry is the number of seconds during which
                 de-jittering data was collected for this AV
                 stream during the sample interval.
              
                 Individual {{param}} values can be less than the
                 sample interval, for several reasons, including:
              
                 * Any of the reasons for which the
                 {{param|.ServiceMonitoring.MainStream.{i}.Sample.SampleSeconds}}
                 values might be less than the sample interval.
              
                 * TCP data collection is not appropriate or
                 possible for this AV stream.";
            }
            leaf PacketsReceived {
              type uint32;
              description
                "Each entry is the total number of TCP packets
                 received for this AV stream during the sample
                 interval.";
            }
            leaf PacketsRetransmitted {
              type uint32;
              description
                "Each entry is the total number of TCP packets being
                 retransmitted this AV stream.during the sample
                 interval.";
            }
            leaf BytesReceived {
              type uint32;
              description
                "Each entry is the total number of bytes received
                 for this AV stream.during the sample interval.";
            }
          }

          container RTPStats {
            config false;
            description
              "RTP Sample statistics for this ''ServiceMonitoring''
               main stream instance.
            
               If no EC is applied the ''BeforeEC'' statistics
               provide the same values as the corresponding
               statistics, e.g.  when there is no EC,
               {{param|PacketsReceivedBeforeEC}} =
               {{param|PacketsReceived}}.";
            leaf SampleSeconds {
              type uint32;
              description
                "Each entry is the number of seconds during which
                 RTP data was collected for this AV stream during
                 the sample interval.
              
                 Individual {{param}} values can be less than the
                 sample interval, for several reasons, including:
              
                 * Any of the reasons for which the
                 {{param|.ServiceMonitoring.MainStream.{i}.Sample.SampleSeconds}}
                 values might be less than the sample interval.
              
                 * RTP data collection is not appropriate or
                 possible for this AV stream.";
            }
            leaf PacketsExpected {
              type uint32;
              description
                "Each entry is the total number of RTP packets
                 expected for this AV stream during the sample
                 interval as described in {{bibref|RFC3550|A.3}}.";
            }
            leaf PacketsDiscarded {
              type uint32;
              description
                "Each entry is the number of packets that were
                 discarded at the RTP layer for this AV stream
                 during the sample interval because they were too
                 late for playout, regardless of their being out
                 of sequence or not.
              
                 These statistics are collected when no EC is
                 applied or after any EC if available.";
            }
            leaf PacketsOutOfSequence {
              type uint32;
              description
                "Each entry is the number of packets out of sequence
                 at the RTP level for this AV stream during the
                 sample interval, regardless of their being too
                 late for playout or not.
              
                 These statistics are collected when no EC is
                 applied or after any EC if available.";
            }
            leaf PacketsReceived {
              type uint32;
              description
                "Each entry is the total number of RTP packets
                 received for this AV stream during the sample
                 interval.
              
                 These statistics are collected when no EC is
                 applied or after any EC if available.";
            }
            leaf PacketsReceivedBeforeEC {
              type uint32;
              description
                "Each entry is the total number of RTP packets
                 received for this AV stream during the sample
                 interval.
              
                 These statistics are collected before any EC, if
                 available, is applied.";
            }
            leaf RetransmitTimeouts {
              type uint32;
              description
                "Each entry is the number of RTP/AVPF retransmission
                 timeouts ({{bibref|RFC4585}},
                 {{bibref|RFC4588}}) for this AV stream during
                 the sample interval.";
            }
            leaf PacketsLost {
              type uint32;
              description
                "Each entry is the total number of RTP packets lost
                 for this AV stream during the sample interval.
              
                 Calculated by looking for missing RTP sequence
                 headers.
              
                 These statistics are collected when no EC is
                 applied or after any EC if available.";
            }
            leaf PacketsLostBeforeEC {
              type uint32;
              description
                "Each entry is the total number of RTP packets lost
                 for this AV stream during the sample interval.
              
                 Calculated by looking for missing RTP sequence
                 headers.
              
                 These statistics are collected before any EC, if
                 available, is applied.";
            }
            leaf PacketsLostByEventHistogram {
              type string;
              description
                "{{list}} Each list item is a comma-separated list
                 of unsigned integers that represents, for a
                 sample interval, a histogram of loss events
                 counted by their length in packets (1 packet, 2
                 packets, etc.) according to the intervals
                 defined by
                 {{param|##.PacketsLostByEventHistogramIntervals}}.
              
                 These statistics are collected when no EC is
                 applied or after any EC if available.";
            }
            leaf PacketsLostByEventHistogramBeforeEC {
              type string;
              description
                "{{list}} Each list item is a comma-separated list
                 of unsigned integers that represents, for a
                 sample interval, a histogram of loss events
                 counted by their length in packets (1 packet, 2
                 packets, etc.) according to the intervals
                 defined by
                 {{param|##.PacketsLostByEventHistogramIntervals}}.
              
                 These statistics are collected before any EC, if
                 available, is applied.";
            }
            leaf LossEvents {
              type uint32;
              description
                "Each entry is the total number of Loss Events for
                 this AV stream during the sample interval.
              
                 These statistics are collected when no EC is
                 applied or after any EC if available.";
            }
            leaf LossEventsBeforeEC {
              type uint32;
              description
                "Each entry is the total number of Loss Events for
                 this AV stream during the sample interval.
              
                 These statistics are collected before any EC, if
                 available, is applied.";
            }
            leaf DelayBetweenLossEventsHistogram {
              type string;
              description
                "{{list}} Each list item is a comma-separated list
                 of unsigned integers that represents, for a
                 sample interval, a histogram of the number of
                 times that the delay (in milliseconds) between
                 two consecutive loss events belongs to each time
                 interval defined by
                 {{param|##.DelayBetweenLossEventsHistogramIntervals}}.
              
                 These statistics are collected when no EC is
                 applied or after any EC if available.";
            }
            leaf DelayBetweenLossEventsHistogramBeforeEC {
              type string;
              description
                "{{list}} Each list item is a comma-separated list
                 of unsigned integers that represents, for a
                 sample interval, a histogram of the number of
                 times that the delay (in milliseconds) between
                 two consecutive loss events belongs to each time
                 interval defined by
                 {{param|##.DelayBetweenLossEventsHistogramIntervals}}.
              
                 These statistics are collected before any EC, if
                 available, is applied.";
            }
            leaf SevereLossIndexCount {
              type uint32;
              description
                "Each entry is the total number of Loss Events that
                 occurred at a distance shorter than
                 ''SevereLossMinDistance'' from the previous Loss
                 Event for this AV stream during the sample
                 interval.
              
                 These statistics are collected when no EC is
                 applied or after any EC if available.";
            }
            leaf SevereLossIndexCountBeforeEC {
              type uint32;
              description
                "Each entry is the total number of Loss Events that
                 occurred at a distance shorter than
                 ''SevereLossMinDistance'' from the previous Loss
                 Event for this AV stream during the sample
                 interval.
              
                 These statistics are collected before any EC, if
                 available, is applied.";
            }
            leaf AverageLossDistance {
              type uint32;
              description
                "Each entry is the average distance in {{units}}
                 between consecutive Loss Events for this AV
                 stream during the sample interval.
              
                 These statistics are collected when no EC is
                 applied or after any EC if available.";
            }
            leaf AverageLossDistanceBeforeEC {
              type uint32;
              description
                "Each entry is the average distance in {{units}}
                 between consecutive loss events for this AV
                 stream during the sample interval.
              
                 These statistics are collected before any EC, if
                 available, is applied.";
            }
            leaf MinimumLossDistance {
              type uint32;
              description
                "Each entry is the length in {{units}} of the
                 shortest distance between consecutive Loss
                 Events for this AV stream during the sample
                 interval.
              
                 These statistics are collected when no EC is
                 applied or after any EC if available.";
            }
            leaf MinimumLossDistanceBeforeEC {
              type uint32;
              description
                "Each entry is the length in {{units}} of the
                 shortest distance between consecutive Loss
                 Events for this AV stream during the sample
                 interval.
              
                 These statistics are collected before any EC, if
                 available, is applied.";
            }
            leaf SevereLossLengthCount {
              type uint32;
              description
                "Each entry is the total number of Loss Events with
                 length in RTP packets greater than
                 ''SevereLossMinLength'' for this AV stream
                 during the sample interval.
              
                 These statistics are collected when no EC is
                 applied or after any EC if available.";
            }
            leaf SevereLossLengthCountBeforeEC {
              type uint32;
              description
                "Each entry is the total number of Loss Events with
                 length in RTP packets greater than
                 ''SevereLossMinLength'' for this AV stream
                 during the sample interval.
              
                 These statistics are collected before any EC, if
                 available, is applied.";
            }
            leaf DurationSevereLossEventsHistogram {
              type string;
              description
                "{{list}} Each list item is a comma-separated list
                 of unsigned integers that represents, for a
                 sample interval, a histogram of the number of
                 severe loss events counted by their duration (in
                 milliseconds) according to the intervals defined
                 by
                 {{param|##.DurationSevereLossEventsHistogramIntervals}}.
              
                 These statistics are collected when no EC is
                 applied or after any EC if available.";
            }
            leaf DurationSevereLossEventsHistogramBeforeEC {
              type string;
              description
                "{{list}} Each list item is a comma-separated list
                 of unsigned integers that represents, for a
                 sample interval, a histogram of the number of
                 severe loss events counted by their duration (in
                 milliseconds) according to the intervals defined
                 by
                 {{param|##.DurationSevereLossEventsHistogramIntervals}}.
              
                 These statistics are collected before any EC, if
                 available, is applied.";
            }
            leaf MaximumLossPeriod {
              type uint32;
              description
                "Each entry is the length in {{units}} of the
                 longest Loss Event for this AV stream during the
                 sample interval.
              
                 These statistics are collected when no EC is
                 applied or after any EC if available.";
            }
            leaf MaximumLossPeriodBeforeEC {
              type uint32;
              description
                "Each entry is the length in {{units}} of the
                 longest Loss Event for this AV stream during the
                 sample interval.
              
                 These statistics are collected before any EC, if
                 available, is applied.";
            }
            leaf AverageLossPeriod {
              type uint32;
              description
                "Each entry is the average length in {{units}} of
                 Loss Events for this AV stream during the sample
                 interval.
              
                 These statistics are collected when no EC is
                 applied or after any EC if available.";
            }
            leaf AverageLossPeriodBeforeEC {
              type uint32;
              description
                "Each entry is the average length in {{units}} of
                 Loss Events for this AV stream during the sample
                 interval.
              
                 These statistics are collected before any EC, if
                 available, is applied.";
            }
            leaf MinimumLossPeriod {
              type uint32;
              description
                "Each entry is the length in {{units}} of the
                 shortest RTP Loss Event for this AV stream
                 during the sample interval.
              
                 These statistics are collected when no EC is
                 applied or after any EC if available.";
            }
            leaf MinimumLossPeriodBeforeEC {
              type uint32;
              description
                "Each entry is the length in {{units}} of the
                 shortest RTP Loss Event for this AV stream
                 during the sample interval.
              
                 These statistics are collected before any EC, if
                 available, is applied.";
            }
          }

          container MPEG2TSStats {
            config false;
            description
              "MPEG2-TS Sample statistics for this
               ''ServiceMonitoring'' main stream instance.";
            leaf SampleSeconds {
              type uint32;
              description
                "Each entry is the number of seconds during which
                 MPEG2-TS data was collected for this AV stream
                 during the sample interval.
              
                 Individual {{param}} values can be less than the
                 sample interval, for several reasons, including:
              
                 * Any of the reasons for which the
                 {{param|.ServiceMonitoring.MainStream.{i}.Sample.SampleSeconds}}
                 values might be less than the sample interval.
              
                 * MPEG2-TS data collection is not appropriate or
                 possible for this AV stream.";
            }
            leaf TSPacketsReceived {
              type uint32;
              description
                "Each entry is the total number of MPEG2-TS packets
                 received for this AV stream during the sample
                 interval.";
            }
            leaf TSPacketsDrained {
              type uint32;
              description
                "Each entry is the total number of good MPEG2-TS
                 packets removed from the buffer for this AV
                 stream during the sample interval.
              
                 Packets received minus packets drained provides
                 an indication how close the buffer came to over
                 or under running during the sample interval.";
            }
            leaf TSSyncByteErrorCount {
              type uint32;
              description
                "Each entry is the total number of MPEG2-TS packets
                 with an invalid transport sync byte for this AV
                 stream during the sample interval.
              
                 Not meaningful when MPEG2-TS is transported over
                 IP.";
            }
            leaf TSSyncLossCount {
              type uint32;
              description
                "Each entry is the total number of MPEG2-TS Loss of
                 Synchronization Events for this AV stream during
                 the sample interval.
              
                 Not meaningful when MPEG2-TS is transported over
                 IP.";
            }
            leaf PacketDiscontinuityCounter {
              type uint32;
              description
                "Each entry is the total number of MPEG2-TS
                 Discontinuity errors that were captured for this
                 AV stream during the sample interval.
              
                 These statistics are collected when no CA
                 decryption scheme is in use or after any CA
                 decryption if in use.";
            }
            leaf PacketDiscontinuityCounterBeforeCA {
              type uint32;
              description
                "Each entry is the total number of MPEG2-TS
                 Discontinuity errors that were captured for this
                 AV stream during the sample interval.
              
                 These statistics are collected before any CA
                 decryption scheme, if used, is applied.";
            }
          }

          container VideoDecoderStats {
            config false;
            description
              "Video decoder Sample statistics for this
               ''ServiceMonitoring'' main stream instance.";
            leaf SampleSeconds {
              type uint32;
              description
                "Each entry is the number of seconds during which
                 video decoder data was collected for this AV
                 stream during the sample interval.
              
                 Individual {{param}} values can be less than the
                 sample interval, for several reasons, including:
              
                 * Any of the reasons for which the
                 {{param|.ServiceMonitoring.MainStream.{i}.Sample.SampleSeconds}}
                 values might be less than the sample interval.
              
                 * Video Decoder data collection is not
                 appropriate or possible for this AV stream.";
            }
            leaf FrameRate {
              type uint32;
              description
                "Each entry is the last frame rate at which the STB
                 played out the video content for this AV stream
                 during the sample interval.  .  Also the
                 reported rate will be rounded off to the nearest
                 integer.";
            }
            leaf DecodedFrames {
              type uint32;
              description
                "Each entry is the number of video frames that were
                 decoded completely (errorless frames) or
                 partially (corrupted frames) by the STB for this
                 AV stream during the sample interval.";
            }
            leaf LostFrames {
              type uint32;
              description
                "Each entry is the number of video frames that could
                 not be reproduced by the STB for this AV stream
                 during the sample interval.";
            }
            leaf ConcealedFrames {
              type uint32;
              description
                "Each entry is the number of video frames that were
                 reproduced by the STB for which some information
                 was missing for this AV stream during the sample
                 interval and loss concealment was applied.";
            }
            leaf IDecodedFrames {
              type uint32;
              description
                "Each entry is the number of I frames that were
                 decoded completely (errorless frames) or
                 partially (corrupted frames) by the STB for this
                 AV stream during the sample interval.";
            }
            leaf ILostFrames {
              type uint32;
              description
                "Each entry is the number of I frames that could not
                 be reproduced by the STB for this AV stream
                 during the sample interval.";
            }
            leaf IConcealedFrames {
              type uint32;
              description
                "Each entry is the number of I frames that were
                 reproduced by the STB for which some information
                 was missing for this AV stream during the sample
                 interval and loss concealment applied.";
            }
            leaf PDecodedFrames {
              type uint32;
              description
                "Each entry is the number of P frames that were
                 decoded completely (errorless frames) or
                 partially (corrupted frames) by the STB for this
                 AV stream during the sample interval.";
            }
            leaf PLostFrames {
              type uint32;
              description
                "Each entry is the number of P frames that could not
                 be reproduced by the STB for this AV stream
                 during the sample interval.";
            }
            leaf PConcealedFrames {
              type uint32;
              description
                "Each entry is the number of P frames that were
                 reproduced by the STB for which some information
                 was missing for this AV stream during the sample
                 interval and loss concealment applied.";
            }
            leaf BDecodedFrames {
              type uint32;
              description
                "Each entry is the number of B frames that were
                 decoded completely (errorless frames) or
                 partially (corrupted frames) by the STB for this
                 AV stream during the sample interval.";
            }
            leaf BLostFrames {
              type uint32;
              description
                "Each entry is the number of B frames that could not
                 be reproduced by the STB for this AV stream
                 during the sample interval.";
            }
            leaf BConcealedFrames {
              type uint32;
              description
                "Each entry is the number of B frames that were
                 reproduced by the STB for which some information
                 was missing for this AV stream during the sample
                 interval and loss concealment applied.";
            }
            leaf AVResynchCounter {
              type uint32;
              description
                "Each entry is the number of AV resynchronizations
                 that were performed by the STB for this AV
                 stream during the sample interval.";
            }
          }

          container AudioDecoderStats {
            config false;
            description
              "Audio decoder Sample statistics for this
               ''ServiceMonitoring'' main stream instance.";
            leaf SampleSeconds {
              type uint32;
              description
                "Each entry is the number of seconds during which
                 audio decoder data was collected for this AV
                 stream during the sample interval.
              
                 Individual {{param}} values can be less than the
                 sample interval, for several reasons, including:
              
                 * Any of the reasons for which the
                 {{param|.ServiceMonitoring.MainStream.{i}.Sample.SampleSeconds}}
                 values might be less than the sample interval.
              
                 * Audio decoder data collection is not
                 appropriate or possible for this AV stream.";
            }
            leaf DecodedFrames {
              type uint32;
              description
                "Each entry is the number of audio frames that were
                 decoded completely (errorless frames) or
                 partially (corrupted frames) by the STB for this
                 AV stream during the sample interval.";
            }
            leaf DecodingErrors {
              type uint32;
              description
                "Each entry is the number of audio decoding errors
                 detected by the STB for this AV stream during
                 the sample interval.";
            }
          }

          container VideoResponseStats {
            config false;
            description
              "Video response Sample statistics for this
               ''ServiceMonitoring'' main stream instance.";
            leaf SampleSeconds {
              type uint32;
              description
                "Each entry is the number of seconds during which
                 video response data was collected for this AV
                 stream during the sample interval.
              
                 Individual {{param}} values can be less than the
                 sample interval, for several reasons, including:
              
                 * Any of the reasons for which the
                 {{param|.ServiceMonitoring.MainStream.{i}.Sample.SampleSeconds}}
                 values might be less than the sample interval.
              
                 * Video response data collection is not
                 appropriate or possible for this AV stream.";
            }
            leaf AverageVideoSystemResponse {
              type uint32;
              description
                "Each entry is the time period (in {{units}})
                 between the instant of transmitting an IGMP JOIN
                 or an RTSP SETUP command and the display of the
                 first I frame, computed as the average of the
                 VideoSystemResponse events that occured for this
                 AV stream during the sample interval.";
            }
            leaf MinimumVideoSystemResponse {
              type uint32;
              description
                "Each entry is the minimum time period (in
                 {{units}}) between the instant of transmitting
                 an IGMP JOIN or an RTSP SETUP command and the
                 display of the first I frame for this AV stream
                 during the sample interval.";
            }
            leaf MaximumVideoSystemResponse {
              type uint32;
              description
                "Each entry is the maximum time period (in
                 {{units}}) between the instant of transmitting
                 an IGMP JOIN or an RTSP SETUP command and the
                 display of the first I frame for this AV stream
                 during the sample interval.";
            }
            leaf AverageVoDControlResponse {
              type uint32;
              description
                "Each entry is the time period, in {{units}},
                 between the instant of transmitting a RTSP PLAY
                 command to start playing stream, and displaying
                 the first I-frame of unicast stream, computed as
                 the average of the VoDControlResponse events
                 that occured for this AV stream during the
                 sample interval.  Only measured when started
                 from a non-play state, i.e.  either idle or
                 paused.";
            }
            leaf MinimumVoDControlResponse {
              type uint32;
              description
                "Each entry is the minimum time period, in
                 {{units}}, between the instant of transmitting a
                 RTSP PLAY command to start playing stream, and
                 displaying the first I-frame of unicast stream.
                 Only measured when started from a non-play
                 state, i.e.  either idle or paused.";
            }
            leaf MaximumVoDControlResponse {
              type uint32;
              description
                "Each entry is the maximum time period, in
                 {{units}}, between the instant of transmitting a
                 RTSP PLAY command to start playing stream, and
                 displaying the first I-frame of unicast stream.
                 Only measured when started from a non-play
                 state, i.e.  either idle or paused.";
            }
            leaf VoDControlResponse {
              type string {
                pattern "(\d+(:\d+)*)?";
              }
              description
                "Each entry is a colon separated list of time
                 periods in milliseconds between the instant of
                 transmitting a RTSP PLAY command to start
                 playing stream, and displaying the first I-frame
                 of unicast stream.  Only measured when started
                 from a non-play state, i.e.  either idle or
                 paused.
              
                 A comma separates measurements made in different
                 sample intervals, while a colon separates
                 individual measurements within a specific sample
                 interval.
              
                 If no VoDControlResponse measurements were made
                 during a specific sample interval then this MUST
                 be represented by an empty string.
              
                 Example: ,837:453:1234,759,,,923:698,,,1284
              
                 Here there were no measurements during first
                 sample interval, three during the second, one
                 during the third, etc.
              
                 The statistics values in this list MUST be in
                 time order, with the oldest one first and the
                 most recent one last.  This applies both to
                 sample intervals and to individual measurements
                 during a specific sample interval.
                 {{nopattern}}";
            }
            leaf VideoSystemResponse {
              type string {
                pattern "(\d+(:\d+)*)?";
              }
              description
                "Each entry is a colon separated list of time
                 periods in milliseconds between the instant of
                 transmitting an IGMP JOIN or an RTSP SETUP
                 command and the display of the first I frame
                 that occurred for this AV stream during the
                 sample interval.
              
                 A comma separates measurements made in different
                 sample intervals, while a colon separates
                 individual measurements within a specific sample
                 interval.
              
                 If no VideoSystemResponse measurements were made
                 during a specific sample interval then this MUST
                 be represented by an empty string.
              
                 Example: ,837:453:1234,759,,,923:698,,,1284
              
                 Here there were no measurements during first
                 sample interval, three during the second, one
                 during the third, etc.
              
                 The statistics values in this list MUST be in
                 time order, with the oldest one first and the
                 most recent one last.  This applies both to
                 sample intervals and to individual measurements
                 during a specific sample interval.
                 {{nopattern}}";
            }
            leaf RequestedTransactions {
              type uint32;
              description
                "Each entry is the number of RTSP protocol requests
                 to start a VoD program display during the sample
                 interval.
              
                 Only meaningful for VoD.";
            }
            leaf AccessSuccesses {
              type uint32;
              description
                "Each entry is the number of successful VoD attempts
                 during the sample interval.  An attempt is
                 considered successful when the first I-frame is
                 displayed by the client.
              
                 Only meaningful for VoD.";
            }
            leaf CompletionCount {
              type uint32;
              description
                "Each entry is the number of completed VoD requests
                 during the sample interval.  An attempt is
                 defined successful if it continues until a RTSP
                 protocol request to end the session is sent by
                 the STB.
              
                 Only meaningful for VoD.";
            }
            leaf ChannelChangeFailures {
              type uint32;
              description
                "Each entry is the number of channel change
                 failures.  A channel change is considered as
                 failed when the time period between a user
                 channel change request and the display of the
                 first I frame for this AVStream is above
                 {{param|.ServiceMonitoring.MainStream.{i}.ChannelChangeFailureTimeout}}.";
            }
          }

          list HighLevelMetricStats {
            key "MetricName";
            description
              "High-level metric Sample statistics for this
               ''ServiceMonitoring'' main stream instance.  One
               or more different high-level metrics can be
               supported; this is specified by
               {{param|.ServiceMonitoring.MainStream.{i}.Sample.HighLevelMetricStatsNumberOfEntries}}.";
            leaf Enable {
              type boolean;
              description
                "Enables or disables this Metric instance.";
            }
            leaf Status {
              type enumeration {
                enum "Disabled";
                enum "Enabled";
                enum "Error";
              }
              config false;
              description
                "The status of this Metric instance.  {{enum}}
              
                 The {{enum|Error}} value MAY be used by the CPE
                 to indicate a locally defined error condition.";
            }
            leaf MetricName {
              type string {
                length "0..256";
              }
              config false;
              description
                "Indicates a unique identifier for this high-level
                 metric.";
            }
            leaf Metric1Threshold {
              type uint32 {
                range "0..65535";
              }
              description
                "This parameter is DEPRECATED and replaced by the
                 {{param|MetricThreshold}} parameter and, if
                 needed, several instances of
                 {{object|.ServiceMonitoring.MainStream.{i}.Sample.HighLevelMetricStats.}}.";
            }
            leaf Metric2Threshold {
              type uint32 {
                range "0..65535";
              }
              description
                "This parameter is DEPRECATED and replaced by the
                 {{param|MetricThreshold}} parameter and, if
                 needed, several instances of
                 {{object|.ServiceMonitoring.MainStream.{i}.Sample.HighLevelMetricStats.}}.";
            }
            leaf SampleSeconds {
              type uint32;
              config false;
              description
                "Each entry is the number of seconds during which
                 this high-level metric's data was collected for
                 this AV stream during the sample interval.
              
                 Individual {{param}} values can be less than the
                 sample interval, for several reasons, including:
              
                 * Any of the reasons for which the
                 {{param|.ServiceMonitoring.MainStream.{i}.Sample.SampleSeconds}}
                 values might be less than the sample interval.
              
                 * This high-level metric's data collection is
                 not appropriate or possible for this AV stream.";
            }
            leaf Metric1 {
              type uint32 {
                range "0..65535";
              }
              config false;
              description
                "This parameter is DEPRECATED and replaced by the
                 {{param|Metric}} parameter and, if needed,
                 several instances of
                 {{object|.ServiceMonitoring.MainStream.{i}.Sample.HighLevelMetricStats.}}.";
            }
            leaf Metric2 {
              type uint32 {
                range "0..65535";
              }
              config false;
              description
                "This parameter is DEPRECATED and replaced by the
                 {{param|Metric}} parameter and, if needed,
                 several instances of
                 {{object|.ServiceMonitoring.MainStream.{i}.Sample.HighLevelMetricStats.}}.";
            }
            leaf Metric1Failures {
              type uint32;
              config false;
              description
                "This parameter is DEPRECATED and replaced by the
                 {{param|MetricFailures}} parameter and, if
                 needed, several instances of
                 {{object|.ServiceMonitoring.MainStream.{i}.Sample.HighLevelMetricStats.}}.";
            }
            leaf Metric2Failures {
              type uint32;
              config false;
              description
                "This parameter is DEPRECATED and replaced by the
                 {{param|MetricFailures}} parameter and, if
                 needed, several instances of
                 {{object|.ServiceMonitoring.MainStream.{i}.Sample.HighLevelMetricStats.}}.";
            }
            leaf MetricSampleInterval {
              type uint32;
              description
                "A time period measured in {{units}}.  A new value
                 for the high level metric is calculated every
                 {{param}} seconds.
              
                 The value for {{param}} MUST be less than, or
                 equal to,
                 {{param|.ServiceMonitoring.SampleInterval}}.
              
                 {{param}} SHOULD be chosen such that
                 {{param|.ServiceMonitoring.SampleInterval}} is
                 an integer multiple of {{param}}.  If not, the
                 last metric sample interval in each sample
                 interval MUST be shortened so that the last
                 metric sample interval ends when the sample
                 interval ends.
              
                 The value for {{param}} is algorithm-specific.";
            }
            leaf MetricThreshold {
              type uint32 {
                range "0..65535";
              }
              description
                "The threshold value that controls the calculation
                 of the {{param|MetricFailures}} parameter.";
            }
            leaf Metric {
              type uint32 {
                range "0..65535";
              }
              config false;
              description
                "Each entry is a high-level metric calculated for
                 this AV stream during the sample interval as the
                 average of the high level metric values
                 calculated on a metric sample interval basis.
                 The length of the metric sample interval is
                 given by {{param|MetricSampleInterval}}.
              
                 The interpretation of the metric values is
                 algorithm-specific; the only constraints are
                 that values have to be numeric, in the range
                 [0:65535] and that lower values indicate worse
                 QoE than do higher values.";
            }
            leaf MetricFailures {
              type uint32;
              config false;
              description
                "Counts the number of times (since the last time
                 this ''MainStream'' and Sample statistics
                 collection were both enabled) that a
                 newly-calculated value of high-level metric
                 {{param|Metric}} was less than or equal to
                 {{param|MetricThreshold}}.
              
                 This parameter can be incremented at any time
                 during a sample interval, and might be
                 incremented more than once during a single
                 sample interval.";
            }
          }
        }
      }
    }

    container Applications {
      description
        "Applications.";

      list ServiceProvider {
        key "Name";
        description
          "Service Provider instance table.";
        leaf Name {
          type string {
            length "0..256";
          }
          description
            "Service Provider name.";
        }
        leaf Domain {
          type string {
            length "0..256";
          }
          description
            "Service Provider domain URI.";
        }
        leaf ServiceDiscoveryServer {
          type string {
            length "0..256";
          }
          description
            "Service Provider’s Service Discovery Server.  It MAY be
             configured in the format of IMS Public Service
             Identifier, or IP address or URL.";
        }
        leaf ActiveBCGServers {
          type string {
            length "0..1024";
          }
          config false;
          description
            "Comma separated list of the BCG (Broadband Content
             Guide) server URLs the STB is currently retrieving
             IPTV service information from.";
        }
      }

      container AudienceStats {
        description
          "Audience viewing statistics.";
        leaf Enable {
          type boolean;
          description
            "Enables or disables collection of viewing statistics.
             Enabling collection of viewing statistics also
             resets the viewing statistics table.";
        }
        leaf Reset {
          type boolean;
          description
            "When set to {{true}} resets the viewing statistics
             table.  Setting it to {{false}} has no effect.  The
             value is not saved in device state and is always
             {{false}} when read.
          
             Resetting statistics MUST reset all
             {{param|Channel.{i}.Duration}} parameters.";
        }
        leaf ResetTime {
          type uint32;
          config false;
          description
            "Number of {{units}} since the Audience statistics were
             last enabled or reset.";
        }

        list Channel {
          key "Name";
          config false;
          description
            "Table to record what the STB has been receiving.  Time
             durations are recorded only for an AVPlayer's main
             AVStream (i.e.  for TV channels being displayed in
             the main screen).
          
             Each entry corresponds to a given TV channel and is
             indexed by channel name (the instance number is
             chosen by the STB and is not related to the channel
             number).";
          leaf Name {
            type string {
              length "0..256";
            }
            description
              "String describing the TV channel being displayed in
               the main screen.  MUST be the value of the
               corresponding
               {{param|.AVStreams.AVStream.{i}.Name}} parameter.";
          }
          leaf Duration {
            type uint32;
            description
              "The cumulative duration of this channel in {{units}}.";
          }
        }
      }

      container CDSPush {
        description
          "Details of STB CDS Push logical internal parameters.";
        leaf Reference {
          type string {
            length "0..256";
          }
          config false;
          description
            "It references the object instance dedicated to the CDS
             Push service.  Example:
             “Device.Services.StorageService.1.LogicalVolume.1.Folder.1”.";
        }

        list ContentItem {
          key "ContentReferenceId";
          description
            "Content Item instance table.";
          leaf ContentReferenceId {
            type string;
            config false;
            description
              "Unique Content Item reference as defined in
               {{bibref|TS102323}}, or {{bibref|RFC4078}}.";
          }
          leaf VersionNumber {
            type uint32 {
              range "0..255";
            }
            config false;
            description
              "Version number of the stored content item (a content
               item could be updated with a new version e.g.  in
               case of errors in the video preventing the play
               out).";
          }
          leaf DeleteItem {
            type boolean;
            description
              "When set to {{true}}, deletes this Content Item
               instance.  The value is not saved in device state
               and is always {{false}} when read.";
          }
        }
      }

      container CDSPull {
        description
          "Details of STB CDS Pull logical internal component.  This
           object is present only if the user allowed (via his
           local STB UI) the remote management of the CDS Pull
           service.";
        leaf Reference {
          type string {
            length "0..256";
          }
          config false;
          description
            "It references the object instance dedicated to the CDS
             Pull service.  Example:
             “Device.Services.StorageService.1.LogicalVolume.1.Folder.1”.";
        }

        list ContentItem {
          key "ContentReferenceId";
          description
            "Content Item instance table.";
          leaf ContentReferenceId {
            type string;
            config false;
            description
              "Unique Content Item reference as defined in
               {{bibref|TS102323}}, or {{bibref|RFC4078}}.";
          }
          leaf VersionNumber {
            type uint32 {
              range "0..255";
            }
            config false;
            description
              "Version number of the stored content item (a content
               item could be updated with a new version e.g.  in
               case of errors in the video preventing the play
               out).";
          }
          leaf DeleteItem {
            type boolean;
            description
              "When set to {{true}}, deletes this Content Item
               instance.  The value is not saved in device state
               and is always {{false}} when read.";
          }
        }
      }
    }
  }
}
