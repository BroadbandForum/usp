module Device {
  namespace "urn:tbd";
  prefix TBD;
  
  import ietf-yang-types {
    prefix yang;
  }
  
  import tr-106-types {
    prefix types;
  }
  
  organization
    "TBD";
  
  contact
    "TBD";
  
  description
    "";
  
  revision 1970-01-01 {
    description
      "TBD";
    reference
      "TBD";
  }

  container Device {
    description
      "The top-level object for a Device.";
    leaf RootDataModelVersion {
      type string {
        length "0..32";
        pattern "2\.\d+";
      }
      config false;
      description
        "Root data model version, e.g.  ''2.4''.  For a
         vendor-defined root data model, this is the standard
         Broadband Forum model on which the vendor-defined model
         is based.";
    }

    container Services {
      config false;
      description
        "This object contains general services information.";
    }

    container DeviceInfo {
      description
        "This object contains general device information.";
      leaf DeviceCategory {
        type string;
        config false;
        description
          "Each list item is a device category (e.g.  \"AV_TV\" and
           \"AV_Recorder\"), or the value is {{empty}} if no such
           element is provided by the device.
        
           Note: It is assumed that this list might be used for
           HTIP (Home-network Topology Identifying Protocol)
           {{bibref|JJ-300.00}} and {{bibref|G.9973}}.  Standard
           HTIP device categories are defined in
           {{bibref|JJ-300.01}}.  In this case, the maximum
           length of the list is 127 and of each item is 31, and
           any non-HTIP device categories SHOULD NOT conflict
           with standard HTIP device categories.";
      }
      leaf Manufacturer {
        type string {
          length "0..64";
        }
        config false;
        description
          "The manufacturer of the CPE (human readable string).";
      }
      leaf ManufacturerOUI {
        type string {
          length "6";
          pattern "[0-9A-F]{6}";
        }
        config false;
        description
          "Organizationally unique identifier of the device
           manufacturer.  Represented as a six hexadecimal-digit
           value using all upper-case letters and including any
           leading zeros.  {{pattern}}
        
           The value MUST be a valid OUI as defined in
           {{bibref|OUI}}.
        
           This value MUST remain fixed over the lifetime of the
           device, including across firmware updates.  Any change
           would indicate that it's a new device and would
           therefore require a BOOTSTRAP Inform.";
      }
      leaf ModelName {
        type string {
          length "0..64";
        }
        config false;
        description
          "Model name of the CPE (human readable string).";
      }
      leaf ModelNumber {
        type string {
          length "0..64";
        }
        config false;
        description
          "The model number of the device (human readable string),
           or {{empty}} if no model number is provided by the
           device.
        
           Note: It is assumed that this string might be used for
           HTIP (Home-network Topology Identifying Protocol)
           {{bibref|JJ-300.00}} and {{bibref|G.9973}}.  In this
           case, the maximum length of the string is 31.";
      }
      leaf Description {
        type string {
          length "0..256";
        }
        config false;
        description
          "A full description of the CPE device (human readable
           string).";
      }
      leaf ProductClass {
        type string {
          length "0..64";
        }
        config false;
        description
          "Identifier of the class of product for which the serial
           number applies.  That is, for a given manufacturer,
           this parameter is used to identify the product or
           class of product over which the {{param|SerialNumber}}
           parameter is unique.
        
           This value MUST remain fixed over the lifetime of the
           device, including across firmware updates.  Any change
           would indicate that it's a new device and would
           therefore require a BOOTSTRAP Inform.";
      }
      leaf SerialNumber {
        type string {
          length "0..64";
        }
        config false;
        description
          "Identifier of the particular device that is unique for
           the indicated class of product and manufacturer.
        
           This value MUST remain fixed over the lifetime of the
           device, including across firmware updates.  Any change
           would indicate that it's a new device and would
           therefore require a BOOTSTRAP Inform.";
      }
      leaf HardwareVersion {
        type string {
          length "0..64";
        }
        config false;
        description
          "A string identifying the particular CPE model and
           version.";
      }
      leaf SoftwareVersion {
        type string {
          length "0..64";
        }
        config false;
        description
          "A string identifying the software version currently
           installed in the CPE (i.e.  version of the overall CPE
           firmware).
        
           To allow version comparisons, this element SHOULD be
           in the form of dot-delimited integers, where each
           successive integer represents a more minor category of
           variation.  For example, ''3.0.21'' where the
           components mean: ''Major.Minor.Build''.";
      }
      leaf AdditionalHardwareVersion {
        type string;
        config false;
        description
          "{{list}} Each entry is an additional version.  Represents
           any additional hardware version information the vendor
           might wish to supply.";
      }
      leaf AdditionalSoftwareVersion {
        type string;
        config false;
        description
          "{{list}} Each entry is an additional version.  Represents
           any additional software version information the vendor
           might wish to supply.";
      }
      leaf ProvisioningCode {
        type string {
          length "0..64";
        }
        description
          "Identifier of the primary service provider and other
           provisioning information, which MAY be used by the ACS
           to determine service provider-specific customization
           and provisioning parameters.";
      }
      leaf UpTime {
        type uint32;
        config false;
        description
          "Time in {{units}} since the CPE was last restarted.";
      }
      leaf FirstUseDate {
        type yang:date-and-time;
        config false;
        description
          "Date and time in UTC that the CPE first both successfully
           established an IP-layer network connection and
           acquired an absolute time reference using NTP or
           equivalent over that network connection.  The CPE MAY
           reset this date after a factory reset.
        
           If NTP or equivalent is not available, this parameter,
           if present, SHOULD be set to the Unknown Time value.";
      }

      list VendorConfigFile {
        key "Name";
        config false;
        description
          "Every instance of this object is a Vendor Configuration
           File, and contains parameters associated with the
           Vendor Configuration File.
        
           This table of Vendor Configuration Files is for
           information only and does not allow the ACS to operate
           on these files in any way.
        
           Whenever the CPE successfully downloads a
           configuration file as a result of the Download RPC
           with the FileType argument of ''3 Vendor Configuration
           File'', the CPE MUST update this table.";
        leaf Name {
          type string {
            length "0..64";
          }
          description
            "Name of the vendor configuration file.
          
             If the CPE is able to obtain the name of the
             configuration file from the file itself, then the
             value of this parameter MUST be set to that name.
          
             Otherwise, if the CPE can extract the file name from
             the URL used to download the configuration file,
             then the value of this parameter MUST be set to that
             name.
          
             Otherwise, the value of this parameter MUST be set
             to the value of the TargetFileName argument of the
             Download RPC used to download this configuration
             file.";
        }
        leaf Version {
          type string {
            length "0..16";
          }
          description
            "A string identifying the configuration file version
             currently used in the CPE.
          
             If the CPE is able to obtain the version of the
             configuration file from the file itself, then the
             value of this parameter MUST be set to the obtained
             value.
          
             Otherwise, the value of this parameter MUST be
             {{empty}}.";
        }
        leaf Date {
          type yang:date-and-time;
          description
            "Date and time when the content of the current version
             of this vendor configuration file was first applied
             by the CPE.";
        }
        leaf Description {
          type string {
            length "0..256";
          }
          description
            "A description of the vendor configuration file
             (human-readable string).";
        }
        leaf UseForBackupRestore {
          type boolean;
          description
            "When {{true}}, this parameter indicates that this
             {{object}} instance is to be used for backup and
             restoration purposes.
          
             Note: The backup and restore operations may require
             the use of multiple {{object}} instances.  In this
             scenario the mechanism for detemining the order and
             combination of {{object}} instances used for backup
             and restoration purposes is implementation specific.";
        }
      }

      list SupportedDataModel {
        key "URL";
        config false;
        description
          "This table contains details of the device's Current
           Supported Data Model.
        
           The table MUST describe the device's entire Supported
           Data Model.  Therefore, if a device's Supported Data
           Model changes at run-time, entries will need to be
           added or removed as appropriate.
        
           Each table entry MUST refer to only a single Root
           Object or Service Object.  The device MAY choose to
           use more than one table entry for a given Root Object
           or Service Object.
        
           Considering that every device has some form of a data
           model, this table MUST NOT be empty.";
        leaf URL {
          type string {
            length "0..256";
          }
          description
            "URL ({{bibref|RFC3986}}) that describes some or all of
             the device's Current Supported Data Model.
          
             The URL MUST reference an XML file which describes
             the appropriate part of the Supported Data Model.
          
             The referenced XML file MUST be compliant with the
             DT (Device Type) Schema that is described in
             {{bibref|TR-106a3|Annex B}}, including any
             additional normative requirements referenced within
             the Schema.
          
             The XML file referenced by this URL MUST NOT change
             while the CPE is running, and SHOULD NOT change
             across a CPE reboot.  Note that {{param|UUID}} is a
             unique key, so the XML file referenced by this URL
             will never change.
          
             The XML file MAY be located within the CPE.  In this
             scenario the CPE MAY use the value of \"localhost\"
             as URL host portion, When the \"localhost\" value is
             used, the ACS has the responsibility to substitute
             the \"localhost\" value with the host portion of the
             connection request URL.
          
             Behavior in the event of an invalid URL, failure to
             access the referenced XML file, or an invalid XML
             file, is implementation-dependent.";
        }
        leaf UUID {
          type yang:uuid;
          description
            "UUID ({{bibref|RFC4122}}) that is the value of the uuid
             attribute in the DT Instance referenced by
             {{param|URL}}.";
        }
        leaf URN {
          type string {
            length "0..256";
          }
          description
            "URN ({{bibref|RFC3986}}) that is the value of the spec
             attribute in the DM (data model) Instance that
             defines the Root Object or Service Object referenced
             by this table entry.
          
             For example, if this table entry references a DT
             Instance that refers to the ''Device:1.3'' Root
             Object, the value of this parameter would be
             ''urn:broadband-forum-org:tr-157-1-0-0'', because
             TR-157 defines ''Device:1.3''.  If the DT Instance
             instead referred to a vendor-specific Root Object,
             e.g.  ''X_EXAMPLE_Device:1.0'' (derived from
             ''Device:1.3''), the value of this parameter would
             be something like ''urn:example-com:device-1-0-0''.";
        }
        leaf Features {
          type string;
          description
            "This parameter MUST list exactly the features that are
             defined using the top-level ''feature'' element in
             the DT Instance referenced by {{param|URL}}.
          
             For example, if the DT instance specified the
             following:
          
             :<feature name=\"DNSServer\"/>
          
             :<feature name=\"Router\"/>
          
             :<feature name=\"X_MyDeviceFeature\"/>
          
             then the value of this parameter might be
             ''DNSServer,Router,X_MyDeviceFeature''.  The order
             in which the features are listed is not significant.";
        }
      }

      container MemoryStatus {
        config false;
        description
          "Status of the device's volatile physical memory.";
        leaf Total {
          type uint32;
          description
            "The total physical RAM, in {{units}}, installed on the
             device.";
        }
        leaf Free {
          type uint32;
          description
            "The free physical RAM, in {{units}}, currently
             available on the device.";
        }
      }

      container ProcessStatus {
        config false;
        description
          "Status of the processes on the device.";
        leaf CPUUsage {
          type uint32 {
            range "min..100";
          }
          description
            "The total amount of the CPU, in {{units}}, rounded up
             to the nearest whole {{units}}.  In the case that
             multiple CPU are present, this value represents the
             average of all CPU.";
        }

        list Process {
          key "PID";
          description
            "List of all processes running on the device.";
          leaf PID {
            type uint32;
            description
              "The Process Identifier.";
          }
          leaf Command {
            type string {
              length "0..256";
            }
            description
              "The name of the command that has caused the process
               to exist.";
          }
          leaf Size {
            type uint32;
            description
              "The size in {{units}} of the memory occupied by the
               process.";
          }
          leaf Priority {
            type uint32 {
              range "min..99";
            }
            description
              "The priority of the process where 0 is highest.";
          }
          leaf CPUTime {
            type uint32;
            description
              "The amount of time in {{units}} that the process has
               spent taking up CPU time since the process was
               started.";
          }
          leaf State {
            type enumeration {
              enum "Running";
              enum "Sleeping";
              enum "Stopped";
              enum "Idle";
              enum "Uninterruptible";
              enum "Zombie";
            }
            description
              "The current state that the process is in.";
          }
        }
      }

      container TemperatureStatus {
        description
          "Status of the temperature of the device.";

        list TemperatureSensor {
          key "Name";
          description
            "This object represents information that the device has
             obtained via sampling an internal temperature
             sensor.";
          leaf Enable {
            type boolean;
            description
              "Indicates whether or not the temperature sensor is
               enabled.";
          }
          leaf Status {
            type enumeration {
              enum "Disabled";
              enum "Enabled";
              enum "Error";
            }
            config false;
            description
              "The status of this temperature sensor.";
          }
          leaf Reset {
            type boolean;
            description
              "When set to {{true}}, resets the temperature sensor.";
          }
          leaf ResetTime {
            type yang:date-and-time;
            config false;
            description
              "The time at which this temperature sensor was reset.
            
               Reset can be caused by:
            
               * {{param|Status}} transition from
               {{enum|Disabled|Status}} to
               {{enum|Enabled|Status}}
            
               * {{param|Reset}} set to {{true}}.
            
               * An internal reset of the temperature sensor
               (including a reboot of the device).
            
               The Unknown Time value, as defined in
               {{bibref|TR-106a2}}, indicates that this
               temperature sensor has never been reset, which can
               only happen if it has never been enabled.";
          }
          leaf Name {
            type string {
              length "0..256";
            }
            config false;
            description
              "Name of this temperature sensor.  This text MUST be
               sufficient to distinguish this temperature sensor
               from other temperature sensors.";
          }
          leaf Value {
            type int32 {
              range "-274..max";
            }
            config false;
            description
              "This temperature sensor's last good reading in
               {{units}}.
            
               A value of -274 (which is below absolute zero)
               indicates a good reading has not been obtained
               since last reset.";
          }
          leaf LastUpdate {
            type yang:date-and-time;
            config false;
            description
              "The time at which this temperature sensor's last good
               reading was obtained.
            
               The Unknown Time value, as defined in
               {{bibref|TR-106a2}}, indicates a good reading has
               not been obtained since last reset.";
          }
          leaf MinValue {
            type int32 {
              range "-274..max";
            }
            config false;
            description
              "This temperature sensor's lowest value reading in
               {{units}} since last reset.
            
               A value of -274 (which is below absolute zero)
               indicates a good reading has not been obtained
               since last reset.";
          }
          leaf MinTime {
            type yang:date-and-time;
            config false;
            description
              "The time at which this temperature sensor's lowest
               value was read.
            
               The Unknown Time value, as defined in
               {{bibref|TR-106a2}}, indicates a good reading has
               not been obtained since last reset.";
          }
          leaf MaxValue {
            type int32 {
              range "-274..max";
            }
            config false;
            description
              "This temperature sensor's highest value reading in
               {{units}} since last reset.
            
               A value of -274 (which is below absolute zero)
               indicates a good reading has not been obtained
               since last reset.";
          }
          leaf MaxTime {
            type yang:date-and-time;
            config false;
            description
              "The time at which this temperature sensor's highest
               value was read.
            
               The Unknown Time value, as defined in
               {{bibref|TR-106a2}}, indicates a good reading has
               not been obtained since last reset.";
          }
          leaf LowAlarmValue {
            type int32 {
              range "-274..max";
            }
            description
              "This temperature sensor's low alarm value in
               {{units}}.
            
               A value of -274 (which is below absolute zero)
               indicates a non configured value.
            
               A change to this value will cause
               {{param|LowAlarmTime}} to be reset.";
          }
          leaf LowAlarmTime {
            type yang:date-and-time;
            config false;
            description
              "Initial time at which this temperature sensor's
               {{param|LowAlarmValue}} was encountered.
            
               This value is only set the first time the alarm is
               seen and not changed until the next reset.
            
               The Unknown Time value, as defined in
               {{bibref|TR-106a2}}, indicates that an alarm has
               not been encountered since the last reset.";
          }
          leaf HighAlarmValue {
            type int32 {
              range "-274..max";
            }
            description
              "This temperature sensor's high alarm value in
               {{units}}.
            
               A value of -274 (which is below absolute zero)
               indicates a non configured value.
            
               A change to this value will cause
               {{param|HighAlarmTime}} to be reset.";
          }
          leaf PollingInterval {
            type uint32;
            description
              "The interval, measured in {{units}}, in which the
               device polls this {{object}}.
            
               If the value is 0 then the device selects its own
               polling interval.
            
               If the value is greater than 0 then the device
               MUST use this value as the polling interval.";
          }
          leaf HighAlarmTime {
            type yang:date-and-time;
            config false;
            description
              "Initial time at which this temperature sensor's
               {{param|HighAlarmValue}} was encountered.
            
               This value is only set the first time the alarm is
               seen and not changed until the next reset.
            
               The Unknown Time value, as defined in
               {{bibref|TR-106a2}}, indicates that an alarm has
               not been encountered since the last reset.";
          }
        }
      }

      container NetworkProperties {
        config false;
        description
          "This object defines the parameters that describe how the
           device handles network traffic.";
        leaf MaxTCPWindowSize {
          type uint32;
          description
            "The maximum number of {{units}} of outstanding data a
             sender can send on a particular connection prior to
             an acknowledgment {{bibref|RFC793}}.  Any scaling
             factor SHOULD be included in this parameter
             {{bibref|RFC1323}}.";
        }
        leaf TCPImplementation {
          type enumeration {
            enum "Tahoe";
            enum "Reno";
            enum "New Reno";
            enum "Vegas";
          }
          description
            "{{list}} Indicates the TCP congestion control
             mechanism(s) implemented.  {{enum}}
          
             Tahoe, Reno, and New Reno are defined in
             {{bibref|RFC2582}}";
        }
      }

      list Processor {
        key "Alias";
        config false;
        description
          "Each table entry represents a hardware or virtual
           processor that resides on this device.";
        leaf Architecture {
          type enumeration {
            enum "arm";
            enum "i386";
            enum "m68010";
            enum "m68k";
            enum "mipseb";
            enum "mipsel";
            enum "powerpc";
            enum "sh3eb";
            enum "sh3el";
            enum "x86_64";
          }
          description
            "The architecture of the processor on the underlying
             hardware.  {{enum}}
          
             For processor architectures not included in this
             list, the vendor MAY include vendor-specific values,
             which MUST use the format defined in
             {{bibref|TR-106a4|Section 3.3}}.";
        }
      }

      list VendorLogFile {
        key "Alias";
        config false;
        description
          "Each table entry represents a Vendor Log File.
        
           This table of log files is informational only and does
           not allow the ACS to operate on these files in any
           way.";
        leaf Name {
          type string {
            length "0..64";
          }
          description
            "Name of the log file.
          
             Typically this will be the full file system path,
             but provided that it is guaranteed to be unique
             across current and future log files, it MAY be a
             shorter name derived from the file system path, or
             be derived via another mechanism.";
        }
        leaf MaximumSize {
          type uint32;
          description
            "The maximum size of the log file in {{units}}.  If the
             device doesn't know the maximum file size then
             {{param}} will be 0.";
        }
        leaf Persistent {
          type boolean;
          description
            "When {{true}}, the log file contents are preserved
             across a device reboot.
          
             When {{false}}, the log file contents will be purged
             when the device is rebooted.";
        }
      }

      container ProxierInfo {
        config false;
        description
          "Represents the associated CPE Proxier for a Proxied
           Device that utilizes the Virtual CWMP Device Mechanism
           {{bibref|TR-069a4|Annex J.1.1}}.";
        leaf ManufacturerOUI {
          type string {
            length "6";
            pattern "[0-9A-F]{6}";
          }
          description
            "Organizationally unique identifier of the associated
             CPE Proxier.  Represented as a six hexadecimal-digit
             value using all upper-case letters and including any
             leading zeros.  {{pattern}}
          
             The value MUST be a valid OUI as defined in
             {{bibref|OUI}}.";
        }
        leaf ProductClass {
          type string {
            length "0..64";
          }
          description
            "Identifier of the class of product of the associated
             CPE Proxier for which the serial number applies.
          
             {{empty}} indicates either that the CPE Proxier does
             not use a product class to differentiate its serial
             number.";
        }
        leaf SerialNumber {
          type string {
            length "0..64";
          }
          description
            "Serial number of the associated CPE Proxier.";
        }
        leaf ProxyProtocol {
          type enumeration {
            enum "Z-Wave";
            enum "ZigBee";
            enum "UPnP-DM";
            enum "ETSI-M2M";
          }
          description
            "The protocol being used to communicate between the CPE
             Proxier and this Proxied Device.  {{enum}}
          
             Vendors can extend the enumerated values with vendor
             specific extensions, in which case the rules
             outlined in {{bibref|TR-106a6|3.3}} MUST be adhered
             to.";
        }
      }

      list Location {
        key "Source ExternalSource";
        description
          "This object contains Location information.";
        leaf Source {
          type enumeration {
            enum "GPS";
            enum "AGPS";
            enum "Manual";
            enum "External";
          }
          config false;
          default "External";
          description
            "Identifies the source of the location data.";
        }
        leaf AcquiredTime {
          type yang:date-and-time;
          config false;
          description
            "The time when the location was acquired.";
        }
        leaf ExternalSource {
          type string;
          config false;
          description
            "URL, MAC address, or other identifier that identifies
             an \"External\" source of this location.
          
             Meaningful only if {{param|Source}} has a value of
             {{enum|External|Source}}, otherwise it MUST be
             {{empty}}.
          
             If {{param|ExternalProtocol}} has a value of
             {{enum|CWMP|ExternalProtocol}}, this is the URL or
             IP address of the ACS.";
        }
        leaf ExternalProtocol {
          type enumeration {
            enum "";
            enum "CWMP";
            enum "OMA-DM";
            enum "SNMP";
            enum "UPnP";
            enum "HELD";
            enum "DHCPv4";
            enum "DHCPv6";
            enum "LLDP-MED";
            enum "MLP";
            enum "Other";
          }
          config false;
          default "CWMP";
          description
            "Protocol used to acquire a location from an
             \"External\" source.  {{enum}}
          
             Meaningful only if {{param|Source}} has a value of
             {{enum|External|Source}}, otherwise it MUST be
             {{empty}}.";
        }
        leaf DataObject {
          type string {
            length "0..1200";
          }
          description
            "The currently valid location information.
          
             Writable only when {{param|ExternalProtocol}} has a
             value of {{enum|CWMP|ExternalProtocol}}.
          
             If obtained through the local GPS/AGPS then the
             location information is formatted according to
             {{bibref|RFC5491}}.
          
             If manually configured then location information
             will be XML-formatted according to
             {{bibref|RFC5491}} (geographical information) and
             {{bibref|RFC5139}} (civic addresses).
          
             If obtained by an external source this is the
             location information as received.
          
             If it's an XML document (e.g.  CWMP, OMA-DM, UPnP,
             HELD, MLP) the location information will be
             represented as-is, otherwise it will be converted to
             base64.
          
             CWMP configured location information will be
             XML-formatted according to {{bibref|RFC5491}}
             (geographical information) and {{bibref|RFC5139}}
             (civic addresses).
          
             Only zero or one Location object instance with value
             {{enum|CWMP|ExternalProtocol}} MUST exist at any
             given time.";
        }
      }
    }

    container ManagementServer {
      description
        "This object contains parameters relating to the CPE's
         association with an ACS.";
      leaf EnableCWMP {
        type boolean;
        default "true";
        description
          "Enables and disables the CPE's support for CWMP.
        
           {{false}} means that CWMP support in the CPE is
           disabled, in which case the device MUST NOT send any
           Inform messages to the ACS or accept any Connection
           Request notifications from the ACS.
        
           {{true}} means that CWMP support on the CPE is
           enabled.
        
           The subscriber can re-enable the CPE's CWMP support
           either by performing a factory reset or by using a
           LAN-side protocol to change the value of this
           parameter back to {{true}}.";
      }
      leaf URL {
        type string {
          length "0..256";
        }
        description
          "URL, as defined in {{bibref|RFC3986}}, for the CPE to
           connect to the ACS using the CPE WAN Management
           Protocol.
        
           This parameter MUST be in the form of a valid HTTP or
           HTTPS URL.
        
           The ''host'' portion of this URL is used by the CPE
           for validating the ACS certificate when using SSL or
           TLS.
        
           Note that on a factory reset of the CPE, the value of
           this parameter might be reset to its factory value.
           If an ACS modifies the value of this parameter, it
           SHOULD be prepared to accommodate the situation that
           the original value is restored as the result of a
           factory reset.";
      }
      leaf Username {
        type string {
          length "0..256";
        }
        description
          "Username used to authenticate the CPE when making a
           connection to the ACS using the CPE WAN Management
           Protocol.
        
           This username is used only for HTTP-based
           authentication of the CPE.
        
           Note that on a factory reset of the CPE, the value of
           this parameter might be reset to its factory value.
           If an ACS modifies the value of this parameter, it
           SHOULD be prepared to accommodate the situation that
           the original value is restored as the result of a
           factory reset.";
      }
      leaf Password {
        type string {
          length "0..256";
        }
        description
          "Password used to authenticate the CPE when making a
           connection to the ACS using the CPE WAN Management
           Protocol.
        
           This password is used only for HTTP-based
           authentication of the CPE.
        
           Note that on a factory reset of the CPE, the value of
           this parameter might be reset to its factory value.
           If an ACS modifies the value of this parameter, it
           SHOULD be prepared to accommodate the situation that
           the original value is restored as the result of a
           factory reset.";
      }
      leaf ScheduleReboot {
        type yang:date-and-time;
        description
          "An absolute date and time in UTC at which time the CPE
           will perform a reboot.
        
           If a CWMP session is in progress at the specified
           time, the CPE MUST wait until the session has ended
           before performing the reboot.
        
           If the value specifies a date and time that has
           already passed (ie, a past date and time), no reboot
           will be performed.";
      }
      leaf DelayReboot {
        type int32 {
          range "-1..max";
        }
        description
          "The number of seconds from the time the CWMP session in
           which this parameter value is set is ended until the
           CPE performs a reboot.
        
           Whenever the CPE reboots, this value must be reset by
           the CPE to -1.";
      }
      leaf PeriodicInformEnable {
        type boolean;
        description
          "Whether or not the CPE MUST periodically send CPE
           information to the ACS using the Inform method call.";
      }
      leaf PeriodicInformInterval {
        type uint32 {
          range "1..max";
        }
        description
          "The duration in {{units}} of the interval for which the
           CPE MUST attempt to connect with the ACS and call the
           Inform method if {{param|PeriodicInformEnable}} is
           {{true}}.";
      }
      leaf PeriodicInformTime {
        type yang:date-and-time;
        description
          "An absolute time reference in UTC to determine when the
           CPE will initiate the periodic Inform method calls.
           Each Inform call MUST occur at this reference time
           plus or minus an integer multiple of the
           {{param|PeriodicInformInterval}}.
        
           {{param}} is used only to set the ''phase'' of the
           periodic Informs.  The actual value of {{param}} can
           be arbitrarily far into the past or future.
        
           For example, if {{param|PeriodicInformInterval}} is
           86400 (a day) and if {{param}} is set to UTC midnight
           on some day (in the past, present, or future) then
           periodic Informs will occur every day at UTC midnight.
           These MUST begin on the very next midnight, even if
           {{param}} refers to a day in the future.
        
           The Unknown Time value defined in
           {{bibref|TR-106a2|section 3.2}} indicates that no
           particular time reference is specified.  That is, the
           CPE MAY locally choose the time reference, and needs
           only to adhere to the specified
           {{param|PeriodicInformInterval}}.
        
           If absolute time is not available to the CPE, its
           periodic Inform behavior MUST be the same as if the
           {{param}} parameter was set to the Unknown Time value.";
      }
      leaf ParameterKey {
        type string {
          length "0..32";
        }
        config false;
        description
          "{{param}} provides the ACS a reliable and extensible
           means to track changes made by the ACS.  The value of
           {{param}} MUST be equal to the value of the
           ParameterKey argument from the most recent successful
           SetParameterValues, AddObject, or DeleteObject method
           call from the ACS.
        
           The CPE MUST set {{param}} to the value specified in
           the corresponding method arguments if and only if the
           method completes successfully and no fault response is
           generated.  If a method call does not complete
           successfully (implying that the changes requested in
           the method did not take effect), the value of
           {{param}} MUST NOT be modified.
        
           The CPE MUST only modify the value of {{param}} as a
           result of SetParameterValues, AddObject, DeleteObject,
           or due to a factory reset.  On factory reset, the
           value of {{param}} MUST be set to {{empty}}.";
      }
      leaf ConnectionRequestURL {
        type string {
          length "0..256";
        }
        config false;
        description
          "HTTP URL, as defined in {{bibref|RFC3986}}, for an ACS to
           make a Connection Request notification to the CPE.
        
           In the form:
        
           : http://host:port/path
        
           The ''host'' portion of the URL MAY be the IP address
           for the management interface of the CPE in lieu of a
           host name.
        
           Note: If the ''host'' portion of the URL is a literal
           IPv6 address then it MUST be enclosed in square
           brackets (see {{bibref|RFC3986|Section 3.2.2}}).";
      }
      leaf ConnectionRequestUsername {
        type string {
          length "0..256";
        }
        description
          "Username used to authenticate an ACS making a Connection
           Request to the CPE.";
      }
      leaf ConnectionRequestPassword {
        type string {
          length "0..256";
        }
        description
          "Password used to authenticate an ACS making a Connection
           Request to the CPE.";
      }
      leaf UpgradesManaged {
        type boolean;
        description
          "Indicates whether or not the ACS will manage upgrades for
           the CPE.  If {{true}}, the CPE SHOULD NOT use other
           means other than the ACS to seek out available
           upgrades.  If {{false}}, the CPE MAY use other means
           for this purpose.
        
           Note that an autonomous upgrade (reported via an \"10
           AUTONOMOUS TRANSFER COMPLETE\" Inform Event code)
           SHOULD be regarded as a managed upgrade if it is
           performed according to ACS-specified policy.";
      }
      leaf KickURL {
        type string {
          length "0..256";
        }
        config false;
        description
          "Present only for a CPE that supports the Kicked RPC
           method.
        
           LAN-accessible URL, as defined in {{bibref|RFC3986}},
           from which the CPE can be ''kicked'' to initiate the
           Kicked RPC method call.  MUST be an absolute URL
           including a host name or IP address as would be used
           on the LAN side of the CPE.";
      }
      leaf DownloadProgressURL {
        type string {
          length "0..256";
        }
        config false;
        description
          "Present only for a CPE that provides a LAN-side web page
           to show progress during a file download.
        
           LAN-accessible URL, as defined in {{bibref|RFC3986}},
           to which a web-server associated with the ACS MAY
           redirect a user's browser on initiation of a file
           download to observer the status of the download.";
      }
      leaf DefaultActiveNotificationThrottle {
        type uint32;
        description
          "This parameter is used to control throttling of active
           notifications sent by the CPE to the ACS.  It defines
           the minimum number of {{units}} that the CPE MUST wait
           since the end of the last session with the ACS before
           establishing a new session for the purpose of
           delivering an active notification.
        
           In other words, if CPE needs to establish a new
           session with the ACS for the sole purpose of
           delivering an active notification, it MUST delay
           establishing such a session as needed to ensure that
           the minimum time since the last session completion has
           been met.
        
           The time is counted since the last successfully
           completed session, regardless of whether or not it was
           used for active notifications or other purposes.
           However, if connection to the ACS is established for
           purposes other than just delivering active
           notifications, including for the purpose of retrying a
           failed session, such connection MUST NOT be delayed
           based on this parameter value, and the pending active
           notifications MUST be communicated during that
           connection.
        
           The time of the last session completion does not need
           to be tracked across reboots.";
      }
      leaf CWMPRetryMinimumWaitInterval {
        type uint32 {
          range "1..65535";
        }
        description
          "Configures the first session retry wait interval, in
           {{units}}, as specified in {{bibref|TR-069a2|section
           3.2.1.1}}.
        
           A value of 5 corresponds to the default behavior that
           is described in {{bibref|TR-069a2}}.
        
           The device MUST use a random value between {{param}}
           and ({{param}} * {{param|CWMPRetryIntervalMultiplier}}
           / 1000) as the first retry wait interval.  Other
           values in the retry pattern MUST be calculated using
           this value as a starting point.";
      }
      leaf CWMPRetryIntervalMultiplier {
        type uint32 {
          range "1000..65535";
        }
        description
          "Configures the retry interval multiplier as specified in
           {{bibref|TR-069a2|section 3.2.1.1}}.
        
           This value is expressed in units of 0.001.  Hence the
           values of the multiplier range between 1.000 and
           65.535.
        
           A value of 2000 corresponds to the default behavior
           that is described in {{bibref|TR-069a2}}.
        
           The device MUST use a random value between
           {{param|CWMPRetryMinimumWaitInterval}} and
           ({{param|CWMPRetryMinimumWaitInterval}} * {{param}} /
           1000) as the first retry wait interval.  Other values
           in the retry pattern MUST be calculated using this
           value as a starting point.";
      }
      leaf UDPConnectionRequestAddress {
        type string {
          length "0..256";
        }
        config false;
        description
          "Address and port to which an ACS MAY send a UDP
           Connection Request to the CPE (see
           {{bibref|TR-069a2|Annex G}}).
        
           This parameter is represented in the form of an
           Authority element as defined in {{bibref|RFC3986}}.
           The value MUST be in one of the following two forms:
        
           : host:port
        
           : host
        
           * When {{param|STUNEnable}} is {{true}}, the ''host''
           and ''port'' portions of this parameter MUST represent
           the public address and port corresponding to the NAT
           binding through which the ACS can send UDP Connection
           Request messages (once this information is learned by
           the CPE through the use of STUN).
        
           * When {{param|STUNEnable}} is {{false}}, the ''host''
           and ''port'' portions of the URL MUST represent the
           local IP address and port on which the CPE is
           listening for UDP Connection Request messages.
        
           The second form of this parameter MAY be used only if
           the port value is equal to ''80''.
        
           Note: If the ''host'' portion of the URL is a literal
           IPv6 address then it MUST be enclosed in square
           brackets (see {{bibref|RFC3986|Section 3.2.2}}).";
      }
      leaf STUNEnable {
        type boolean;
        description
          "Enables or disables the use of STUN by the CPE.  This
           applies only to the use of STUN in association with
           the ACS to allow UDP Connection Requests.";
      }
      leaf STUNServerAddress {
        type string {
          length "0..256";
        }
        description
          "Host name or IP address of the STUN server for the CPE to
           send Binding Requests if STUN is enabled via
           {{param|STUNEnable}}.
        
           If is {{empty}} and {{param|STUNEnable}} is {{true}},
           the CPE MUST use the address of the ACS extracted from
           the host portion of the ACS URL.";
      }
      leaf STUNServerPort {
        type uint32 {
          range "0..65535";
        }
        description
          "Port number of the STUN server for the CPE to send
           Binding Requests if STUN is enabled via
           {{param|STUNEnable}}.
        
           By default, this SHOULD be the equal to the default
           STUN port, 3478.";
      }
      leaf STUNUsername {
        type string {
          length "0..256";
        }
        description
          "If is not {{empty}}, the value of the STUN USERNAME
           attribute to be used in Binding Requests (only if
           message integrity has been requested by the STUN
           server).
        
           If is {{empty}}, the CPE MUST NOT send STUN Binding
           Requests with message integrity.";
      }
      leaf STUNPassword {
        type string {
          length "0..256";
        }
        description
          "The value of the STUN Password to be used in computing
           the MESSAGE-INTEGRITY attribute to be used in Binding
           Requests (only if message integrity has been requested
           by the STUN server).";
      }
      leaf STUNMaximumKeepAlivePeriod {
        type int32 {
          range "-1..max";
        }
        description
          "If STUN Is enabled, the maximum period, in {{units}},
           that STUN Binding Requests MUST be sent by the CPE for
           the purpose of maintaining the binding in the Gateway.
           This applies specifically to Binding Requests sent
           from the UDP Connection Request address and port.
        
           A value of -1 indicates that no maximum period is
           specified.";
      }
      leaf STUNMinimumKeepAlivePeriod {
        type uint32;
        description
          "If STUN Is enabled, the minimum period, in {{units}},
           that STUN Binding Requests can be sent by the CPE for
           the purpose of maintaining the binding in the Gateway.
           This limit applies only to Binding Requests sent from
           the UDP Connection Request address and port, and only
           those that do not contain the BINDING-CHANGE
           attribute.  This limit does not apply to
           retransmissions following the procedures defined in
           {{bibref|RFC3489}}.";
      }
      leaf NATDetected {
        type boolean;
        config false;
        description
          "When STUN is enabled, this parameter indicates whether or
           not the CPE has detected address and/or port mapping
           in use.
        
           A {{true}} value indicates that the received
           MAPPED-ADDRESS in the most recent Binding Response
           differs from the CPE's source address and port.
        
           When {{param|STUNEnable}} is {{false}}, this value
           MUST be {{false}}.";
      }
      leaf AliasBasedAddressing {
        type boolean;
        config false;
        description
          "Indicates whether or not the Alias-Based Addressing
           Mechanism is supported.
        
           A {{true}} value indicates that the CPE supports the
           Alias-Based Addressing Mechanism, as defined in
           {{bibref|TR-069a4|3.6.1}} and described in
           {{bibref|TR-069a4|Appendix II}}.";
      }
      leaf InstanceMode {
        type enumeration {
          enum "InstanceNumber";
          enum "InstanceAlias";
        }
        default "InstanceNumber";
        description
          "Instance identification mode as defined in
           {{bibref|TR-069a4|3.6.1}}.  When
           {{param|AliasBasedAddressing}} is {{true}}, {{param}}
           is used by the ACS to control whether the CPE will use
           Instance Numbers or Instance Aliases in returned Path
           Names.  {{enum}}
        
           This parameter is REQUIRED for any CPE supporting
           Alias-Based Addressing.";
      }
      leaf AutoCreateInstances {
        type boolean;
        default "false";
        description
          "Enable or disable the Auto-Create Instance Mechanism.
           When {{param|AliasBasedAddressing}} is {{true}},
           {{param}} indicates whether or not the CPE will
           automatically create instances while processing a
           SetParameterValues RPC (as defined in
           {{bibref|TR-069a4|A.3.2.1}}).
        
           *A {{true}} value indicates that the CPE will perform
           auto-creation of instances when the Alias-Based
           Addressing Mechanism is used in SetParameterValues
           RPC.
        
           *A {{false}} value indicates that the CPE will not
           create new object instances.  Instead, it will reject
           the setting of parameters in unrecognized instances
           and respond with a fault code.
        
           This parameter is REQUIRED for any CPE supporting
           Alias-Based Addressing.";
      }
      leaf ManageableDeviceNotificationLimit {
        type uint32;
        description
          "The minimum time, in seconds, between Active
           Notifications resulting from changes to the
           {{param|ManageableDeviceNumberOfEntries}} (if Active
           Notification is enabled).";
      }
      leaf SupportedConnReqMethods {
        type enumeration {
          enum "HTTP";
          enum "STUN";
          enum "XMPP";
        }
        config false;
        description
          "The connection request methods supported by this
           {{object}}.  {{enum}}";
      }
      leaf ConnReqXMPPConnection {
        type string;
        description
          "{{reference|the {{object|.XMPP.Connection}} instance that
           is used for connection requests to this {{object}}}}";
      }
      leaf ConnReqAllowedJabberIDs {
        type string {
          length "0..256";
        }
        description
          "When an XMPP Connection Request is sent to a CPE the XMPP
           IQ Stanza will contian a \"from\" address that
           contains the Jabber ID of the initiating entity.
        
           This parameter is a {{list}} Each entry represents a
           Jabber ID, or address, that is allowed to initiate an
           XMPP Connection Request.
        
           Each Jabber ID is allowed to be either a \"Full JID\"
           (containing a local-part, domain-part, and
           resource-part in the following format:
           \"local-part@domain-part/resource-part\") or a \"Bare
           JID\" (containing a local-part and a domain-part in
           the following format: \"local-part@domain-part\").
           \"Full JID\" entries require an exact match whereas
           \"Bare JID\" entries are a wildcard match and will
           match any Jabber ID with the same local-part and
           domain-part independent of the resource-part.
        
           For example, if {{param}} contained
           \"ACS1@tr069.example.com,
           ACS2@tr-069.example.com/resource1\" then the following
           incoming \"from\" addresses would be '''allowed''':
        
           * \"ACS1@tr069.example.com/resource1\"
        
           * \"ACS1@tr069.example.com/resource2\"
        
           * \"ACS2@tr069.example.com/resource1\"
        
           And the following incoming \"from\" addresses '''would
           not be allowed''':
        
           * \"ACS2@tr069.example.com/resource2\"
        
           * \"ACS@tr069.example.com/resource\"
        
           If this Parameter is {{empty}} then all Jabber IDs are
           allowed and an XMPP Connection Request can not be
           deemed invalid due to the \"from\" address.";
      }
      leaf ConnReqJabberID {
        type string;
        config false;
        description
          "The value MUST be the value of the
           {{param|.XMPP.Connection.{i}.JabberID}} contained in
           the {{object|.XMPP.Connection}} instance referenced by
           the {{param|ConnReqXMPPConnection}} parameter.
        
           If the {{param|ConnReqXMPPConnection}} parameter is
           empty or the {{object|.XMPP.Connection}} instance
           being reference is disabled, then this value will be
           empty.
        
           If the {{object|.XMPP.Connection}} instance being
           referenced by the {{param|ConnReqXMPPConnection}}
           parameter is lost
           ({{param|.XMPP.Connection.{i}.Status}} parameter
           changes from Enabled to some other value), then the
           value of this parameter MUST remain unchanged until
           the connection can be reestablished and a new
           {{param|.XMPP.Connection.{i}.JabberID}} can be
           established.  If the new
           {{param|.XMPP.Connection.{i}.JabberID}} is identical
           to the existing value, then the value of this
           parameter MUST NOT be altered and a VALUE CHANGE event
           MUST NOT be generated.";
      }
      leaf HTTPCompressionSupported {
        type enumeration {
          enum "GZIP";
          enum "Compress";
          enum "Deflate";
        }
        config false;
        description
          "Indicates the HTTP Compression mechanism(s) supported by
           this CPE.  Requirements for the use of HTTP
           Compression for CWMP can be found in
           {{bibref|TR-069a5|Section 3.4.7}}.  {{enum}}
        
           Vendors can extend the enumerated values with vendor
           specific extensions, in which case the rules outlined
           in {{bibref|TR-106a7|Section 3.3}} MUST be adhered to.";
      }
      leaf HTTPCompression {
        type string;
        default "Disabled";
        description
          "The value of this parameter represents the HTTP
           Compression mechanism to be used by the CPE when
           communicating with the ACS.";
      }
      leaf LightweightNotificationProtocolsSupported {
        type enumeration {
          enum "UDP";
        }
        config false;
        description
          "Indicates the Lightweight Notification Protocol(s)
           supported by this CPE.  {{enum}}
        
           Vendors can extend the enumerated values with vendor
           specific extensions, in which case the rules outlined
           in {{bibref|TR-106a7|Section 3.3}} MUST be adhered to.";
      }
      leaf LightweightNotificationProtocolsUsed {
        type string;
        description
          "The value of this parameter represents the protocol(s)
           that will be used by the CPE when sending Lightweight
           Notifications.
        
           {{empty}} means that Lightweight Notifications are
           disabled, despite any SetParameterAttributes that have
           been configured on various parameters.";
      }
      leaf UDPLightweightNotificationHost {
        type string {
          length "0..256";
        }
        description
          "Host name or address to be used when sending the UDP
           Lightweight Notifications.
        
           {{param}} is only applicable when
           {{param|LightweightNotificationProtocolsUsed}}
           contains the
           {{enum|UDP|LightweightNotificationProtocolsUsed}}
           enumeration.
        
           If {{param}} is not implemented or is {{empty}}, and
           UDP Lightweight Notifications are supported, the
           destination host MUST be the same as the ACS (as
           contained in the host portion of the {{param|URL}}).";
      }
      leaf UDPLightweightNotificationPort {
        type uint32;
        description
          "The port number to be used when sending UDP Lightweight
           Notifications.
        
           {{param}} is only applicable when
           {{param|LightweightNotificationProtocolsUsed}}
           contains the
           {{enum|UDP|LightweightNotificationProtocolsUsed}}
           enumeration.
        
           If {{param}} is not implemented and UDP Lightweight
           Notifications are supported, the destination port MUST
           be 7547.";
      }

      list ManageableDevice {
        key "ManufacturerOUI SerialNumber ProductClass";
        config false;
        description
          "Each entry in this table corresponds to a distinct LAN
           Device that supports Device-Gateway Association
           according to {{bibref|TR-069a2|Annex F}} as indicated
           by the presence of the DHCP option specified in that
           Annex.";
        leaf ManufacturerOUI {
          type string {
            length "6";
            pattern "[0-9A-F]{6}";
          }
          description
            "Organizationally unique identifier of the Device
             manufacturer as provided to the Gateway by the
             Device.  Represented as a six hexadecimal-digit
             value using all upper-case letters and including any
             leading zeros.  {{pattern}}
          
             The value MUST be a valid OUI as defined in
             {{bibref|OUI}}.";
        }
        leaf SerialNumber {
          type string {
            length "0..64";
          }
          description
            "Serial number of the Device as provided to the Gateway
             by the Device.";
        }
        leaf ProductClass {
          type string {
            length "0..64";
          }
          description
            "Identifier of the class of product for which the
             Device's serial number applies as provided to the
             Gateway by the Device.
          
             If the Device does not provide a Product Class, then
             this parameter MUST be {{empty}}.";
        }
        leaf Host {
          type string;
          description
            "{{list}} {{reference}} References all the
             {{object|.Hosts.Host}} table entries, whether active
             or inactive, that correspond to this physical LAN
             device.  There can be multiple such entries if the
             device has more than one network interface.
          
             For example:
             ''Device.Hosts.Host.1,Device.Hosts.Host.5''";
        }
      }

      container AutonomousTransferCompletePolicy {
        description
          "This object allows configuration of CPE policy for
           notification of AUTONOMOUS TRANSFER COMPLETE events,
           defined in {{bibref|TR-069a2}}.
        
           The CPE policy determines the conditions under which
           the CPE notifies the ACS of the completion of file
           transfers that were not specifically requested by the
           ACS.";
        leaf Enable {
          type boolean;
          description
            "Enable/disable CPE notification of AUTONOMOUS TRANSFER
             COMPLETE events to the ACS.";
        }
        leaf TransferTypeFilter {
          type enumeration {
            enum "Upload";
            enum "Download";
            enum "Both";
          }
          description
            "Indicates the transfer types that MUST be included when
             the CPE notifies the ACS of AUTONOMOUS TRANSFER
             COMPLETE events.  Transfer types not indicated by
             this filter MUST NOT be included when the CPE
             notifies the ACS.  {{enum}}
          
             Note that this includes any backup or restore
             operations that were not specifically requested by
             the ACS.  A backup is regarded as an Upload and a
             restore is regarded as a Download.";
        }
        leaf ResultTypeFilter {
          type enumeration {
            enum "Success";
            enum "Failure";
            enum "Both";
          }
          description
            "Indicates the transfer results that MUST be included
             when the CPE notifies the ACS of AUTONOMOUS TRANSFER
             COMPLETE events.  Transfer results omitted from this
             list MUST NOT be included when the CPE notifies the
             ACS.
          
             Note that this includes any backup or restore
             operations that were not specifically requested by
             the ACS.  A backup is regarded as an Upload and a
             restore is regarded as a Download.";
        }
        leaf FileTypeFilter {
          type string {
            pattern "1 Firmware Upgrade Image";
            pattern "2 Web Content";
            pattern "3 Vendor Configuration File";
            pattern "4 Vendor Log File";
            pattern "X [0-9A-F]{6} .*";
          }
          description
            "{{list}} Indicates the file types that MUST be included
             when the CPE notifies the ACS of AUTONOMOUS TRANSFER
             COMPLETE events.  File types omitted from this list
             MUST NOT be included when the CPE notifies the ACS.
          
             {{pattern}}
          
             Additionally, the following format is defined to
             allow the unique definition of vendor-specific file
             types:
          
             * ''\"X <OUI> <Vendor-specific identifier>\"''
          
             <OUI> is replaced by a 6 hexadecimal-digit OUI
             (organizationally unique identifier) as defined in
             {{bibref|OUI}}, with all upper-case letters and any
             leading zeros included.  The OUI used for a given
             vendor-specific file type MUST be one that is
             assigned to the organization that defined this file
             type (which is not necessarily the same as the
             vendor of the CPE or ACS).
          
             Note that {{empty}} indicates that all file types
             are excluded from this filter, effectively disabling
             CPE notification of AUTONOMOUS TRANSFER COMPLETE
             events to the ACS.";
        }
      }

      container DownloadAvailability {
        description
          "This object contains multicast announcement and query
           parameters used for the purpose of downloading files.";

        container Announcement {
          description
            "This object contains multicast announcement parameters
             used to download files.";
          leaf Enable {
            type boolean;
            description
              "Enable/disable CPE ability to receive and use
               multicast announcements from a server for the
               purpose of downloading files.";
          }
          leaf Status {
            type enumeration {
              enum "Disabled";
              enum "Enabled";
              enum "Error";
            }
            config false;
            description
              "The status of the announcement service.";
          }

          list Group {
            key "URL";
            description
              "Multicast groups to which the CPE SHOULD listen for
               announcements.";
            leaf Enable {
              type boolean;
              default "false";
              description
                "Enable/disable listening to this multicast group.";
            }
            leaf Status {
              type enumeration {
                enum "Disabled";
                enum "Enabled";
                enum "Error";
              }
              config false;
              default "Disabled";
              description
                "The status of this group table entry.";
            }
            leaf URL {
              type string {
                length "0..256";
              }
              default "";
              description
                "URL {{bibref|RFC3986}} encoding the group address,
                 source and port on which to listen, and other
                 protocol information, e.g.  expected
                 announcement format.
              
                 Depending on the application, the messages
                 identified by this URL MAY directly contain the
                 data to be downloaded, or alternatively MAY
                 contain information informing the CPE how to
                 obtain the data to be downloaded via a separate
                 mechanism, which itself could involve a unicast
                 or a multicast download protocol.
              
                 Refer to {{bibref|DVB-TS.102.824}} for an
                 example of a URL format that identifies a SAP
                 {{bibref|RFC2974}} stream that indicates how to
                 use either FLUTE {{bibref|RFC3926}} or DSM-CC
                 {{bibref|ISO-13818-6:1998}} to perform the
                 download.";
            }
          }
        }

        container Query {
          description
            "This object contains multicast query parameters used to
             download files.";
          leaf Enable {
            type boolean;
            description
              "Enable/disable CPE ability to autonomously query a
               server for the purpose of downloading files.";
          }
          leaf Status {
            type enumeration {
              enum "Disabled";
              enum "Enabled";
              enum "Error";
            }
            config false;
            description
              "The status of the query service.";
          }
          leaf URL {
            type string {
              length "0..256";
            }
            description
              "URL {{bibref|RFC3986}} of the query response server.
            
               Depending on the application, the protocol
               described by this URL MAY be a SOAP interface, or
               MAY be any other RPC mechanism.
            
               Refer to {{bibref|DVB-TS.102.824}} for an example
               of a URL format that identifies a SOAP interface
               running over HTTP or HTTPS.";
          }
        }
      }

      container DUStateChangeComplPolicy {
        description
          "This object allows configuration of CPE policy for
           notification of \"12 AUTONOMOUS DU STATE CHANGE
           COMPLETE\" events defined in {{bibref|TR-069a3}}.
        
           The CPE policy determines the conditions under which
           the CPE notifies the ACS of the completion of
           Deployment Unit state changes that were not
           specifically requested via CWMP.";
        leaf Enable {
          type boolean;
          description
            "Enables/Disables CPE notification of \"12 AUTONOMOUS DU
             STATE CHANGE COMPLETE\" events to the ACS.";
        }
        leaf OperationTypeFilter {
          type enumeration {
            enum "Install";
            enum "Update";
            enum "Uninstall";
          }
          description
            "Indicates the Deployment Unit operations that MUST be
             included when the CPE notifies the ACS of \"12
             AUTONOMOUS DU STATE CHANGE COMPLETE\" events.
          
             Operation types not indicated by this list MUST NOT
             be included when the CPE notifies the ACS.
             {{empty}} is essentially the same as setting
             {{param|Enable}} to {{false}}.";
        }
        leaf ResultTypeFilter {
          type enumeration {
            enum "Success";
            enum "Failure";
            enum "Both";
          }
          description
            "Indicates the Deployment Unit state change results that
             MUST be included when the CPE notifies the ACS of
             \"12 AUTONOMOUS DU STATE CHANGE COMPLETE\" events.
             State change results omitted from this filter MUST
             NOT be included when the CPE notifies the ACS.";
        }
        leaf FaultCodeFilter {
          type enumeration {
            enum "9001";
            enum "9003";
            enum "9012";
            enum "9013";
            enum "9015";
            enum "9016";
            enum "9017";
            enum "9018";
            enum "9022";
            enum "9023";
            enum "9024";
            enum "9025";
            enum "9026";
            enum "9027";
            enum "9028";
            enum "9029";
            enum "9030";
            enum "9031";
            enum "9032";
          }
          description
            "Indicates the Deployment Unit state change fault codes
             that MUST be included when the CPE notifies the ACS
             of \"12 AUTONOMOUS DU STATE CHANGE COMPLETE\"
             events.  State change fault codes omitted from this
             filter MUST NOT be included when the CPE notifies
             the ACS.
          
             This filter has no effect on the notification of a
             successful autonomous state change.  This filter
             only applies when {{param|ResultTypeFilter}} is set
             to either {{enum|Failure|ResultTypeFilter}} or
             {{enum|Both|ResultTypeFilter}}.  {{empty}} means
             that failed autonomous state changes will not be
             sent to the ACS.";
        }
      }

      list EmbeddedDevice {
        key "ControllerID ProxiedDeviceID";
        config false;
        description
          "Each entry in this table represents a distinct Proxied
           Device that utilizes the Embedded Object Mechanism
           {{bibref|TR-069a4|Annex J.1.2}} for proxying devices.";
        leaf ControllerID {
          type string {
            length "0..256";
          }
          description
            "Identifier of the controller that is responsible for a
             sub-network of Proxied Devices within the LAN.
          
             {{empty}} indicates that this Proxied Device either:
          
             * Isn't part of a sub-network, within the LAN, with
             a controller entity.
          
             * Doesn't need a {{param}} to ensure its
             {{param|ProxiedDeviceID}} is unique throughout the
             LAN.";
        }
        leaf ProxiedDeviceID {
          type string {
            length "0..256";
          }
          description
            "Idenitfier of the Proxied Device.
          
             This is an opaque string that is unique to the
             Proxied Device within a specific sub-network within
             the LAN (identified by the {{param|ControllerID}}).
             If the {{param|ControllerID}} is {{empty}} this
             {{param}} is unique across the LAN.";
        }
        leaf Reference {
          type string;
          description
            "{{noreference}}The value MUST be the path name of a
             table row.  If the referenced object is deleted,
             this {{object}} instance MUST also be removed.
             Represents the instance of a multi-instanced object
             that is directly controlled by, and has come into
             existence because of, this Proxied Device that
             utilizes the Embedded Object Mechanism
             {{bibref|TR-069a4|Annex J.1.2}}.";
        }
        leaf SupportedDataModel {
          type string;
          description
            "Represents the CWMP-DT schema instance(s) that this
             Proxied Device is utilizing.  The CWMP-DT schema
             instance is also the one being utilized by the
             object referenced within {{param|Reference}}.";
        }
        leaf Host {
          type string;
          description
            "References the {{object|.Hosts.Host}} table entry(s),
             whether active or inactive, that corresponds to this
             proxied LAN device.";
        }
        leaf ProxyProtocol {
          type enumeration {
            enum "Z-Wave";
            enum "ZigBee";
            enum "UPnP-DM";
            enum "ETSI-M2M";
          }
          description
            "The protocol being used to communicate between the CPE
             Proxier and this Proxied Device.  {{enum}}
          
             Vendors can extend the enumerated values with vendor
             specific extensions, in which case the rules
             outlined in {{bibref|TR-106a6|3.3}} MUST be adhered
             to.";
        }
        leaf ProxyProtocolReference {
          type string;
          description
            "{{reference|a protocol object that uses the
             {{param|ProxyProtocol}}}}";
        }
        leaf DiscoveryProtocol {
          type enumeration {
            enum "Z-Wave";
            enum "ZigBee";
            enum "UPnP";
            enum "ETSI-M2M";
          }
          description
            "{{list|that represents the discovery protocol(s) for
             this proxied device}}
          
             {{enum}}
          
             Vendors can extend the enumerated values with vendor
             specific extensions, in which case the rules
             outlined in {{bibref|TR-106a3|Section 3.3}} MUST be
             adhered to.";
        }
        leaf DiscoveryProtocolReference {
          type string;
          description
            "{{list}} {{reference|an object discovered using one or
             more protocols listed in
             {{param|DiscoveryProtocol}}|ignore}}
          
             For objects discovered by the UPnP discovery
             protocol, the {{param}} would contain items that are
             references to instances of the following:
          
             * {{object|.UPnP.Discovery.RootDevice}}
          
             * {{object|.UPnP.Discovery.Device}}
          
             * {{object|.UPnP.Discovery.Service}}
          
             For objects discovered by the ETSI-M2M discovery
             protocol, the {{param}} would contain items that are
             references to instances of
             ETSIM2M.SCL.{i}.AreaNwkDeviceInfoInstance.";
        }
        leaf CommandProcessed {
          type enumeration {
            enum "Pending";
            enum "Retrying";
            enum "Success";
            enum "Error";
          }
          description
            "Whether or not the CPE Proxier has successfully
             communicated all pending configuration commands down
             to the Proxied Device.";
        }
        leaf CommandProcessingErrMsg {
          type string {
            length "0..1024";
          }
          description
            "Detailed {{param|CommandProcessed}} error description
             (vendor specific).";
        }
        leaf LastSyncTime {
          type yang:date-and-time;
          description
            "The last time that the CPE Proxier synchronized the
             state of the Proxied Device.  This parameter MUST be
             updated when a proxy command is executed
             successfully on the Proxied Device.
          
             The Unknown Time value, as defined in
             {{bibref|TR-106a6}}, indicates that the Proxied
             Device's state has not been synchronized since the
             CPE Proxier was last rebooted.";
        }
      }

      list VirtualDevice {
        key "ManufacturerOUI ProductClass SerialNumber";
        config false;
        description
          "Each entry in this table represents a distinct Proxied
           Device that utilizes the Virtual CWMP Device Mechanism
           {{bibref|TR-069a4|Annex I.1.1}} for proxying devices.";
        leaf ManufacturerOUI {
          type string {
            length "6";
            pattern "[0-9A-F]{6}";
          }
          description
            "Organizationally unique identifier of the associated
             Proxied Device.  Represented as a six
             hexadecimal-digit value using all upper-case letters
             and including any leading zeros.  {{pattern}}
          
             The value MUST be a valid OUI as defined in
             {{bibref|OUI}}.";
        }
        leaf ProductClass {
          type string {
            length "0..64";
          }
          description
            "Identifier of the class of product of the associated
             Proxied Device for which the serial number applies.";
        }
        leaf SerialNumber {
          type string {
            length "0..64";
          }
          description
            "Serial number of the associated Proxied Device.";
        }
        leaf Host {
          type string;
          description
            "{{list}} {{reference}} References all the
             {{object|.Hosts.Host}} table entries, whether active
             or inactive, that correspond to this proxied LAN
             device.  There can be multiple such entries if the
             Proxied Device has more than one network interface.";
        }
        leaf ProxyProtocol {
          type enumeration {
            enum "Z-Wave";
            enum "ZigBee";
            enum "UPnP-DM";
            enum "ETSI-M2M";
          }
          description
            "The protocol being used to communicate between the CPE
             Proxier and this Proxied Device.  {{enum}}
          
             Vendors can extend the enumerated values with vendor
             specific extensions, in which case the rules
             outlined in {{bibref|TR-106a6|3.3}} MUST be adhered
             to.";
        }
        leaf ProxyProtocolReference {
          type string;
          description
            "{{reference|a protocol object that uses the
             {{param|ProxyProtocol}}}}";
        }
        leaf DiscoveryProtocol {
          type enumeration {
            enum "Z-Wave";
            enum "ZigBee";
            enum "UPnP";
            enum "ETSI-M2M";
          }
          description
            "{{list|that represents the discovery protocol(s) for
             this proxied device}}
          
             {{enum}}
          
             Vendors can extend the enumerated values with vendor
             specific extensions, in which case the rules
             outlined in {{bibref|TR-106a3|Section 3.3}} MUST be
             adhered to.";
        }
        leaf DiscoveryProtocolReference {
          type string;
          description
            "{{list}} {{reference|an object discovered using one or
             more protocols listed in
             {{param|DiscoveryProtocol}}|ignore}}
          
             For objects discovered by the UPnP discovery
             protocol, the {{param}} would contain items that are
             references to instances of the following:
          
             * {{object|.UPnP.Discovery.RootDevice}}
          
             * {{object|.UPnP.Discovery.Device}}
          
             * {{object|.UPnP.Discovery.Service}}
          
             For objects discovered by the ETSI-M2M discovery
             protocol, the {{param}} would contain items that are
             references to instances of
             ETSIM2M.SCL.{i}.AreaNwkDeviceInfoInstance.";
        }
      }

      container StandbyPolicy {
        description
          "Parameters related to CPE behavior when waking up from
           standby.  If this object is supported then the CPE
           MUST support the requirements of
           {{bibref|TR-069a5|Annex L}}.
        
           NOTE: \"CR\", as used in the names and descriptions of
           the parameters defined in this object, refers to the
           Connection Request concept defined in TR-069.";
        leaf CRUnawarenessMaxDuration {
          type int32 {
            range "-1..max";
          }
          default "-1";
          description
            "When waking up from a non CR-Aware Standby that lasted
             more than this parameter's value (in {{units}}), the
             CPE MUST issue a WAKEUP Event.
          
             If the value is -1, the CPE MUST NOT ever issue
             WAKEUP Events for having been non CR-aware.";
        }
        leaf MaxMissedPeriodic {
          type int32 {
            range "-1..max";
          }
          default "-1";
          description
            "When waking up from a non fully Timer-Aware Standby
             that made it miss more than this parameter's value
             Periodic Contacts, the CPE MUST issue a WAKEUP
             Event.
          
             If the value is -1, the CPE MUST NOT ever issue
             WAKEUP Events for exceeding that limit.";
        }
        leaf NotifyMissedScheduled {
          type boolean;
          default "false";
          description
            "When waking up from a non fully Timer-Aware Standby
             that made it miss at least one Scheduled Contact,
             the CPE MUST issue a WAKEUP Event if this parameter
             is {{true}}.";
        }
        leaf NetworkAwarenessCapable {
          type boolean;
          config false;
          description
            "Indicates that the CPE is capable of CR-Aware Standby.";
        }
        leaf SelfTimerCapable {
          type boolean;
          config false;
          description
            "Indicates that the CPE is capable of Timer-Aware
             Standby.";
        }
        leaf CRAwarenessRequested {
          type boolean;
          default "false";
          description
            "If {{param|NetworkAwarenessCapable}} and this parameter
             are both {{true}}, the CPE MUST NOT go into a non
             CR-Aware Standby state.";
        }
        leaf PeriodicAwarenessRequested {
          type boolean;
          default "false";
          description
            "If {{param|SelfTimerCapable}} and this parameter are
             both {{true}}, the CPE MUST NOT go into a standby
             state that prevents it from honoring Periodic
             Contacts.";
        }
        leaf ScheduledAwarenessRequested {
          type boolean;
          description
            "If this parameter is true, the CPE MUST NOT go into a
             standby state that prevents it from honoring
             Scheduled Contacts.  This means that, whenever the
             ACS has requested a Scheduled Contact:
          
             *if {{param|SelfTimerCapable}} is {{true}} and the
             CPE chooses to go into Standby before the Scheduled
             Contact has been honored, it MUST use a Timer-Aware
             Standby;
          
             *if {{param|SelfTimerCapable}} is {{false}}, the CPE
             MUST NOT go into Standby before the Scheduled
             Contact has been honored.";
        }
      }

      list InformParameter {
        key "ParameterName";
        description
          "This table provides the ACS with the ability to control
           the Parameters that are delivered by the Inform RPC.
        
           Any Parameter (identified by {{param|ParameterName}})
           contained in this table MUST be included within the
           ParameterList argument of the Inform RPC whenever any
           Event within the {{param|EventList}} is being
           delivered.
        
           This table does not include Forced Inform Parameters,
           and Forced Inform Parameters are not allowed to be
           inserted into this table.  Any attempt by an ACS to
           configure this table to contain a Forced Inform
           Parameter MUST result in the failure of the
           SetParameterValues RPC with error code 9007.";
        leaf Enable {
          type boolean;
          default "false";
          description
            "Enables or disables this {{object}}.";
        }
        leaf ParameterName {
          type string {
            length "0..256";
          }
          default "";
          description
            "A pattern that describes the Parameter(s) to be
             included in the Inform’s ParameterList argument.
             Specifically, patterns with wildcards (an \"*\"
             character) in place of Instance Identifiers are
             allowed; any attempt to set the value otherwise MUST
             be rejected by the CPE.
          
             If the pattern does not match any existing
             Parameters at the time that the CPE is creating the
             Inform RPC, then this {{object|#.InformParameter}}
             instance is not included in the Inform’s
             ParameterList argument.";
        }
        leaf EventList {
          type string;
          default "";
          description
            "Each entry in this list represents an Event for which
             this Parameter MUST be included within the
             ParameterList argument of the Inform RPC.
          
             All Inform Events (see {{bibref|TR-069|Section
             3.7.1.5}}), except for \"4 VALUE CHANGE\", are
             allowed as entries in this list.  \"4 VALUE CHANGE\"
             is not allowed as that would violate requirements
             contained in {{bibref|TR-069|Section A.3.3.1}}.
          
             {{empty}} means all events except \"4 VALUE
             CHANGE\".";
        }
      }
    }

    container GatewayInfo {
      config false;
      description
        "This object contains information associated with a
         connected Internet Gateway Device.";
      leaf ManufacturerOUI {
        type string {
          length "0..6";
          pattern "";
          pattern "[0-9A-F]{6}";
        }
        description
          "Organizationally unique identifier of the associated
           Internet Gateway Device.  {{pattern}}
        
           {{empty}} indicates that there is no associated
           Internet Gateway Device that has been detected.";
      }
      leaf ProductClass {
        type string {
          length "0..64";
        }
        description
          "Identifier of the product class of the associated
           Internet Gateway Device.  {{empty}} indicates either
           that there is no associated Internet Gateway Device
           that has been detected, or the Internet Gateway Device
           does not support the use of the product-class
           parameter.";
      }
      leaf SerialNumber {
        type string {
          length "0..64";
        }
        description
          "Serial number of the associated Internet Gateway Device.
           {{empty}} indicates that there is no associated
           Internet Gateway Device that has been detected.";
      }
    }

    container Time {
      description
        "This object contains parameters relating an NTP or SNTP
         time client in the CPE.";
      leaf Enable {
        type boolean;
        description
          "Enables or disables the NTP or SNTP time client.";
      }
      leaf Status {
        type enumeration {
          enum "Disabled";
          enum "Unsynchronized";
          enum "Synchronized";
          enum "Error_FailedToSynchronize";
          enum "Error";
        }
        config false;
        description
          "Status of Time support on the CPE.  {{enum}}
        
           The {{enum|Unsynchronized}} value indicates that the
           CPE's absolute time has not yet been set.
        
           The {{enum|Synchronized}} value indicates that the CPE
           has acquired accurate absolute time; its current time
           is accurate.
        
           The {{enum|Error_FailedToSynchronize}} value indicates
           that the CPE failed to acquire accurate absolute time;
           its current time is not accurate.
        
           The {{enum|Error}} value MAY be used by the CPE to
           indicate a locally defined error condition.";
      }
      leaf NTPServer1 {
        type string {
          length "0..64";
        }
        description
          "First NTP timeserver.  Either a host name or IP address.";
      }
      leaf NTPServer2 {
        type string {
          length "0..64";
        }
        description
          "Second NTP timeserver.  Either a host name or IP address.";
      }
      leaf NTPServer3 {
        type string {
          length "0..64";
        }
        description
          "Third NTP timeserver.  Either a host name or IP address.";
      }
      leaf NTPServer4 {
        type string {
          length "0..64";
        }
        description
          "Fourth NTP timeserver.  Either a host name or IP address.";
      }
      leaf NTPServer5 {
        type string {
          length "0..64";
        }
        description
          "Fifth NTP timeserver.  Either a host name or IP address.";
      }
      leaf CurrentLocalTime {
        type yang:date-and-time;
        config false;
        description
          "The current date and time in the CPE's local time zone.";
      }
      leaf LocalTimeZone {
        type string {
          length "0..256";
        }
        description
          "The local time zone definition, encoded according to IEEE
           1003.1 (POSIX).  The following is an example value:
        
           : EST+5 EDT,M4.1.0/2,M10.5.0/2";
      }
    }

    container UserInterface {
      description
        "This object contains parameters relating to the user
         interface of the CPE.";
      leaf PasswordRequired {
        type boolean;
        description
          "Present only if the CPE provides a password-protected
           LAN-side user interface.
        
           Indicates whether or not the local user interface MUST
           require a password to be chosen by the user.  If
           {{false}}, the choice of whether or not a password is
           used is left to the user.";
      }
      leaf PasswordUserSelectable {
        type boolean;
        description
          "Present only if the CPE provides a password-protected
           LAN-side user interface and supports LAN-side
           Auto-Configuration.
        
           Indicates whether or not a password to protect the
           local user interface of the CPE MAY be selected by the
           user directly (i.e.
           {{param|.Users.User.{i}.Password}}), or MUST be equal
           to the password used by the LAN-side
           Auto-Configuration protocol (i.e.
           {{param|.LANConfigSecurity.ConfigPassword}}).";
      }
      leaf PasswordReset {
        type boolean; /* command */
        description
          "Present only if the CPE provides a password-protected
           LAN-side user interface and supports LAN-side
           Auto-Configuration.
        
           When set to true, resets
           {{param|.LANConfigSecurity.ConfigPassword}} to its
           factory value.";
      }
      leaf UpgradeAvailable {
        type boolean;
        description
          "Indicates that a CPE upgrade is available, allowing the
           CPE to display this information to the user.";
      }
      leaf WarrantyDate {
        type yang:date-and-time;
        description
          "Indicates the date and time in UTC that the warranty
           associated with the CPE is to expire.";
      }
      leaf ISPName {
        type string {
          length "0..64";
        }
        description
          "The name of the customer's ISP.";
      }
      leaf ISPHelpDesk {
        type string {
          length "0..32";
        }
        description
          "The help desk phone number of the ISP.";
      }
      leaf ISPHomePage {
        type string {
          length "0..256";
        }
        description
          "The URL of the ISP's home page.";
      }
      leaf ISPHelpPage {
        type string {
          length "0..256";
        }
        description
          "The URL of the ISP's on-line support page.";
      }
      leaf ISPLogo {
        type binary {
          length "0..4095";
        }
        description
          "Base64 encoded GIF or JPEG image.  The binary image is
           constrained to 4095 bytes or less.";
      }
      leaf ISPLogoSize {
        type uint32 {
          range "0..4095";
        }
        description
          "Un-encoded binary image size in bytes.
        
           If ISPLogoSize input value is 0 then the ISPLogo is
           cleared.
        
           ISPLogoSize can also be used as a check to verify
           correct transfer and conversion of Base64 string to
           image size.";
      }
      leaf ISPMailServer {
        type string {
          length "0..256";
        }
        description
          "The URL of the ISP's mail server.";
      }
      leaf ISPNewsServer {
        type string {
          length "0..256";
        }
        description
          "The URL of the ISP's news server.";
      }
      leaf TextColor {
        type yang:hex-string {
          length "3";
        }
        description
          "The color of text on the GUI screens in RGB hexadecimal
           notation (e.g., FF0088).";
      }
      leaf BackgroundColor {
        type yang:hex-string {
          length "3";
        }
        description
          "The color of the GUI screen backgrounds in RGB
           hexadecimal notation (e.g., FF0088).";
      }
      leaf ButtonColor {
        type yang:hex-string {
          length "3";
        }
        description
          "The color of buttons on the GUI screens in RGB
           hexadecimal notation (e.g., FF0088).";
      }
      leaf ButtonTextColor {
        type yang:hex-string {
          length "3";
        }
        description
          "The color of text on buttons on the GUI screens in RGB
           hexadecimal notation (e.g., FF0088).";
      }
      leaf AutoUpdateServer {
        type string {
          length "0..256";
        }
        description
          "The server the CPE can check to see if an update is
           available for direct download to it.  This MUST NOT be
           used by the CPE if the
           {{param|.ManagementServer.UpgradesManaged}} parameter
           is {{true}}.";
      }
      leaf UserUpdateServer {
        type string {
          length "0..256";
        }
        description
          "The server where a user can check via a web browser if an
           update is available for download to a PC.  This MUST
           NOT be used by the CPE if the
           {{param|.ManagementServer.UpgradesManaged}} parameter
           is {{true}}.";
      }
      leaf AvailableLanguages {
        type string;
        config false;
        description
          "{{list}} List items represent user-interface languages
           that are available, where each language is specified
           according to {{bibref|RFC3066}}.";
      }
      leaf CurrentLanguage {
        type string {
          length "0..16";
        }
        description
          "Current user-interface language, specified according to
           {{bibref|RFC3066}}.  The value MUST be a member of the
           list reported by the {{param|AvailableLanguages}}
           parameter.";
      }

      container RemoteAccess {
        description
          "This object contains parameters relating to remotely
           accessing the CPE's user interface.
        
           Remote access is defined as any entity not of a local
           subnet attempting to connect to the CPE.
        
           Remote access requires user authentication.  To
           provide remote access authentication the CPE MUST
           support a \"User\" table with at least one instance
           that has \"RemoteAccessCapable\" set to {{true}}.";
        leaf Enable {
          type boolean;
          description
            "Enables/Disables remotely accessing the CPE's user
             interface.";
        }
        leaf Port {
          type uint32 {
            range "min..65535";
          }
          description
            "Destination TCP port required for remote access
             connection.";
        }
        leaf SupportedProtocols {
          type enumeration {
            enum "HTTP";
            enum "HTTPS";
          }
          config false;
          description
            "{{list}} Indicates the protocols that are supported by
             the CPE for the purpose of remotely accessing the
             user interface.";
        }
        leaf Protocol {
          type string;
          description
            "This is the protocol currently being used for remote
             access.";
        }
      }

      container LocalDisplay {
        description
          "This object describes how to remotely manage the initial
           positioning of a user interface on a device's local
           display.";
        leaf Movable {
          type boolean;
          description
            "Controls whether the user is allowed to change the GUI
             window position on the local CPE's display.";
        }
        leaf Resizable {
          type boolean;
          description
            "Controls whether the user is allowed to resize the GUI
             window on the local CPE's display.";
        }
        leaf PosX {
          type int32;
          description
            "The horizontal position of the User Interface's top
             left corner within the local CPE's display measured
             from the top left corner, expressed in {{units}}.";
        }
        leaf PosY {
          type int32;
          description
            "The vertical position of the User Interface's top left
             corner within the local CPE's display measured from
             the top left corner, expressed in {{units}}.";
        }
        leaf Width {
          type uint32;
          description
            "The width of the user interface within the local CPE's
             display, expressed in {{units}}.";
        }
        leaf Height {
          type uint32;
          description
            "The height of the user interface within the local CPE's
             display, expressed in {{units}}.";
        }
        leaf DisplayWidth {
          type uint32;
          config false;
          description
            "The width of the local CPE's display, expressed in
             {{units}}.";
        }
        leaf DisplayHeight {
          type uint32;
          config false;
          description
            "The height of the local CPE's display, expressed in
             {{units}}.";
        }
      }
    }

    list InterfaceStack {
      key "HigherLayer LowerLayer";
      config false;
      description
        "This table contains information about the relationships
         between the multiple layers of interface objects
         ({{bibref|TR-181i2|Section 4.3}}).  In particular, it
         contains information on which interfaces run ''on top
         of'' which other interfaces.
      
         This table is auto-generated by the CPE based on the
         ''LowerLayers'' parameters on individual interface
         objects.
      
         Each table row represents a \"link\" between two
         interface objects, a higher-layer interface object
         (referenced by {{param|HigherLayer}}) and a lower-layer
         interface object (referenced by {{param|LowerLayer}}).
         Consequently, if a referenced interface object is
         deleted, the CPE MUST delete the corresponding
         {{object}} row(s) that had referenced it.";
      leaf HigherLayer {
        type string {
          length "0..256";
        }
        description
          "{{noreference}}A reference to the interface object
           corresponding to the higher layer of the relationship,
           i.e.  the interface which runs on ''top'' of the
           interface identified by the corresponding instance of
           {{param|LowerLayer}}.
        
           When the referenced higher layer interface is deleted,
           the CPE MUST delete the table row.";
      }
      leaf LowerLayer {
        type string {
          length "0..256";
        }
        description
          "{{noreference}}A reference to the interface object
           corresponding to the lower layer of the relationship,
           i.e.  the interface which runs ''below'' the interface
           identified by the corresponding instance of
           {{param|HigherLayer}}.
        
           When the referenced lower layer interface is deleted,
           the CPE MUST delete the table row.";
      }
      leaf HigherAlias {
        type string {
          length "0..64";
        }
        description
          "The value of the ''Alias'' parameter for the interface
           object referenced by {{param|HigherLayer}}.";
      }
      leaf LowerAlias {
        type string {
          length "0..64";
        }
        description
          "The value of the ''Alias'' parameter for the interface
           object referenced by {{param|LowerLayer}}.";
      }
    }

    container DSL {
      description
        "This object models DSL lines, DSL channels, DSL bonding,
         and DSL diagnostics.  The specific interface objects
         defined here are {{object|Line}}, {{object|Channel}},
         and {{object|BondingGroup}}.  Each {{object|Line}}
         models a layer 1 DSL Line interface, and each
         {{object|Channel}} models a layer 1 DSL Channel
         interface where multiple channels can run over a DSL
         line.  In the case where bonding is configured, it is
         expected that {{object|BondingGroup}} is stacked above
         the {{object|Channel}} instances within its group.";

      list Line {
        key "Alias";
        description
          "DSL Line table (a stackable interface object as described
           in {{bibref|TR-181i2|Section 4.2}}).
        
           This table models physical DSL lines.";
        leaf Enable {
          type boolean;
          description
            "Enables or disables the DSL line.
          
             This parameter is based on ''ifAdminStatus'' from
             {{bibref|RFC2863}}.";
        }
        leaf EnableDataGathering {
          type boolean;
          description
            "Enables or disables data gathering on the DSL line.";
        }
        leaf Status {
          type enumeration {
            enum "Up";
            enum "Down";
            enum "Unknown";
            enum "Dormant";
            enum "NotPresent";
            enum "LowerLayerDown";
            enum "Error";
          }
          config false;
          description
            "The current operational state of the DSL line (see
             {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the DSL line as assigned by the
             CPE.";
        }
        leaf LastChange {
          type uint32;
          config false;
          description
            "The accumulated time in {{units}} since the DSL line
             entered its current operational state.";
        }
        leaf LowerLayers {
          type string;
          description
            "{{list}} {{reference|an interface object that is
             stacked immediately below this interface object}}
             See {{bibref|TR-181i2|Section 4.2.1}}.
          
             Note: Since {{object}} is a layer 1 interface, it is
             expected that {{param}} will not be used.";
        }
        leaf Upstream {
          type boolean;
          config false;
          description
            "Indicates whether the interface points towards the
             Internet ({{true}}) or towards End Devices
             ({{false}}).
          
             For example:
          
             * For an Internet Gateway Device, {{param}} will be
             {{true}} for all WAN interfaces and {{false}} for
             all LAN interfaces.
          
             * For a standalone WiFi Access Point that is
             connected via Ethernet to an Internet Gateway
             Device, {{param}} will be {{true}} for the Ethernet
             interface and {{false}} for the WiFi Radio
             interface.
          
             * For an End Device, {{param}} will be {{true}} for
             all interfaces.";
        }
        leaf FirmwareVersion {
          type string {
            length "0..64";
          }
          config false;
          description
            "A string identifying the version of the modem firmware
             currently installed for this interface.  This is
             applicable only when the modem firmware is separable
             from the overall CPE software.";
        }
        leaf LinkStatus {
          type enumeration {
            enum "Up";
            enum "Initializing";
            enum "EstablishingLink";
            enum "NoSignal";
            enum "Disabled";
            enum "Error";
          }
          config false;
          description
            "Status of the DSL physical link.  {{enum}}
          
             When {{param}} is {{enum|Up}}, {{param|Status}} is
             expected to be {{enum|Up|Status}}.  When {{param}}
             is {{enum|Initializing}} or
             {{enum|EstablishingLink}} or {{enum|NoSignal}} or
             {{enum|Disabled}}, {{param|Status}} is expected to
             be {{enum|Down|Status}}.
          
             The {{enum|Error}} value MAY be used by the CPE to
             indicate a locally defined error condition.";
        }
        leaf StandardsSupported {
          status deprecated;
          type enumeration {
            enum "G.992.1_Annex_A";
            enum "G.992.1_Annex_B";
            enum "G.992.1_Annex_C";
            enum "T1.413";
            enum "T1.413i2";
            enum "ETSI_101_388";
            enum "G.992.2";
            enum "G.992.3_Annex_A";
            enum "G.992.3_Annex_B";
            enum "G.992.3_Annex_C";
            enum "G.992.3_Annex_I";
            enum "G.992.3_Annex_J";
            enum "G.992.3_Annex_L";
            enum "G.992.3_Annex_M";
            enum "G.992.4";
            enum "G.992.5_Annex_A";
            enum "G.992.5_Annex_B";
            enum "G.992.5_Annex_C";
            enum "G.992.5_Annex_I";
            enum "G.992.5_Annex_J";
            enum "G.992.5_Annex_M";
            enum "G.993.1";
            enum "G.993.1_Annex_A";
            enum "G.993.2_Annex_A";
            enum "G.993.2_Annex_B";
            enum "G.993.2_Annex_C";
          }
          config false;
          description
            "{{list}} List items indicate which DSL standards and
             recommendations are supported by the {{object}}
             instance.  {{enum}}
          
             Note: In G.997.1, this parameter is called \"xDSL
             Transmission system capabilities\".  See ITU-T
             Recommendation {{bibref|G.997.1}}.
          
             This parameter is DEPRECATED because its entries are
             out-of-date; {{param|XTSE}} points to a current
             list.  Therefore its value MAY be {{empty}} if (and
             only if) {{param|XTSE}} is supported.";
        }
        leaf XTSE {
          type yang:hex-string {
            length "8";
          }
          config false;
          description
            "This configuration parameter defines the transmission
             system types to be allowed by the xTU on this
             {{object}} instance.  Each bit is 0 if not allowed
             or 1 if allowed, as defined for the xTU transmission
             system enabling (XTSE) in ITU-T G.997.1.
          
             Note: This parameter is defined as xDSL Transmission
             system enabling (XTSE) in ITU-T G.997.1.  For a full
             definition, see Clause 7.3.1.1.1 of ITU-T
             Recommendation {{bibref|G.997.1}}.";
        }
        leaf StandardUsed {
          status deprecated;
          type string;
          config false;
          description
            "Indicates the standard that the {{object}} instance is
             using for the connection.
          
             Note: In G.997.1, this parameter is called \"xDSL
             Transmission system\".  See ITU-T Recommendation
             {{bibref|G.997.1}}.
          
             This parameter is DEPRECATED because its entries are
             out-of-date; {{param|XTSE}} points to a current
             list.  Therefore its value MAY be {{empty}} if (and
             only if) {{param|XTSUsed}} is supported.";
        }
        leaf XTSUsed {
          type yang:hex-string {
            length "8";
          }
          config false;
          description
            "This parameter indicates which DSL standard and
             recommendation are currently in use by the
             {{object}} instance.  Only one bit is set, as
             defined for the xTU transmission system enabling
             (XTSE) in ITU-T G.997.1.";
        }
        leaf LineEncoding {
          type enumeration {
            enum "DMT";
            enum "CAP";
            enum "2B1Q";
            enum "43BT";
            enum "PAM";
            enum "QAM";
          }
          config false;
          description
            "The line encoding method used in establishing the Layer
             1 DSL connection between the CPE and the DSLAM.
             {{enum}}
          
             Note: Generally speaking, this variable does not
             change after provisioning.";
        }
        leaf AllowedProfiles {
          type enumeration {
            enum "8a";
            enum "8b";
            enum "8c";
            enum "8d";
            enum "12a";
            enum "12b";
            enum "17a";
            enum "17b";
            enum "30a";
          }
          config false;
          description
            "{{list}} List items indicate which VDSL2 profiles are
             allowed on the line.  {{enum}}
          
             Note: In G.997.1, this parameter is called PROFILES.
             See ITU-T Recommendation {{bibref|G.997.1}}.
          
             Note: This parameter is OPTIONAL at the G and S/T
             interfaces in G.997.1 Amendment 1.  If the parameter
             is implemented but no value is available, its value
             MUST be {{empty}}.";
        }
        leaf CurrentProfile {
          type string;
          config false;
          description
            "Indicates which VDSL2 profile is currently in use on
             the line.
          
             Note: This parameter is OPTIONAL at the G and S/T
             interfaces in G.997.1 Amendment 1.  If the parameter
             is implemented but no value is available, its value
             MUST be {{empty}}.";
        }
        leaf PowerManagementState {
          type enumeration {
            enum "L0";
            enum "L1";
            enum "L2";
            enum "L3";
            enum "L4";
          }
          config false;
          description
            "The power management state of the line.  {{enum}}
          
             Note: See ITU-T Recommendation {{bibref|G.997.1}}.";
        }
        leaf SuccessFailureCause {
          type uint32 {
            range "0..6";
          }
          config false;
          description
            "The success failure cause of the initialization.  An
             enumeration of the following integer values:
          
             * 0: Successful
          
             * 1: Configuration error.  This error occurs with
             inconsistencies in configuration parameters, e.g.
             when the line is initialized in an xDSL Transmission
             system where an xTU does not support the configured
             Maximum Delay or the configured Minimum or Maximum
             Data Rate for one or more bearer channels.
          
             * 2: Configuration not feasible on the line.  This
             error occurs if the Minimum Data Rate cannot be
             reached on the line with the Minimum Noise Margin,
             Maximum PSD level, Maximum Delay and Maximum Bit
             Error Ratio for one or more bearer channels.
          
             * 3: Communication problem.  This error occurs, for
             example, due to corrupted messages or bad syntax
             messages or if no common mode can be selected in the
             G.994.1 handshaking procedure or due to a timeout.
          
             * 4: No peer xTU detected.  This error occurs if the
             peer xTU is not powered or not connected or if the
             line is too long to allow detection of a peer xTU.
          
             * 5: Any other or unknown Initialization Failure
             cause.
          
             * 6: ITU T G.998.4 retransmission mode was not
             selected while RTX_MODE = FORCED or with RTX_MODE =
             RTX_TESTMODE.
          
             Note: In G.997.1, this parameter is called
             \"Initialization success/failure cause\".  See
             Clause 7.5.1.6 of ITU-T Recommendation
             {{bibref|G.997.1}}.";
        }
        leaf UPBOKLER {
          type uint32 {
            range "0..1280";
          }
          config false;
          description
            "This parameter contains the estimated electrical loop
             length estimated by the VTU-R expressed in {{units}}
             at 1MHz (see O-UPDATE in section
             12.2.4.2.1.2/G.993.2).  The value is coded as an
             unsignedInt in the range 0 (coded as 0) to 128 dB
             (coded as 1280) in steps of {{units}}.
          
             Note: This parameter is defined as UPBOKLE-R in
             Clause 7.5.1.23.2 of ITU-T Recommendation
             {{bibref|G.997.1}}.";
        }
        leaf UPBOKLEPb {
          type uint32 {
            range "0..1280 | 2047";
          }
          config false;
          description
            "VTU-O estimated upstream power back-off electrical
             length per band.
          
             This parameter is a vector of UPBO electrical length
             per-band estimates for each supported downstream
             band, expressed in {{units}} at 1 MHz (kl0)
             calculated by the VTU-R, based on separate
             measurements in the supported upstream bands.  The
             value of each list element ranges from 0 to 128 dB
             in steps of {{units}}, with special value 204.7
             which indicates that the estimate is greater than
             128 dB.  This parameter is required for the
             alternative electrical length estimation method
             (ELE-M1).
          
             Note: This parameter is defined as UPBOKLE-pb in
             Clause 7.5.1.23.3 of ITU-T Recommendation
             {{bibref|G.997.1}}.";
        }
        leaf UPBOKLERPb {
          type uint32 {
            range "0..1280 | 2047";
          }
          config false;
          description
            "VTU-R estimated upstream power back-off electrical
             length per band.
          
             This parameter is a vector of UPBO electrical length
             per-band estimates for each supported downstream
             band, expressed in {{units}} at 1 MHz (kl0)
             calculated by the VTU-R, based on separate
             measurements in the supported downstream bands.  The
             value of each list element ranges from 0 to 128 dB
             in steps of {{units}}, with special value 204.7
             which indicates that the estimate is greater than
             128 dB.  This parameter is required for the
             alternative electrical length estimation method
             (ELE-M1).
          
             The value of each list element is coded as an
             unsigned 16 bit number in the range 0 (coded as 0)
             to 128 dB (coded as 1280) in steps of {{units}}.
          
             Note: This parameter is defined as UPBOKLE-R-pb in
             Clause 7.5.1.23.4 of ITU-T Recommendation
             {{bibref|G.997.1}}.";
        }
        leaf RXTHRSHds {
          type int32 {
            range "-640..0";
          }
          config false;
          description
            "UPBO downstream receiver signal level threshold.
          
             This parameter reports the downstream received
             signal level threshold value used in the alternative
             electrical length estimation method (ELE-M1).  This
             parameter represents an offset from -100 dBm/Hz, and
             ranges from -64 dB to 0 dB in steps of {{units}}.
          
             The value is coded as a 16 bit number in the range
             -64 (coded as -640) to 0 dB (coded as 0) in steps of
             {{units}}.
          
             Note: See ITU-T Recommendation {{bibref|G.997.1}}.";
        }
        leaf ACTRAMODEds {
          type uint32 {
            range "1..4";
          }
          config false;
          description
            "This parameter indicates the actual active rate
             adaptation mode in the downstream direction.
          
             * If {{param}} equals 1, the link is operating in
             RA-MODE 1 (MANUAL).
          
             * If {{param}} equals 2, the link is operating in
             RA-MODE 2 (AT_INIT).
          
             * If {{param}} equals 3, the link is operating in
             RA-MODE 3 (DYNAMIC).
          
             * If {{param}} equals 4, the link is operating in
             RA-MODE 4 (DYNAMIC with SOS).
          
             Note: This parameter is defined as ACT-RA-MODEds in
             Clause 7.5.1.33.1 of ITU-T Recommendation
             {{bibref|G.997.1}}.";
        }
        leaf ACTRAMODEus {
          type uint32 {
            range "1..4";
          }
          config false;
          description
            "This parameter indicates the actual active rate
             adaptation mode in the upstream direction.
          
             * If {{param}} equals 1, the link is operating in
             RA-MODE 1 (MANUAL).
          
             * If {{param}} equals 2, the link is operating in
             RA-MODE 2 (AT_INIT).
          
             * If {{param}} equals 3, the link is operating in
             RA-MODE 3 (DYNAMIC).
          
             * If {{param}} equals 4, the link is operating in
             RA-MODE 4 (DYNAMIC with SOS).
          
             Note: This parameter is defined as ACT-RA-MODEus in
             Clause 7.5.1.33.2 of ITU-T Recommendation
             {{bibref|G.997.1}}.";
        }
        leaf ACTINPROCds {
          type uint32;
          config false;
          description
            "This parameter reports the actual impulse noise
             protection (INP) of the robust overhead channel
             (ROC) in the downstream direction.  The format and
             usage is identical to the channel status parameter
             {{param|#.Channel.{i}.ACTINP}}.
          
             Note: This parameter is defined as ACTINP-ROC-ds in
             Clause 7.5.1.34.1 of ITU-T Recommendation
             {{bibref|G.997.1}}.";
        }
        leaf ACTINPROCus {
          type uint32;
          config false;
          description
            "This parameter reports the actual impulse noise
             protection (INP) of the robust overhead channel
             (ROC) in the upstream direction.  The format and
             usage is identical to the channel status parameter
             {{param|#.Channel.{i}.ACTINP}}.
          
             Note: This parameter is defined as ACTINP-ROC-us in
             Clause 7.5.1.34.2 ITU-T Recommendation
             {{bibref|G.997.1}}.";
        }
        leaf SNRMROCds {
          type uint32;
          config false;
          description
            "This parameter reports the actual signal-to-noise
             margin of the robust overhead channel (ROC) in the
             downstream direction (expressed in {{units}}).  The
             format is identical to the format of the line status
             parameter SNRM margin
             {{param|DownstreamNoiseMargin}}.
          
             Note: This parameter is defined as SNRM-ROC-ds in
             Clause 7.5.1.35.1 ITU-T Recommendation
             {{bibref|G.997.1}}.";
        }
        leaf SNRMROCus {
          type uint32;
          config false;
          description
            "This parameter reports the actual signal-to-noise
             margin of the robust overhead channel (ROC) in the
             upstream direction (expressed in {{units}}).  The
             format is identical to the format of the line status
             parameter SNRM margin
             ({{param|UpstreamNoiseMargin}}).
          
             Note: This parameter is defined as SNRM-ROC-us in
             Clause 7.5.1.35.2 ITU-T Recommendation
             {{bibref|G.997.1}}.";
        }
        leaf LastStateTransmittedDownstream {
          type uint32;
          config false;
          description
            "This parameter represents the last successful
             transmitted initialization state in the downstream
             direction in the last full initialization performed
             on the line.  Initialization states are defined in
             the individual xDSL Recommendations and are counted
             from 0 (if G.994.1 is used) or 1 (if G.994.1 is not
             used) up to Showtime.  This parameter needs to be
             interpreted along with the xDSL Transmission System.
          
             This parameter is available only when, after a
             failed full initialization, the line diagnostics
             procedures are activated on the line.
          
             Note: See ITU-T Recommendation {{bibref|G.997.1}}.";
        }
        leaf LastStateTransmittedUpstream {
          type uint32;
          config false;
          description
            "This parameter represents the last successful
             transmitted initialization state in the upstream
             direction in the last full initialization performed
             on the line.  Initialization states are defined in
             the individual xDSL Recommendations and are counted
             from 0 (if G.994.1 is used) or 1 (if G.994.1 is not
             used) up to Showtime.  This parameter needs to be
             interpreted along with the xDSL Transmission System.
          
             This parameter is available only when, after a
             failed full initialization, the line diagnostics
             procedures are activated on the line.
          
             Note: See ITU-T Recommendation {{bibref|G.997.1}}.";
        }
        leaf UPBOKLE {
          type uint32 {
            range "0..1280";
          }
          config false;
          description
            "This parameter contains the estimated electrical loop
             length expressed in {{units}} at 1MHz (see O-UPDATE
             in section 12.2.4.2.1.2/G.993.2).  The value SHALL
             be coded as an unsigned 16 bit number in the range 0
             (coded as 0) to 128 dB (coded as 1280) in steps of
             0.1 dB.
          
             Note: See ITU-T Recommendation {{bibref|G.997.1}}.";
        }
        leaf MREFPSDds {
          type binary {
            length "0..145";
          }
          config false;
          description
            "This parameter SHALL contain the set of breakpoints
             exchanged in the MREFPSDds fields of the O-PRM
             message of G.993.2.  Base64 encoded of the binary
             representation defined in Table 12-19/G.993.2
             (maximum length is 145 octets, which requires 196
             bytes for Base64 encoding).
          
             Note: See ITU-T Recommendation {{bibref|G.997.1}}.";
        }
        leaf MREFPSDus {
          type binary {
            length "0..145";
          }
          config false;
          description
            "This parameter SHALL contain the set of breakpoints
             exchanged in the MREFPSDus fields of the R-PRM
             message of G.993.2.  Base64 encoded of the binary
             representation defined in Table 12-19/G.993.2
             (maximum length is 145 octets, which requires 196
             bytes for Base64 encoding).
          
             Note: See ITU-T Recommendation {{bibref|G.997.1}}.";
        }
        leaf LIMITMASK {
          type uint32;
          config false;
          description
            "Indicates the enabled VDSL2 Limit PSD mask of the
             selected PSD mask class.  Bit mask as specified in
             ITU-T Recommendation G.997.1.
          
             Note: For a VDSL2-capable multimode device operating
             in a mode other than VDSL2, the value of this
             parameter SHOULD be set to 0.
          
             Note: See ITU-T Recommendation {{bibref|G.997.1}}.";
        }
        leaf US0MASK {
          type uint32;
          config false;
          description
            "Indicates the allowed VDSL2 US0 PSD masks for Annex A
             operation.  Bit mask as specified in see ITU-T
             Recommendation G.997.1.
          
             Note: For a VDSL2-capable multimode device operating
             in a mode other than VDSL2, the value of this
             parameter SHOULD be set to 0.
          
             Note: See ITU-T Recommendation {{bibref|G.997.1}}.";
        }
        leaf TRELLISds {
          type int32;
          config false;
          description
            "Reports whether trellis coding is enabled in the
             downstream direction.  A value of 1 indicates that
             trellis coding is in use, and a value of 0 indicates
             that the trellis is disabled.
          
             Note: See ITU-T Recommendation {{bibref|G.997.1}}.
             For a multimode device operating in a mode in which
             this parameter does not apply, the value of this
             parameter SHOULD be set to -1.";
        }
        leaf TRELLISus {
          type int32;
          config false;
          description
            "Reports whether trellis coding is enabled in the
             upstream direction.  A value of 1 indicates that
             trellis coding is in use, and a value of 0 indicates
             that the trellis is disabled.
          
             Note: See ITU-T Recommendation {{bibref|G.997.1}}.
             For a multimode device operating in a mode in which
             this parameter does not apply, the value of this
             parameter SHOULD be set to -1.";
        }
        leaf ACTSNRMODEds {
          type uint32;
          config false;
          description
            "Reports whether the OPTIONAL virtual noise mechanism is
             in use in the downstream direction.  A value of 1
             indicates the virtual noise mechanism is not in use,
             and a value of 2 indicates the virtual noise
             mechanism is in use.
          
             Note: See ITU-T Recommendation {{bibref|G.997.1}}.
             For a multimode device operating in a mode in which
             this parameter does not apply, the value of this
             parameter SHOULD be set to 0.";
        }
        leaf ACTSNRMODEus {
          type uint32;
          config false;
          description
            "Reports whether the OPTIONAL virtual noise mechanism is
             in use in the upstream direction.  A value of 1
             indicates the virtual noise mechanism is not in use,
             and a value of 2 indicates the virtual noise
             mechanism is in use.
          
             Note: See ITU-T Recommendation {{bibref|G.997.1}}.
             For a multimode device operating in a mode in which
             this parameter does not apply, the value of this
             parameter SHOULD be set to 0.";
        }
        leaf VirtualNoisePSDds {
          type binary {
            length "0..97";
          }
          config false;
          description
            "Reports the virtual noise PSD for the downstream
             direction.  Base64 encoded of the binary
             representation defined in G.997.1 by the parameter
             called TXREFVNds (maximum length is 97 octets, which
             requires 132 bytes for Base64 encoding).
          
             See ITU-T Recommendation {{bibref|G.997.1}}.  For a
             multimode device operating in a mode in which this
             parameter does not apply, the value of this
             parameter SHOULD be set to {{empty}}.";
        }
        leaf VirtualNoisePSDus {
          type binary {
            length "0..49";
          }
          config false;
          description
            "Reports the virtual noise PSD for the upstream
             direction.  Base64 encoded of the binary
             representation defined in G.997.1by the parameter
             called TXREFVNus (maximum length is 49 octets, which
             requires 68 bytes for Base64 encoding).
          
             See ITU-T Recommendation {{bibref|G.997.1}}.  For a
             multimode device operating in a mode in which this
             parameter does not apply, the value of this
             parameter SHOULD be set to {{empty}}.";
        }
        leaf ACTUALCE {
          type uint32;
          config false;
          description
            "Reports the actual cyclic extension, as the value of m,
             in use for the connection.
          
             Note: See ITU-T Recommendation {{bibref|G.997.1}}.
             For a multimode device operating in a mode in which
             this parameter does not apply, the value of this
             parameter SHOULD be set to 99.";
        }
        leaf LineNumber {
          type int32 {
            range "1..max";
          }
          config false;
          description
            "Signifies the line pair that the modem is using to
             connection.  {{param}} = 1 is the innermost pair.";
        }
        leaf UpstreamMaxBitRate {
          type uint32;
          config false;
          description
            "The current maximum attainable data rate upstream
             (expressed in {{units}}).
          
             Note: This parameter is related to the G.997.1
             parameter ATTNDRus, which is measured in bits/s.
             See ITU-T Recommendation {{bibref|G.997.1}}.";
        }
        leaf DownstreamMaxBitRate {
          type uint32;
          config false;
          description
            "The current maximum attainable data rate downstream
             (expressed in {{units}}).
          
             Note: This parameter is related to the G.997.1
             parameter ATTNDRds, which is measured in bits/s.
             See ITU-T Recommendation {{bibref|G.997.1}}.";
        }
        leaf UpstreamNoiseMargin {
          type int32;
          config false;
          description
            "The current signal-to-noise ratio margin (expressed in
             {{units}}) in the upstream direction.
          
             Note: In G.997.1, this parameter is called SNRMus.
             See ITU-T Recommendation {{bibref|G.997.1}}.";
        }
        leaf DownstreamNoiseMargin {
          type int32;
          config false;
          description
            "The current signal-to-noise ratio margin (expressed in
             {{units}}) in the downstream direction.
          
             Note: In G.997.1, this parameter is called SNRMds.
             See ITU-T Recommendation {{bibref|G.997.1}}.";
        }
        leaf SNRMpbus {
          type string;
          config false;
          description
            "{{list}} Indicates the current signal-to-noise ratio
             margin of each upstream band.  Interpretation of the
             values is as defined in ITU-T Rec.  G.997.1.
          
             Note: See ITU-T Recommendation {{bibref|G.997.1}}.";
        }
        leaf SNRMpbds {
          type string;
          config false;
          description
            "{{list}} Indicates the current signal-to-noise ratio
             margin of each band.  Interpretation of the values
             is as defined in ITU-T Rec.  G.997.1.
          
             Note: See ITU-T Recommendation {{bibref|G.997.1}}.";
        }
        leaf INMIATOds {
          type uint32 {
            range "3..511";
          }
          config false;
          description
            "The Impulse Noise Monitoring (INM) Inter Arrival Time
             (IAT) Offset, measured in DMT symbols, that the xTU
             receiver uses to determine in which bin of the IAT
             histogram the IAT is reported.
          
             Note: In G.997.1, this parameter is called INMIATO.
             See ITU-T Recommendation {{bibref|G.997.1}}.";
        }
        leaf INMIATSds {
          type uint32 {
            range "0..7";
          }
          config false;
          description
            "The Impulse Noise Monitoring (INM) Inter Arrival Time
             (IAT) Step that the xTU receiver uses to determine
             in which bin of the IAT histogram the IAT is
             reported.
          
             Note: In G.997.1, this parameter is called INMIATS.
             See ITU-T Recommendation {{bibref|G.997.1}}.";
        }
        leaf INMCCds {
          type uint32 {
            range "0..64";
          }
          config false;
          description
            "The Impulse Noise Monitoring (INM) Cluster Continuation
             value, measured in DMT symbols, that the xTU
             receiver uses in the cluster indication process.
          
             Note: In G.997.1, this parameter is called INMCC.
             See ITU-T Recommendation {{bibref|G.997.1}}.";
        }
        leaf INMINPEQMODEds {
          type uint32 {
            range "0..3";
          }
          config false;
          description
            "The Impulse Noise Monitoring (INM) Equivalent Impulse
             Noise Protection (INP) Mode that the xTU receiver
             uses in the computation of the Equivalent INP.
          
             Note: In G.997.1, this parameter is called
             INM_INPEQ_MODE.  See ITU-T Recommendation
             {{bibref|G.997.1}}.";
        }
        leaf UpstreamAttenuation {
          type int32;
          config false;
          description
            "The current upstream signal loss (expressed in
             {{units}}).";
        }
        leaf DownstreamAttenuation {
          type int32;
          config false;
          description
            "The current downstream signal loss (expressed in
             {{units}}).";
        }
        leaf UpstreamPower {
          type int32;
          config false;
          description
            "The current output power at the CPE's DSL line
             (expressed in {{units}}).";
        }
        leaf DownstreamPower {
          type int32;
          config false;
          description
            "The current received power at the CPE's DSL line
             (expressed in {{units}}).";
        }
        leaf XTURVendor {
          type yang:hex-string {
            length "4";
          }
          config false;
          description
            "xTU-R vendor identifier as defined in G.994.1 and
             T1.413.  In the case of G.994.1 this corresponds to
             the four-octet provider code, which MUST be
             represented as eight hexadecimal digits.
          
             Note: This parameter is OPTIONAL at the G and S/T
             interfaces in G.997.1 Amendment 1.  If the parameter
             is implemented but no value is available, it MUST
             have the value \"00000000\".
          
             Note: In G.997.1, this parameter is called \"xTU-R
             G.994.1 Vendor ID\".  See ITU-T Recommendation
             {{bibref|G.997.1}}.";
        }
        leaf XTURCountry {
          type yang:hex-string {
            length "2";
          }
          config false;
          description
            "T.35 country code of the xTU-R vendor as defined in
             G.994.1, where the two-octet value defined in
             G.994.1 MUST be represented as four hexadecimal
             digits.
          
             Note: This parameter is OPTIONAL at the G and S/T
             interfaces in G.997.1 Amendment 1.  If the parameter
             is implemented but no value is available, it MUST
             have the value \"0000\".
          
             Note: In G.997.1, this parameter is called \"xTU-R
             G.994.1 Vendor ID\".  See ITU-T Recommendation
             {{bibref|G.997.1}}.";
        }
        leaf XTURANSIStd {
          type uint32;
          config false;
          description
            "xTU-R T1.413 Revision Number as defined in T1.413 Issue
             2.
          
             When T1.413 modulation is not in use, the parameter
             value SHOULD be 0.";
        }
        leaf XTURANSIRev {
          type uint32;
          config false;
          description
            "xTU-R Vendor Revision Number as defined in T1.413 Issue
             2.
          
             When T1.413 modulation is not in use, the parameter
             value SHOULD be 0.";
        }
        leaf XTUCVendor {
          type yang:hex-string {
            length "4";
          }
          config false;
          description
            "xTU-C vendor identifier as defined in G.994.1 and
             T1.413.  In the case of G.994.1 this corresponds to
             the four-octet provider code, which MUST be
             represented as eight hexadecimal digits.
          
             Note: This parameter is OPTIONAL at the G and S/T
             interfaces in G.997.1 Amendment 1.  If the parameter
             is implemented but no value is available, it MUST
             have the value \"00000000\".";
        }
        leaf XTUCCountry {
          type yang:hex-string {
            length "2";
          }
          config false;
          description
            "T.35 country code of the xTU-C vendor as defined in
             G.994.1, where the two-octet value defined in
             G.994.1 MUST be represented as four hexadecimal
             digits.
          
             Note: This parameter is OPTIONAL at the G and S/T
             interfaces in G.997.1 Amendment 1.  If the parameter
             is implemented but no value is available, it MUST
             have the value \"0000\".";
        }
        leaf XTUCANSIStd {
          type uint32;
          config false;
          description
            "xTU-C T1.413 Revision Number as defined in T1.413 Issue
             2.
          
             When T1.413 modulation is not in use, the parameter
             value SHOULD be 0.";
        }
        leaf XTUCANSIRev {
          type uint32;
          config false;
          description
            "xTU-C Vendor Revision Number as defined in T1.413 Issue
             2.
          
             When T1.413 modulation is not in use, the parameter
             value SHOULD be 0.";
        }

        container DataGathering {
          config false;
          description
            "This object models the DSL data gathering function at
             the VTU-R.  This only applies to VDSL2.
          
             Note: see ITU-T Recommendation {{bibref|G.993.2}}.";
          leaf LoggingDepthR {
            type uint32;
            description
              "This parameter is the maximum depth of the entire
               data gathering event buffer at the VTU-R, in
               number of {{units}}, where each of the {{units}}
               consists of 6 bytes indicating a data gathering
               event as defined in {{bibref|G.993.2}}.
            
               Note: This parameter is defined as LOGGING_DEPTH_R
               in Clause 7.5.3.2 of ITU-T Recommendation
               {{bibref|G.997.1}}.";
          }
          leaf ActLoggingDepthReportingR {
            type uint32;
            description
              "This parameter is actual logging depth that is used
               for reporting the VTU-R event trace buffer over
               the eoc channel, in number of {{units}}, where
               each of the {{units}} consists of 6 bytes
               indicating a data gathering event as defined in
               {{bibref|G.993.2}}.
            
               Note: This parameter is defined as
               ACT_LOGGING_DEPTH_REPORTING_R in Clause 7.5.3.4 of
               ITU-T Recommendation {{bibref|G.997.1}}.";
          }
          leaf EventTraceBufferR {
            type string {
              length "0..256";
            }
            description
              "This parameter identifies the log file of the the
               data gathering event trace buffer containing the
               event records that originated at the VTU-R.
            
               This indicates the table entry that represents a
               Vendor Log File that contains the data gathering
               buffer at the VTU-R in the
               {{object|###.DeviceInfo.VendorLogFile}} table.
            
               This data gathering buffer MAY be retrieved wia an
               upload RPC of the identified Vendor Log File.
            
               Note: This parameter is defined as
               EVENT_TRACE_BUFFER_R in Clause 7.5.3.6 of ITU-T
               Recommendation {{bibref|G.997.1}} and Clause 11.5
               of ITU-T Recommendation {{bibref|G.993.2}}.";
          }
        }

        container Stats {
          config false;
          description
            "Throughput statistics for this interface.
          
             The CPE MUST reset the interface's Stats parameters
             (unless otherwise stated in individual object or
             parameter descriptions) either when the interface
             becomes operationally down due to a previous
             administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2|section 4.2.2}}.";
          leaf BytesSent {
            type uint64;
            description
              "The total number of bytes transmitted out of the
               interface, including framing characters.";
          }
          leaf BytesReceived {
            type uint64;
            description
              "The total number of bytes received on the interface,
               including framing characters.";
          }
          leaf PacketsSent {
            type uint64;
            description
              "The total number of packets transmitted out of the
               interface.";
          }
          leaf PacketsReceived {
            type uint64;
            description
              "The total number of packets received on the
               interface.";
          }
          leaf ErrorsSent {
            type uint32;
            description
              "The total number of outbound packets that could not
               be transmitted because of errors.";
          }
          leaf ErrorsReceived {
            type uint32;
            description
              "The total number of inbound packets that contained
               errors preventing them from being delivered to a
               higher-layer protocol.";
          }
          leaf DiscardPacketsSent {
            type uint32;
            description
              "The total number of outbound packets which were
               chosen to be discarded even though no errors had
               been detected to prevent their being transmitted.
               One possible reason for discarding such a packet
               could be to free up buffer space.";
          }
          leaf DiscardPacketsReceived {
            type uint32;
            description
              "The total number of inbound packets which were chosen
               to be discarded even though no errors had been
               detected to prevent their being delivered.  One
               possible reason for discarding such a packet could
               be to free up buffer space.";
          }
          leaf TotalStart {
            type uint32;
            description
              "DSL-specific statistic.  The Number of {{units}}
               since the beginning of the period used for
               collection of {{object|Total}} statistics.
            
               Statistics SHOULD continue to be accumulated
               across CPE reboots, though this might not always
               be possible.
            
               Note: {{param}} SHOULD NOT be reset when the
               interface statistics are reset via an interface
               disable / enable cycle.";
          }
          leaf ShowtimeStart {
            type uint32;
            description
              "DSL-specific statistic.  The Number of {{units}}
               since the most recent DSL Showtime - the beginning
               of the period used for collection of
               {{object|Showtime}} statistics.
            
               Showtime is defined as successful completion of
               the DSL link establishment process.  The
               ''Showtime'' statistics are those collected since
               the most recent establishment of the DSL link.
            
               Note: {{param}} SHOULD NOT be reset when the
               interface statistics are reset via an interface
               disable / enable cycle.";
          }
          leaf LastShowtimeStart {
            type uint32;
            description
              "DSL-specific statistic.  The Number of {{units}}
               since the second most recent DSL Showtime-the
               beginning of the period used for collection of
               {{object|LastShowtime}} statistics.
            
               If the CPE has not retained information about the
               second most recent Showtime (e.g., on reboot), the
               start of ''LastShowtime'' statistics MAY
               temporarily coincide with the start of
               ''Showtime'' statistics.
            
               Note: {{param}} SHOULD NOT be reset when the
               interface statistics are reset via an interface
               disable / enable cycle.";
          }
          leaf CurrentDayStart {
            type uint32;
            description
              "DSL-specific statistic.  The Number of {{units}}
               since the beginning of the period used for
               collection of {{object|CurrentDay}} statistics.
            
               The CPE MAY align the beginning of each
               ''CurrentDay'' interval with days in the UTC time
               zone, but is not required to do so.
            
               Statistics SHOULD continue to be accumulated
               across CPE reboots, though this might not always
               be possible.
            
               Note: {{param}} SHOULD NOT be reset when the
               interface statistics are reset via an interface
               disable / enable cycle.";
          }
          leaf QuarterHourStart {
            type uint32;
            description
              "DSL-specific statistic.  The Number of {{units}}
               since the beginning of the period used for
               collection of {{object|QuarterHour}} statistics.
            
               The CPE MAY align the beginning of each
               ''QuarterHour'' interval with real-time
               quarter-hour intervals, but is not required to do
               so.
            
               Statistics SHOULD continue to be accumulated
               across CPE reboots, though this might not always
               be possible.
            
               Note: {{param}} SHOULD NOT be reset when the
               interface statistics are reset via an interface
               disable / enable cycle.";
          }

          container Total {
            description
              "This object contains DSL line total statistics.  See
               {{bibref|G.997.1|Chapter 7.2.6}}.
            
               Note: The {{object}} parameters SHOULD NOT be
               reset when the interface statistics are reset via
               an interface disable / enable cycle.";
            leaf ErroredSecs {
              type uint32;
              description
                "Total number of errored seconds (ES-L as defined in
                 ITU-T Rec.  {{bibref|G.997.1}}).
              
                 Note: This parameter is OPTIONAL at the G and
                 S/T interfaces in G.997.1 Amendment 1.  If the
                 parameter is implemented but no value is
                 available, its value MUST be 4294967295 (the
                 maximum for its data type).";
            }
            leaf SeverelyErroredSecs {
              type uint32;
              description
                "Total number of severely errored seconds (SES-L as
                 defined in ITU-T Rec.  {{bibref|G.997.1}}).
              
                 Note: This parameter is OPTIONAL at the G and
                 S/T interfaces in G.997.1 Amendment 1.  If the
                 parameter is implemented but no value is
                 available, its value MUST be 4294967295 (the
                 maximum for its data type).";
            }
          }

          container Showtime {
            description
              "This object contains DSL line statistics accumulated
               since the most recent DSL Showtime.  See
               {{bibref|G.997.1|Chapter 7.2.6}}.
            
               Note: The {{object}} parameters SHOULD NOT be
               reset when the interface statistics are reset via
               an interface disable / enable cycle.";
            leaf ErroredSecs {
              type uint32;
              description
                "Number of errored seconds since the most recent DSL
                 Showtime (ES-L as defined in ITU-T Rec.
                 {{bibref|G.997.1}}).
              
                 Note: This parameter is OPTIONAL at the G and
                 S/T interfaces in G.997.1 Amendment 1.  If the
                 parameter is implemented but no value is
                 available, its value MUST be 4294967295 (the
                 maximum for its data type).";
            }
            leaf SeverelyErroredSecs {
              type uint32;
              description
                "Number of severely errored seconds since the most
                 recent DSL Showtime (SES-L as defined in ITU-T
                 Rec.  {{bibref|G.997.1}}).
              
                 Note: This parameter is OPTIONAL at the G and
                 S/T interfaces in G.997.1 Amendment 1.  If the
                 parameter is implemented but no value is
                 available, its value MUST be 4294967295 (the
                 maximum for its data type).";
            }
          }

          container LastShowtime {
            description
              "This object contains DSL line statistics accumulated
               since the second most recent DSL Showtime.  See
               {{bibref|G.997.1|Chapter 7.2.6}}.
            
               Note: The {{object}} parameters SHOULD NOT be
               reset when the interface statistics are reset via
               an interface disable / enable cycle.";
            leaf ErroredSecs {
              type uint32;
              description
                "Number of errored seconds since the second most
                 recent DSL Showtime (ES-L as defined in ITU-T
                 Rec.  {{bibref|G.997.1}}).
              
                 Note: This parameter is OPTIONAL at the G and
                 S/T interfaces in G.997.1 Amendment 1.  If the
                 parameter is implemented but no value is
                 available, its value MUST be 4294967295 (the
                 maximum for its data type).";
            }
            leaf SeverelyErroredSecs {
              type uint32;
              description
                "Number of severely errored seconds since the second
                 most recent DSL Showtime (SES-L as defined in
                 ITU-T Rec.  {{bibref|G.997.1}}).
              
                 Note: This parameter is OPTIONAL at the G and
                 S/T interfaces in G.997.1 Amendment 1.  If the
                 parameter is implemented but no value is
                 available, its value MUST be 4294967295 (the
                 maximum for its data type).";
            }
          }

          container CurrentDay {
            description
              "This object contains DSL line statistics accumulated
               during the current day.  See
               {{bibref|G.997.1|Chapter 7.2.6}}.
            
               Note: The {{object}} parameters SHOULD NOT be
               reset when the interface statistics are reset via
               an interface disable / enable cycle.";
            leaf ErroredSecs {
              type uint32;
              description
                "Number of errored seconds since the second most
                 recent DSL Showtime (ES-L as defined in ITU-T
                 Rec.  {{bibref|G.997.1}}).
              
                 Note: This parameter is OPTIONAL at the G and
                 S/T interfaces in G.997.1 Amendment 1.  If the
                 parameter is implemented but no value is
                 available, its value MUST be 4294967295 (the
                 maximum for its data type).";
            }
            leaf SeverelyErroredSecs {
              type uint32;
              description
                "Number of severely errored seconds since the second
                 most recent DSL Showtime (SES-L as defined in
                 ITU-T Rec.  {{bibref|G.997.1}}).
              
                 Note: This parameter is OPTIONAL at the G and
                 S/T interfaces in G.997.1 Amendment 1.  If the
                 parameter is implemented but no value is
                 available, its value MUST be 4294967295 (the
                 maximum for its data type).";
            }
          }

          container QuarterHour {
            description
              "This object contains DSL line statistics accumulated
               during the current quarter hour.  See
               {{bibref|G.997.1|Chapter 7.2.6}}.
            
               Note: The {{object}} parameters SHOULD NOT be
               reset when the interface statistics are reset via
               an interface disable / enable cycle.";
            leaf ErroredSecs {
              type uint32;
              description
                "Number of errored seconds since the second most
                 recent DSL Showtime (ES-L as defined in ITU-T
                 Rec.  {{bibref|G.997.1}}).
              
                 Note: This parameter is OPTIONAL at the G and
                 S/T interfaces in G.997.1 Amendment 1.  If the
                 parameter is implemented but no value is
                 available, its value MUST be 4294967295 (the
                 maximum for its data type).";
            }
            leaf SeverelyErroredSecs {
              type uint32;
              description
                "Number of severely errored seconds since the second
                 most recent DSL Showtime (SES-L as defined in
                 ITU-T Rec.  {{bibref|G.997.1}}).
              
                 Note: This parameter is OPTIONAL at the G and
                 S/T interfaces in G.997.1 Amendment 1.  If the
                 parameter is implemented but no value is
                 available, its value MUST be 4294967295 (the
                 maximum for its data type).";
            }
          }
        }

        container TestParams {
          config false;
          description
            "This object contains the DSL line test parameters that
             are available during the L0 (i.e., Showtime) state.";
          leaf HLOGGds {
            type uint32;
            description
              "Number of sub-carriers per sub-carrier group in the
               downstream direction for {{param|HLOGpsds}}.
               Valid values are 1, 2, 4, and 8.
            
               Note: See ITU-T Recommendation {{bibref|G.997.1}}.
               For a multimode device operating in a mode in
               which this parameter does not apply, the value of
               this parameter SHOULD be set to 1.";
          }
          leaf HLOGGus {
            type uint32;
            description
              "Number of sub-carriers per sub-carrier group in the
               upstream direction for {{param|HLOGpsus}}.  Valid
               values are 1, 2, 4, and 8.
            
               Note: See ITU-T Recommendation {{bibref|G.997.1}}.
               For a multimode device operating in a mode in
               which this parameter does not apply, the value of
               this parameter SHOULD be set to 1.";
          }
          leaf HLOGpsds {
            type string;
            description
              "{{list}} Indicates the downstream logarithmic line
               characteristics per sub-carrier group.  The
               maximum number of elements is 256 for G.992.3, and
               512 for G.992.5.  For G.993.2, the number of
               elements will depend on the value of
               {{param|HLOGGds}} but will not exceed 512.
               Interpretation of the values is as defined in
               ITU-T Rec.  G.997.1.
            
               Note: See ITU-T Recommendation {{bibref|G.997.1}}.
               For a multimode device operating in a mode in
               which this parameter does not apply, the value of
               this parameter SHOULD be set to ''None''.
            
               Note: {{param}} is measured during initialization
               and is not updated during Showtime.";
          }
          leaf HLOGpsus {
            type string;
            description
              "{{list}} Indicates the upstream logarithmic line
               characteristics per sub-carrier group.  The
               maximum number of elements is 64 for G.992.3 and
               G.992.5.  For G.993.2, the number of elements will
               depend on the value of {{param|HLOGGus}} but will
               not exceed 512.  Interpretation of the values is
               as defined in ITU-T Rec.  G.997.1.
            
               Note: See ITU-T Recommendation {{bibref|G.997.1}}.
               For a multimode device operating in a mode in
               which this parameter does not apply, the value of
               this parameter SHOULD be set to ''None''.
            
               Note: {{param}} is measured during initialization
               and is not updated during Showtime.";
          }
          leaf HLOGMTds {
            type uint32;
            description
              "Indicates the number of symbols over which
               {{param|HLOGpsds}} was measured.
            
               Note: See ITU-T Recommendation {{bibref|G.997.1}}.
               For a multimode device operating in a mode in
               which this parameter does not apply, the value of
               this parameter SHOULD be set to 0.";
          }
          leaf HLOGMTus {
            type uint32;
            description
              "Indicates the number of symbols over which
               {{param|HLOGpsus}} was measured.
            
               Note: See ITU-T Recommendation {{bibref|G.997.1}}.
               For a multimode device operating in a mode in
               which this parameter does not apply, the value of
               this parameter SHOULD be set to 0.";
          }
          leaf QLNGds {
            type uint32;
            description
              "Number of sub-carriers per sub-carrier group in the
               downstream direction for {{param|QLNpsds}}.  Valid
               values are 1, 2, 4, and 8.
            
               Note: See ITU-T Recommendation {{bibref|G.997.1}}.
               For a multimode device operating in a mode in
               which this parameter does not apply, the value of
               this parameter SHOULD be set to 1.";
          }
          leaf QLNGus {
            type uint32;
            description
              "Number of sub-carriers per sub-carrier group in the
               upstream direction for {{param|QLNpsus}}.  Valid
               values are 1, 2, 4, and 8.
            
               Note: See ITU-T Recommendation {{bibref|G.997.1}}.
               For a multimode device operating in a mode in
               which this parameter does not apply, the value of
               this parameter SHOULD be set to 1.";
          }
          leaf QLNpsds {
            type int32;
            description
              "{{list}} Indicates the downstream quiet line noise
               per subcarrier group.  The maximum number of
               elements is 256 for G.992.3 and G.992.5.  For
               G.993.2, the number of elements will depend on the
               value of {{param|QLNGds}} but will not exceed 512.
               Interpretation of the values is as defined in
               ITU-T Rec.  G.997.1.
            
               Note: See ITU-T Recommendation {{bibref|G.997.1}}.
               For a multimode device operating in a mode in
               which this parameter does not apply, the value of
               this parameter SHOULD be set to ''None''.
            
               Note: {{param}} is measured during initialization
               and is not updated during Showtime.";
          }
          leaf QLNpsus {
            type string;
            description
              "{{list}} Indicates the upstream quiet line noise per
               subcarrier group.  The maximum number of elements
               is 64 for G.992.3 and G.992.5.  For G.993.2, the
               number of elements will depend on the value of
               {{param|QLNGus}} but will not exceed 512.
               Interpretation of the values is as defined in
               ITU-T Rec.  G.997.1.
            
               Note: See ITU-T Recommendation {{bibref|G.997.1}}.
               For a multimode device operating in a mode in
               which this parameter does not apply, the value of
               this parameter SHOULD be set to ''None''.
            
               Note: {{param}} is measured during initialization
               and is not updated during Showtime.";
          }
          leaf QLNMTds {
            type uint32;
            description
              "Indicates the number of symbols over which
               {{param|QLNpsds}} was measured.
            
               Note: See ITU-T Recommendation {{bibref|G.997.1}}.
               For a multimode device operating in a mode in
               which this parameter does not apply, the value of
               this parameter SHOULD be set to 0.";
          }
          leaf QLNMTus {
            type uint32;
            description
              "Indicates the number of symbols over which
               {{param|QLNpsus}} was measured.
            
               Note: See ITU-T Recommendation {{bibref|G.997.1}}.
               For a multimode device operating in a mode in
               which this parameter does not apply, the value of
               this parameter SHOULD be set to 0.";
          }
          leaf SNRGds {
            type uint32;
            description
              "Number of sub-carriers per sub-carrier group in the
               downstream direction for {{param|SNRpsds}}.  Valid
               values are 1, 2, 4, and 8.
            
               Note: See ITU-T Recommendation {{bibref|G.997.1}}.
               For a multimode device operating in a mode in
               which this parameter does not apply, the value of
               this parameter SHOULD be set to 1.";
          }
          leaf SNRGus {
            type uint32;
            description
              "Number of sub-carriers per sub-carrier group in the
               upstream direction for {{param|SNRpsus}}.  Valid
               values are 1, 2, 4, and 8.
            
               Note: See ITU-T Recommendation {{bibref|G.997.1}}.
               For a multimode device operating in a mode in
               which this parameter does not apply, the value of
               this parameter SHOULD be set to 1.";
          }
          leaf SNRpsds {
            type int32;
            description
              "{{list}} Indicates the downstream SNR per subcarrier
               group.  The maximum number of elements is 256 for
               G.992.3, and 512 for G.992.5.  For G.993.2, the
               number of elements will depend on the value of
               {{param|SNRGds}} but will not exceed 512.
               Interpretation of the values is as defined in
               ITU-T Rec.  G.997.1.
            
               Note: See ITU-T Recommendation {{bibref|G.997.1}}.
               For a multimode device operating in a mode in
               which this parameter does not apply, the value of
               this parameter SHOULD be set to ''None''.
            
               Note: {{param}} is first measured during
               initialization and is updated during Showtime.";
          }
          leaf SNRpsus {
            type string;
            description
              "{{list}} Indicates the upstream SNR per subcarrier
               group.  The maximum number of elements is 64 for
               G.992.3 and G.992.5.  For G.993.2, the number of
               elements will depend on the value of
               {{param|SNRGus}} but will not exceed 512.
               Interpretation of the values is as defined in
               ITU-T Rec.  G.997.1.
            
               Note: See ITU-T Recommendation {{bibref|G.997.1}}.
               For a multimode device operating in a mode in
               which this parameter does not apply, the value of
               this parameter SHOULD be set to ''None''.
            
               Note: {{param}} is first measured during
               initialization and is updated during Showtime.";
          }
          leaf SNRMTds {
            type uint32;
            description
              "Indicates the number of symbols over which
               {{param|SNRpsds}} was measured.
            
               Note: See ITU-T Recommendation {{bibref|G.997.1}}.
               For a multimode device operating in a mode in
               which this parameter does not apply, the value of
               this parameter SHOULD be set to 0.";
          }
          leaf SNRMTus {
            type uint32;
            description
              "Indicates the number of symbols over which
               {{param|SNRpsus}} was measured.
            
               Note: See ITU-T Recommendation {{bibref|G.997.1}}.
               For a multimode device operating in a mode in
               which this parameter does not apply, the value of
               this parameter SHOULD be set to 0.";
          }
          leaf LATNds {
            type string;
            description
              "{{list}} Indicates the downstream line attenuation
               per usable band, as computed during
               initialization.  Number of elements is dependent
               on the number of downstream bands but will exceed
               one only for G.993.2.  Interpretation of {{param}}
               is as defined in ITU-T Rec.  G.997.1.
            
               Note: See ITU-T Recommendation {{bibref|G.997.1}}.";
          }
          leaf LATNus {
            type string;
            description
              "{{list}} Indicates the upstream line attenuation per
               usable band, as computed during initialization.
               Number of elements is dependent on the number of
               upstream bands but will exceed one only for
               G.993.2.  Interpretation of {{param}} is as
               defined in ITU-T Rec.  G.997.1.
            
               Note: See ITU-T Recommendation {{bibref|G.997.1}}.";
          }
          leaf SATNds {
            type string;
            description
              "{{list}} Indicates the downstream signal attenuation
               per usable band, as computed during the L0 (i.e.,
               Showtime) state.  Number of elements is dependent
               on the number of downstream bands but will exceed
               one only for G.993.2.  Interpretation of {{param}}
               is as defined in ITU-T Rec.  G.997.1.
            
               Note: See ITU-T Recommendation {{bibref|G.997.1}}.";
          }
          leaf SATNus {
            type string;
            description
              "{{list}} Indicates the upstream signal attenuation
               per usable band, as computed during the L0 (i.e.,
               Showtime) state.  Number of elements is dependent
               on the number of downstream bands but will exceed
               one only for G.993.2.  Interpretation of {{param}}
               is as defined in ITU-T Rec.  G.997.1.
            
               Note: See ITU-T Recommendation {{bibref|G.997.1}}.";
          }
        }
      }

      list Channel {
        key "Alias";
        description
          "DSL Channel table (a stackable interface object as
           described in {{bibref|TR-181i2|Section 4.2}}).
        
           This table models DSL channel(s) on top of physical
           DSL lines.";
        leaf Enable {
          type boolean;
          description
            "Enables or disables the channel.
          
             This parameter is based on ''ifAdminStatus'' from
             {{bibref|RFC2863}}.";
        }
        leaf Status {
          type enumeration {
            enum "Up";
            enum "Down";
            enum "Unknown";
            enum "Dormant";
            enum "NotPresent";
            enum "LowerLayerDown";
            enum "Error";
          }
          config false;
          description
            "The current operational state of the channel (see
             {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the channel as assigned by the CPE.";
        }
        leaf LastChange {
          type uint32;
          config false;
          description
            "The accumulated time in {{units}} since the channel
             entered its current operational state.";
        }
        leaf LowerLayers {
          type string;
          config false;
          description
            "{{list}} {{reference|an interface object that is
             stacked immediately below this interface object}}
             See {{bibref|TR-181i2|Section 4.2.1}}.";
        }
        leaf LinkEncapsulationSupported {
          type enumeration {
            enum "G.992.3_Annex_K_ATM";
            enum "G.992.3_Annex_K_PTM";
            enum "G.993.2_Annex_K_ATM";
            enum "G.993.2_Annex_K_PTM";
            enum "G.994.1";
          }
          config false;
          description
            "{{list}} List items indicate which link encapsulation
             standards and recommendations are supported by the
             {{object}} instance.";
        }
        leaf LinkEncapsulationUsed {
          type enumeration {
            enum "G.992.3_Annex_K_ATM";
            enum "G.992.3_Annex_K_PTM";
            enum "G.993.2_Annex_K_ATM";
            enum "G.993.2_Annex_K_PTM";
          }
          config false;
          description
            "Indicates the link encapsulation standard that the
             {{object}} instance is using for the connection.
             {{enum}}
          
             When ATM encapsulation is identified then an
             upper-layer {{object|.ATM.Link}} interface MUST be
             used.
          
             When PTM encapsulation is identified then an
             upper-layer {{object|.PTM.Link}} interface MUST be
             used.";
        }
        leaf LPATH {
          type uint32 {
            range "min..3";
          }
          config false;
          description
            "Reports the index of the latency path supporting the
             bearer channel.
          
             Note: See ITU-T Recommendation
             {{bibref|G.997.1|Section 7.5.2.7}}.";
        }
        leaf INTLVDEPTH {
          type uint32;
          config false;
          description
            "Reports the interleaver depth D for the latency path
             indicated in {{param|LPATH}}.
          
             Note: See ITU-T Recommendation {{bibref|G.997.1}}.
             For a multimode device operating in a mode in which
             this parameter does not apply, the value of this
             parameter SHOULD be set to 0.";
        }
        leaf INTLVBLOCK {
          type int32;
          config false;
          description
            "Reports the interleaver block length in use on the
             latency path indicated in {{param|LPATH}}.
          
             Note: See ITU-T Recommendation {{bibref|G.997.1}}.
             For a multimode device operating in a mode in which
             this parameter does not apply, the value of this
             parameter SHOULD be set to -1.";
        }
        leaf ActualInterleavingDelay {
          type uint32;
          config false;
          description
            "Reports the actual delay, in {{units}}, of the latency
             path due to interleaving.
          
             Note: In G.997.1, this parameter is called \"Actual
             Interleaving Delay.\" See ITU-T Recommendation
             {{bibref|G.997.1}}.";
        }
        leaf ACTINP {
          type int32;
          config false;
          description
            "Reports the actual impulse noise protection (INP)
             provided by the latency path indicated in
             {{param|LPATH}}.  The value is the actual INP in the
             L0 (i.e., Showtime) state.
          
             Note: See ITU-T Recommendation {{bibref|G.997.1}}.
             For a multimode device operating in a mode in which
             this parameter does not apply, the value of this
             parameter SHOULD be set to -1.";
        }
        leaf INPREPORT {
          type boolean;
          config false;
          description
            "Reports whether the value reported in ACTINP was
             computed assuming the receiver does not use erasure
             decoding.  Valid values are 0 (computed per the
             formula assuming no erasure decoding) and 1
             (computed by taking into account erasure decoding
             capabilities of receiver).
          
             Note: See ITU-T Recommendation {{bibref|G.997.1}}.
             For a multimode device operating in a mode in which
             this parameter does not apply, the value of this
             parameter SHOULD be set to {{false}}.";
        }
        leaf NFEC {
          type int32;
          config false;
          description
            "Reports the size, in {{units}}, of the Reed-Solomon
             codeword in use on the latency path indicated in
             {{param|LPATH}}.
          
             Note: See ITU-T Recommendation {{bibref|G.997.1}}.
             For a multimode device operating in a mode in which
             this parameter does not apply, the value of this
             parameter SHOULD be set to -1.";
        }
        leaf RFEC {
          type int32;
          config false;
          description
            "Reports the number of redundancy bytes per Reed-Solomon
             codeword on the latency path indicated in
             {{param|LPATH}}.
          
             Note: See ITU-T Recommendation {{bibref|G.997.1}}.
             For a multimode device operating in a mode in which
             this parameter does not apply, the value of this
             parameter SHOULD be set to -1.";
        }
        leaf LSYMB {
          type int32;
          config false;
          description
            "Reports the number of bits per symbol assigned to the
             latency path indicated in {{param|LPATH}}.  This
             value does not include overhead due to trellis
             coding.
          
             Note: See ITU-T Recommendation {{bibref|G.997.1}}.
             For a multimode device operating in a mode in which
             this parameter does not apply, the value of this
             parameter SHOULD be set to -1.";
        }
        leaf UpstreamCurrRate {
          type uint32;
          config false;
          description
            "The current physical layer aggregate data rate
             (expressed in {{units}}) of the upstream DSL
             connection.
          
             Note: If the parameter is implemented but no value
             is available, it MUST have the value 4294967295 (the
             maximum for its data type).";
        }
        leaf DownstreamCurrRate {
          type uint32;
          config false;
          description
            "The current physical layer aggregate data rate
             (expressed in {{units}}) of the downstream DSL
             connection.
          
             Note: If the parameter is implemented but no value
             is available, it MUST have the value 4294967295 (the
             maximum for its data type).";
        }
        leaf ACTNDR {
          type uint32;
          config false;
          description
            "Actual net data rate expressed in {{units}}.
             Independent whether retransmission is used or not in
             a given transmit direction:
          
             * In L0 state, this parameter reports the net data
             rate (as specified in [ITU T G.992.3], [ITU T
             G.992.5] or [ITU T G.993.2]) at which the bearer
             channel is operating.
          
             * In L2 state, the parameter contains the net data
             rate (as specified in [ITU T G.992.3], [ITU T
             G.992.5] or [ITU T G.993.2]) in the previous L0
             state.
          
             Note: See ITU-T Recommendation {{bibref|G.997.1}}.";
        }
        leaf ACTINPREIN {
          type uint32 {
            range "0..255";
          }
          config false;
          description
            "Actual impulse noise protection against REIN, expressed
             in {{units}}.
          
             If retransmission is used in a given transmit
             direction, this parameter reports the actual impulse
             noise protection (INP) against REIN (under specific
             conditions detailed in [ITU T G.998.4]) on the
             bearer channel in the L0 state.  In the L2 state,
             the parameter contains the INP in the previous L0
             state.
          
             The value is coded in fractions of DMT symbols with
             a granularity of 0.1 symbols.
          
             The range is from 0 to 25.4.  A special value of
             25.5 indicates an ACTINP_REIN of 25.5 or higher.
          
             Note: This parameter is defined as ACTINP_REIN in
             Clause 7.5.2.9 of ITU-T Recommendation
             {{bibref|G.997.1}}.";
        }

        container Stats {
          config false;
          description
            "Throughput statistics for this interface.
          
             The CPE MUST reset the interface's Stats parameters
             (unless otherwise stated in individual object or
             parameter descriptions) either when the interface
             becomes operationally down due to a previous
             administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2|section 4.2.2}}.";
          leaf BytesSent {
            type uint64;
            description
              "The total number of bytes transmitted out of the
               interface, including framing characters.";
          }
          leaf BytesReceived {
            type uint64;
            description
              "The total number of bytes received on the interface,
               including framing characters.";
          }
          leaf PacketsSent {
            type uint64;
            description
              "The total number of packets transmitted out of the
               interface.";
          }
          leaf PacketsReceived {
            type uint64;
            description
              "The total number of packets received on the
               interface.";
          }
          leaf ErrorsSent {
            type uint32;
            description
              "The total number of outbound packets that could not
               be transmitted because of errors.";
          }
          leaf ErrorsReceived {
            type uint32;
            description
              "The total number of inbound packets that contained
               errors preventing them from being delivered to a
               higher-layer protocol.";
          }
          leaf DiscardPacketsSent {
            type uint32;
            description
              "The total number of outbound packets which were
               chosen to be discarded even though no errors had
               been detected to prevent their being transmitted.
               One possible reason for discarding such a packet
               could be to free up buffer space.";
          }
          leaf DiscardPacketsReceived {
            type uint32;
            description
              "The total number of inbound packets which were chosen
               to be discarded even though no errors had been
               detected to prevent their being delivered.  One
               possible reason for discarding such a packet could
               be to free up buffer space.";
          }
          leaf TotalStart {
            type uint32;
            description
              "DSL-specific statistic.  The Number of {{units}}
               since the beginning of the period used for
               collection of {{object|Total}} statistics.
            
               Statistics SHOULD continue to be accumulated
               across CPE reboots, though this might not always
               be possible.
            
               Note: {{param}} SHOULD NOT be reset when the
               interface statistics are reset via an interface
               disable / enable cycle.";
          }
          leaf ShowtimeStart {
            type uint32;
            description
              "DSL-specific statistic.  The Number of {{units}}
               since the most recent DSL Showtime - the beginning
               of the period used for collection of
               {{object|Showtime}} statistics.
            
               Showtime is defined as successful completion of
               the DSL link establishment process.  The
               ''Showtime'' statistics are those collected since
               the most recent establishment of the DSL link.
            
               Note: {{param}} SHOULD NOT be reset when the
               interface statistics are reset via an interface
               disable / enable cycle.";
          }
          leaf LastShowtimeStart {
            type uint32;
            description
              "DSL-specific statistic.  The Number of {{units}}
               since the second most recent DSL Showtime-the
               beginning of the period used for collection of
               {{object|LastShowtime}} statistics.
            
               If the CPE has not retained information about the
               second most recent Showtime (e.g., on reboot), the
               start of ''LastShowtime'' statistics MAY
               temporarily coincide with the start of
               ''Showtime'' statistics.
            
               Note: {{param}} SHOULD NOT be reset when the
               interface statistics are reset via an interface
               disable / enable cycle.";
          }
          leaf CurrentDayStart {
            type uint32;
            description
              "DSL-specific statistic.  The Number of {{units}}
               since the beginning of the period used for
               collection of {{object|CurrentDay}} statistics.
            
               The CPE MAY align the beginning of each
               ''CurrentDay'' interval with days in the UTC time
               zone, but is not required to do so.
            
               Statistics SHOULD continue to be accumulated
               across CPE reboots, though this might not always
               be possible.
            
               Note: {{param}} SHOULD NOT be reset when the
               interface statistics are reset via an interface
               disable / enable cycle.";
          }
          leaf QuarterHourStart {
            type uint32;
            description
              "DSL-specific statistic.  The Number of {{units}}
               since the beginning of the period used for
               collection of {{object|QuarterHour}} statistics.
            
               The CPE MAY align the beginning of each
               ''QuarterHour'' interval with real-time
               quarter-hour intervals, but is not required to do
               so.
            
               Statistics SHOULD continue to be accumulated
               across CPE reboots, though this might not always
               be possible.
            
               Note: {{param}} SHOULD NOT be reset when the
               interface statistics are reset via an interface
               disable / enable cycle.";
          }

          container Total {
            description
              "This object contains DSL channel total statistics
               {{bibref|G.997.1}}.
            
               Note: The {{object}} parameters SHOULD NOT be
               reset when the interface statistics are reset via
               an interface disable / enable cycle.";
            leaf XTURFECErrors {
              type uint32;
              description
                "Total number of FEC errors detected (FEC-C as
                 defined in ITU-T Rec.  {{bibref|G.997.1}}).
              
                 Note: If the parameter is implemented but no
                 value is available, its value MUST be 4294967295
                 (the maximum for its data type).";
            }
            leaf XTUCFECErrors {
              type uint32;
              description
                "Total number of FEC errors detected by the ATU-C
                 (FEC-CFE as defined in ITU-T Rec.
                 {{bibref|G.997.1}}).
              
                 Note: If the parameter is implemented but no
                 value is available, its value MUST be 4294967295
                 (the maximum for its data type).";
            }
            leaf XTURHECErrors {
              type uint32;
              description
                "Total number of HEC errors detected (HEC-P as
                 defined in ITU-T Rec.  {{bibref|G.997.1}}).
              
                 Note: If the parameter is implemented but no
                 value is available, its value MUST be 4294967295
                 (the maximum for its data type).";
            }
            leaf XTUCHECErrors {
              type uint32;
              description
                "Total number of HEC errors detected by the ATU-C
                 (HEC-PFE as defined in ITU-T Rec.
                 {{bibref|G.997.1}}).
              
                 Note: If the parameter is implemented but no
                 value is available, its value MUST be 4294967295
                 (the maximum for its data type).";
            }
            leaf XTURCRCErrors {
              type uint32;
              description
                "Total number of CRC errors detected (CV-C as
                 defined in ITU-T Rec.  {{bibref|G.997.1}}).
              
                 Note: If the parameter is implemented but no
                 value is available, its value MUST be 4294967295
                 (the maximum for its data type).";
            }
            leaf XTUCCRCErrors {
              type uint32;
              description
                "Total number of CRC errors detected by the ATU-C
                 (CV-CFE as defined in ITU-T Rec.
                 {{bibref|G.997.1}}).
              
                 Note: If the parameter is implemented but no
                 value is available, its value MUST be 4294967295
                 (the maximum for its data type).";
            }
          }

          container Showtime {
            description
              "This object contains DSL channel statistics
               accumulated since the most recent DSL Showtime
               {{bibref|G.997.1}}.
            
               Note: The {{object}} parameters SHOULD NOT be
               reset when the interface statistics are reset via
               an interface disable / enable cycle.";
            leaf XTURFECErrors {
              type uint32;
              description
                "Number of FEC errors detected since the most recent
                 DSL Showtime (FEC-C as defined in ITU-T Rec.
                 {{bibref|G.997.1}}).
              
                 Note: If the parameter is implemented but no
                 value is available, its value MUST be 4294967295
                 (the maximum for its data type).";
            }
            leaf XTUCFECErrors {
              type uint32;
              description
                "Number of FEC errors detected by the ATU-C since
                 the most recent DSL Showtime (FEC-CFE as defined
                 in ITU-T Rec.  {{bibref|G.997.1}}).
              
                 Note: If the parameter is implemented but no
                 value is available, its value MUST be 4294967295
                 (the maximum for its data type).";
            }
            leaf XTURHECErrors {
              type uint32;
              description
                "Number of HEC errors detected since the most recent
                 DSL Showtime (HEC-P as defined in ITU-T Rec.
                 {{bibref|G.997.1}}).
              
                 Note: If the parameter is implemented but no
                 value is available, its value MUST be 4294967295
                 (the maximum for its data type).";
            }
            leaf XTUCHECErrors {
              type uint32;
              description
                "Number of HEC errors detected by the ATU-C since
                 the most recent DSL Showtime (HEC-PFE as defined
                 in ITU-T Rec.  {{bibref|G.997.1}}).
              
                 Note: If the parameter is implemented but no
                 value is available, its value MUST be 4294967295
                 (the maximum for its data type).";
            }
            leaf XTURCRCErrors {
              type uint32;
              description
                "Number of CRC errors detected since the most recent
                 DSL Showtime (CV-C as defined in ITU-T Rec.
                 {{bibref|G.997.1}}).
              
                 Note: If the parameter is implemented but no
                 value is available, its value MUST be 4294967295
                 (the maximum for its data type).";
            }
            leaf XTUCCRCErrors {
              type uint32;
              description
                "Number of CRC errors detected by the ATU-C since
                 the most recent DSL Showtime (CV-CFE as defined
                 in ITU-T Rec.  {{bibref|G.997.1}}).
              
                 Note: If the parameter is implemented but no
                 value is available, its value MUST be 4294967295
                 (the maximum for its data type).";
            }
          }

          container LastShowtime {
            description
              "This object contains DSL channel statistics
               accumulated since the second most recent DSL
               Showtime {{bibref|G.997.1}}.
            
               Note: The {{object}} parameters SHOULD NOT be
               reset when the interface statistics are reset via
               an interface disable / enable cycle.";
            leaf XTURFECErrors {
              type uint32;
              description
                "Number of FEC errors detected since the second most
                 recent DSL Showtime (FEC-C as defined in ITU-T
                 Rec.  {{bibref|G.997.1}}).
              
                 Note: If the parameter is implemented but no
                 value is available, its value MUST be 4294967295
                 (the maximum for its data type).";
            }
            leaf XTUCFECErrors {
              type uint32;
              description
                "Number of FEC errors detected by the ATU-C since
                 the second most recent DSL Showtime (FEC-CFE as
                 defined in ITU-T Rec.  {{bibref|G.997.1}}).
              
                 Note: If the parameter is implemented but no
                 value is available, its value MUST be 4294967295
                 (the maximum for its data type).";
            }
            leaf XTURHECErrors {
              type uint32;
              description
                "Number of HEC errors detected since the second most
                 recent DSL Showtime (HEC-P as defined in ITU-T
                 Rec.  {{bibref|G.997.1}}).
              
                 Note: If the parameter is implemented but no
                 value is available, its value MUST be 4294967295
                 (the maximum for its data type).";
            }
            leaf XTUCHECErrors {
              type uint32;
              description
                "Number of HEC errors detected by the ATU-C since
                 the second most recent DSL Showtime (HEC-PFE as
                 defined in ITU-T Rec.  {{bibref|G.997.1}}).
              
                 Note: If the parameter is implemented but no
                 value is available, its value MUST be 4294967295
                 (the maximum for its data type).";
            }
            leaf XTURCRCErrors {
              type uint32;
              description
                "Number of CRC errors detected since the second most
                 recent DSL Showtime (CV-C as defined in ITU-T
                 Rec.  {{bibref|G.997.1}}).
              
                 Note: If the parameter is implemented but no
                 value is available, its value MUST be 4294967295
                 (the maximum for its data type).";
            }
            leaf XTUCCRCErrors {
              type uint32;
              description
                "Number of CRC errors detected by the ATU-C since
                 the second most recent DSL Showtime (CV-CFE as
                 defined in ITU-T Rec.  {{bibref|G.997.1}}).
              
                 Note: If the parameter is implemented but no
                 value is available, its value MUST be 4294967295
                 (the maximum for its data type).";
            }
          }

          container CurrentDay {
            description
              "This object contains DSL channel statistics
               accumulated during the current day
               {{bibref|G.997.1}}.
            
               Note: The {{object}} parameters SHOULD NOT be
               reset when the interface statistics are reset via
               an interface disable / enable cycle.";
            leaf XTURFECErrors {
              type uint32;
              description
                "Number of FEC errors detected since the second most
                 recent DSL Showtime (FEC-C as defined in ITU-T
                 Rec.  {{bibref|G.997.1}}).
              
                 Note: If the parameter is implemented but no
                 value is available, its value MUST be 4294967295
                 (the maximum for its data type).";
            }
            leaf XTUCFECErrors {
              type uint32;
              description
                "Number of FEC errors detected by the ATU-C since
                 the second most recent DSL Showtime (FEC-CFE as
                 defined in ITU-T Rec.  {{bibref|G.997.1}}).
              
                 Note: If the parameter is implemented but no
                 value is available, its value MUST be 4294967295
                 (the maximum for its data type).";
            }
            leaf XTURHECErrors {
              type uint32;
              description
                "Number of HEC errors detected since the second most
                 recent DSL Showtime (HEC-P as defined in ITU-T
                 Rec.  {{bibref|G.997.1}}).
              
                 Note: If the parameter is implemented but no
                 value is available, its value MUST be 4294967295
                 (the maximum for its data type).";
            }
            leaf XTUCHECErrors {
              type uint32;
              description
                "Number of HEC errors detected by the ATU-C since
                 the second most recent DSL Showtime (HEC-PFE as
                 defined in ITU-T Rec.  {{bibref|G.997.1}}).
              
                 Note: If the parameter is implemented but no
                 value is available, its value MUST be 4294967295
                 (the maximum for its data type).";
            }
            leaf XTURCRCErrors {
              type uint32;
              description
                "Number of CRC errors detected since the second most
                 recent DSL Showtime (CV-C as defined in ITU-T
                 Rec.  {{bibref|G.997.1}}).
              
                 Note: If the parameter is implemented but no
                 value is available, its value MUST be 4294967295
                 (the maximum for its data type).";
            }
            leaf XTUCCRCErrors {
              type uint32;
              description
                "Number of CRC errors detected by the ATU-C since
                 the second most recent DSL Showtime (CV-CFE as
                 defined in ITU-T Rec.  {{bibref|G.997.1}}).
              
                 Note: If the parameter is implemented but no
                 value is available, its value MUST be 4294967295
                 (the maximum for its data type).";
            }
          }

          container QuarterHour {
            description
              "This object contains DSL channel statistics
               accumulated during the current quarter hour
               {{bibref|G.997.1}}.
            
               Note: The {{object}} parameters SHOULD NOT be
               reset when the interface statistics are reset via
               an interface disable / enable cycle.";
            leaf XTURFECErrors {
              type uint32;
              description
                "Number of FEC errors detected since the second most
                 recent DSL Showtime (FEC-C as defined in ITU-T
                 Rec.  {{bibref|G.997.1}}).
              
                 Note: If the parameter is implemented but no
                 value is available, its value MUST be 4294967295
                 (the maximum for its data type).";
            }
            leaf XTUCFECErrors {
              type uint32;
              description
                "Number of FEC errors detected by the ATU-C since
                 the second most recent DSL Showtime (FEC-CFE as
                 defined in ITU-T Rec.  {{bibref|G.997.1}}).
              
                 Note: If the parameter is implemented but no
                 value is available, its value MUST be 4294967295
                 (the maximum for its data type).";
            }
            leaf XTURHECErrors {
              type uint32;
              description
                "Number of HEC errors detected since the second most
                 recent DSL Showtime (HEC-P as defined in ITU-T
                 Rec.  {{bibref|G.997.1}}).
              
                 Note: If the parameter is implemented but no
                 value is available, its value MUST be 4294967295
                 (the maximum for its data type).";
            }
            leaf XTUCHECErrors {
              type uint32;
              description
                "Number of HEC errors detected by the ATU-C since
                 the second most recent DSL Showtime (HEC-PFE as
                 defined in ITU-T Rec.  {{bibref|G.997.1}}).
              
                 Note: If the parameter is implemented but no
                 value is available, its value MUST be 4294967295
                 (the maximum for its data type).";
            }
            leaf XTURCRCErrors {
              type uint32;
              description
                "Number of CRC errors detected since the second most
                 recent DSL Showtime (CV-C as defined in ITU-T
                 Rec.  {{bibref|G.997.1}}).
              
                 Note: If the parameter is implemented but no
                 value is available, its value MUST be 4294967295
                 (the maximum for its data type).";
            }
            leaf XTUCCRCErrors {
              type uint32;
              description
                "Number of CRC errors detected by the ATU-C since
                 the second most recent DSL Showtime (CV-CFE as
                 defined in ITU-T Rec.  {{bibref|G.997.1}}).
              
                 Note: If the parameter is implemented but no
                 value is available, its value MUST be 4294967295
                 (the maximum for its data type).";
            }
          }
        }
      }

      list BondingGroup {
        key "GroupID";
        description
          "DSL bonding group table (a stackable interface object as
           described in {{bibref|TR-181i2|Section 4.2}}).  Each
           instance is a bonding group, and is expected to be
           stacked above a {{object|#.Channel}} instance for each
           bonded channel in the group.
        
           Many of the parameters within this object, including
           {{param|LowerLayers}}, are read-only because bonding
           is not expected to be configured via
           {{bibref|TR-069}}.
        
           The DSL bonding data model is closely aligned with
           {{bibref|TR-159}}.  Corresponds to {{bibref|TR-159}}
           ''oBondingGroup''.";
        leaf Enable {
          type boolean;
          description
            "Enables or disables the bonding group.
          
             This parameter is based on ''ifAdminStatus'' from
             {{bibref|RFC2863}}.";
        }
        leaf Status {
          type enumeration {
            enum "Up";
            enum "Down";
            enum "Unknown";
            enum "Dormant";
            enum "NotPresent";
            enum "LowerLayerDown";
            enum "Error";
          }
          config false;
          description
            "The current operational state of the bonding group (see
             {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the bonding group as assigned by
             the CPE.";
        }
        leaf LastChange {
          type uint32;
          config false;
          description
            "The accumulated time in {{units}} since the bonding
             group entered its current operational state.";
        }
        leaf LowerLayers {
          type string;
          config false;
          description
            "{{list}} {{reference|an interface object that is
             stacked immediately below this interface object}}
             See {{bibref|TR-181i2|Section 4.2.1}}.
          
             {{param}} is read-only for this object because
             bonding is expected to be configured by the CPE, not
             by the ACS.";
        }
        leaf GroupStatus {
          type enumeration {
            enum "NoPeer";
            enum "PeerPowerLoss";
            enum "PeerBondSchemeMismatch";
            enum "LowRate";
          }
          config false;
          description
            "{{list}} Indicates the current fault status of the DSL
             bonding group.  {{enum}}
          
             Corresponds to {{bibref|TR-159}}
             ''oBondingGroup.aGroupStatus''.";
        }
        leaf GroupID {
          type uint32;
          config false;
          description
            "DSL bonding group ID.  Corresponds to {{bibref|TR-159}}
             ''oBondingGroup.aGroupID''.";
        }
        leaf BondSchemesSupported {
          type enumeration {
            enum "ATM";
            enum "Ethernet";
            enum "TDIM";
          }
          config false;
          description
            "{{list}} Supported DSL bonding schemes.  {{enum}}
          
             Corresponds to {{bibref|TR-159}}
             ''oBondingGroup.aGroupBondSchemesSupported''.";
        }
        leaf BondScheme {
          type string;
          config false;
          description
            "Currently operating bonding scheme.  Corresponds to
             {{bibref|TR-159}} ''aGroupOperBondScheme''.";
        }
        leaf GroupCapacity {
          type uint32 {
            range "1..32";
          }
          config false;
          description
            "DSL bonding group capacity, i.e.  the maximum number of
             channels that can be bonded in this group.
             Corresponds to {{bibref|TR-159}}
             ''oBondingGroup.aGroupCapacity''.";
        }
        leaf RunningTime {
          type uint32;
          config false;
          description
            "The accumulated time in {{units}} for which this
             bonding group has been operationally up.
             Corresponds to {{bibref|G.998.1|section 11.4.2}}
             ''Group Running Time''.";
        }
        leaf TargetUpRate {
          type uint32;
          config false;
          description
            "Desired upstream data rate in {{units}} for this DSL
             bonding group (zero indicates best effort).
             Corresponds to {{bibref|TR-159}}
             ''oBondingGroup.aGroupTargetUpRate''.";
        }
        leaf TargetDownRate {
          type uint32;
          config false;
          description
            "Desired downstream data rate in {{units}} for DSL
             bonding group (zero indicates best effort).
             Corresponds to {{bibref|TR-159}}
             ''oBondingGroup.aGroupTargetDownRate''.";
        }
        leaf ThreshLowUpRate {
          type uint32;
          config false;
          description
            "Threshold upstream data rate in {{units}} for this DSL
             bonding group.  {{param|GroupStatus}} will include
             {{enum|LowRate|GroupStatus}} whenever the upstream
             rate is less than this threshold.  Corresponds to
             {{bibref|TR-159}}
             ''oBondingGroup.aGroupThreshLowUpRate''.";
        }
        leaf ThreshLowDownRate {
          type uint32;
          config false;
          description
            "Threshold downstream data rate in {{units}} for this
             DSL bonding group.  {{param|GroupStatus}} will
             include {{enum|LowRate|GroupStatus}} whenever the
             downstream rate is less than this threshold.
             Corresponds to {{bibref|TR-159}}
             ''oBondingGroup.aGroupThreshLowDownRate''.";
        }
        leaf UpstreamDifferentialDelayTolerance {
          type uint32;
          config false;
          description
            "The maximum upstream differential delay in {{units}}
             among member links in a bonding group.  Corresponds
             to {{bibref|G.998.1|section 11.4.1}} ''Differential
             Delay Tolerance''.";
        }
        leaf DownstreamDifferentialDelayTolerance {
          type uint32;
          config false;
          description
            "The maximum downstream differential delay in {{units}}
             among member links in a bonding group.  Corresponds
             to {{bibref|G.998.1|section 11.4.1}} ''Differential
             Delay Tolerance''.";
        }

        list BondedChannel {
          key "Channel";
          config false;
          description
            "DSL bonded channel table.  Each table entry represents
             a bonded channel within the bonding group, and is
             associated with exactly one {{object|##.Channel}}
             instance.  There MUST be an instance of {{object}}
             for each DSL channel that is bonded.
          
             When a {{object|##.Channel}} is no longer bonded,
             then the CPE MUST delete the corresponding
             {{object}} instance.  However, when a bonded
             {{object|##.Channel}} becomes disabled, the channel
             remains bonded and so the corresponding {{object}}
             instance MUST NOT be deleted.";
          leaf Channel {
            type string {
              length "0..256";
            }
            description
              "{{reference}}This is the channel that is being
               bonded.
            
               This is read-only because bonding is expected to
               be configured by the CPE, not by the ACS.";
          }

          container Ethernet {
            description
              "Per-channel {{bibref|G.998.2}} Ethernet-based bonding
               parameters.
            
               This object MUST be present if, and only if,
               {{param|##.BondScheme}} is
               {{enum|Ethernet|##.BondScheme}}.";

            container Stats {
              description
                "Per-channel {{bibref|G.998.2}} Ethernet-based
                 bonding statistics.
              
                 These relate to the {{bibref|G.998.2}} PME
                 (Physical Medium Entity) Aggregation Function
                 (PAF) lower layer (per-channel) interfaces.
              
                 The CPE MUST reset the Stats parameters either
                 when the interface becomes operationally down
                 due to a previous administrative down (i.e.  the
                 interface's {{param|###.Status}} parameter
                 transitions to a down state after the interface
                 is disabled) or when the interface becomes
                 administratively up (i.e.  the interface's
                 {{param|###.Enable}} parameter transitions from
                 {{false}} to {{true}}).  Administrative and
                 operational interface status is discussed in
                 {{bibref|TR-181i2|section 4.2.2}}.";
              leaf UnderflowErrorsSent {
                type uint32;
                description
                  "Number of underflow errors sent, i.e.  on the
                   transmit side of the interface.";
              }
              leaf CRCErrorsReceived {
                type uint32;
                description
                  "Number of CRC errors received, i.e.  on the
                   receive side of the interface.";
              }
              leaf AlignmentErrorsReceived {
                type uint32;
                description
                  "Number of alignment errors received, i.e.  on the
                   receive side of the interface.";
              }
              leaf ShortPacketsReceived {
                type uint32;
                description
                  "Number of short packets received, i.e.  on the
                   receive side of the interface.";
              }
              leaf LongPacketsReceived {
                type uint32;
                description
                  "Number of long packets received, i.e.  on the
                   receive side of the interface.";
              }
              leaf OverflowErrorsReceived {
                type uint32;
                description
                  "Number of overflow errors received, i.e.  on the
                   receive side of the interface.";
              }
              leaf PauseFramesReceived {
                type uint32;
                description
                  "Number of pause frames received, i.e.  on the
                   receive side of the interface.";
              }
              leaf FramesDropped {
                type uint32;
                description
                  "Number of frames dropped, e.g.  because the
                   receive queue is full.";
              }
            }
          }
        }

        container Stats {
          config false;
          description
            "Throughput statistics for this interface.
          
             The CPE MUST reset the interface's Stats parameters
             (unless otherwise stated in individual object or
             parameter descriptions) either when the interface
             becomes operationally down due to a previous
             administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2|section 4.2.2}}.";
          leaf BytesSent {
            type uint64;
            description
              "The total number of bytes transmitted out of the
               interface, including framing characters.";
          }
          leaf BytesReceived {
            type uint64;
            description
              "The total number of bytes received on the interface,
               including framing characters.";
          }
          leaf PacketsSent {
            type uint64;
            description
              "The total number of packets transmitted out of the
               interface.";
          }
          leaf PacketsReceived {
            type uint64;
            description
              "The total number of packets received on the
               interface.";
          }
          leaf ErrorsSent {
            type uint32;
            description
              "The total number of outbound packets that could not
               be transmitted because of errors.";
          }
          leaf ErrorsReceived {
            type uint32;
            description
              "The total number of inbound packets that contained
               errors preventing them from being delivered to a
               higher-layer protocol.";
          }
          leaf UnicastPacketsSent {
            type uint64;
            description
              "The total number of packets requested for
               transmission which were not addressed to a
               multicast or broadcast address at this layer,
               including those that were discarded or not sent.";
          }
          leaf UnicastPacketsReceived {
            type uint64;
            description
              "The total number of received packets, delivered by
               this layer to a higher layer, which were not
               addressed to a multicast or broadcast address at
               this layer.";
          }
          leaf DiscardPacketsSent {
            type uint32;
            description
              "The total number of outbound packets which were
               chosen to be discarded even though no errors had
               been detected to prevent their being transmitted.
               One possible reason for discarding such a packet
               could be to free up buffer space.";
          }
          leaf DiscardPacketsReceived {
            type uint32;
            description
              "The total number of inbound packets which were chosen
               to be discarded even though no errors had been
               detected to prevent their being delivered.  One
               possible reason for discarding such a packet could
               be to free up buffer space.";
          }
          leaf MulticastPacketsSent {
            type uint64;
            description
              "The total number of packets that higher-level
               protocols requested for transmission and which
               were addressed to a multicast address at this
               layer, including those that were discarded or not
               sent.";
          }
          leaf MulticastPacketsReceived {
            type uint64;
            description
              "The total number of received packets, delivered by
               this layer to a higher layer, which were addressed
               to a multicast address at this layer.";
          }
          leaf BroadcastPacketsSent {
            type uint64;
            description
              "The total number of packets that higher-level
               protocols requested for transmission and which
               were addressed to a broadcast address at this
               layer, including those that were discarded or not
               sent.";
          }
          leaf BroadcastPacketsReceived {
            type uint64;
            description
              "The total number of received packets, delivered by
               this layer to a higher layer, which were addressed
               to a broadcast address at this layer.";
          }
          leaf UnknownProtoPacketsReceived {
            type uint32;
            description
              "The total number of packets received via the
               interface which were discarded because of an
               unknown or unsupported protocol.";
          }
          leaf TotalStart {
            type uint32;
            description
              "DSL-specific statistic.  The Number of {{units}}
               since the beginning of the period used for
               collection of {{object|Total}} statistics.
            
               Statistics SHOULD continue to be accumulated
               across CPE reboots, though this might not always
               be possible.
            
               Note: {{param}} SHOULD NOT be reset when the
               interface statistics are reset via an interface
               disable / enable cycle.";
          }
          leaf CurrentDayStart {
            type uint32;
            description
              "DSL-specific statistic.  The Number of {{units}}
               since the beginning of the period used for
               collection of {{object|CurrentDay}} statistics.
            
               The CPE MAY align the beginning of each CurrentDay
               interval with days in the UTC time zone, but is
               not required to do so.
            
               Statistics SHOULD continue to be accumulated
               across CPE reboots, though this might not always
               be possible.
            
               Note: {{param}} SHOULD NOT be reset when the
               interface statistics are reset via an interface
               disable / enable cycle.";
          }
          leaf QuarterHourStart {
            type uint32;
            description
              "DSL-specific statistic.  The Number of {{units}}
               since the beginning of the period used for
               collection of {{object|QuarterHour}} statistics.
            
               The CPE MAY align the beginning of each
               QuarterHour interval with real-time quarter-hour
               intervals, but is not required to do so.
            
               Statistics SHOULD continue to be accumulated
               across CPE reboots, though this might not always
               be possible.
            
               Note: {{param}} SHOULD NOT be reset when the
               interface statistics are reset via an interface
               disable / enable cycle.";
          }

          container Total {
            description
              "Total statistics for this bonding group.
            
               Note: The {{object}} parameters SHOULD NOT be
               reset when the interface statistics are reset via
               an interface disable / enable cycle.";
            leaf FailureReasons {
              type enumeration {
                enum "LowRate";
                enum "ExcessiveDelay";
                enum "InsufficientBuffers";
                enum "Other";
              }
              description
                "{{list}} Indicates the failure conditions that have
                 occurred during the accumulation period.
                 {{enum}}
              
                 Corresponds to {{bibref|G.998.1|section 11.4.3}}
                 ''Current Group Failure Reason''.";
            }
            leaf UpstreamRate {
              type uint32;
              description
                "The achieved upstream data rate in {{units}} (which
                 might change subject to dynamic link usage
                 conditions).  Corresponds to
                 {{bibref|G.998.1|section 11.4.2}} ''Achieved
                 Aggregate Data Rate''.";
            }
            leaf DownstreamRate {
              type uint32;
              description
                "The achieved downstream data rate in {{units}}
                 (which might change subject to dynamic link
                 usage conditions).  Corresponds to
                 {{bibref|G.998.1|section 11.4.2}} ''Achieved
                 Aggregate Data Rate''.";
            }
            leaf UpstreamPacketLoss {
              type uint32;
              description
                "The total number of upstream packets that were lost
                 at aggregation output from a bonding group
                 during the accumulation period.  Corresponds to
                 {{bibref|G.998.1|section 11.4.2}} ''Group Rx
                 Cell Loss Count''.";
            }
            leaf DownstreamPacketLoss {
              type uint32;
              description
                "The total number of downstream packets that were
                 lost at aggregation output from a bonding group
                 during the accumulation period.  Corresponds to
                 {{bibref|G.998.1|section 11.4.2}} ''Group Rx
                 Cell Loss Count''.";
            }
            leaf UpstreamDifferentialDelay {
              type uint32;
              description
                "The achieved upstream differential delay in
                 {{units}} (which might change subject to dynamic
                 link usage conditions).";
            }
            leaf DownstreamDifferentialDelay {
              type uint32;
              description
                "The achieved downstream differential delay in
                 {{units}} (which might change subject to dynamic
                 link usage conditions).";
            }
            leaf FailureCount {
              type uint32;
              description
                "The number of times that the group was declared
                 ''Unavailable'' during the accumulation period.
                 Corresponds to {{bibref|G.998.1|Section 11.4.3}}
                 ''Group Failure Count''.";
            }
            leaf ErroredSeconds {
              type uint32;
              description
                "The time in {{units}} during which the group was
                 declared ''Errored'' during the accumulation
                 period.  Corresponds to {{bibref|TR-159}}
                 ''oBondingGroup.aGroupPerf**ES''.";
            }
            leaf SeverelyErroredSeconds {
              type uint32;
              description
                "The time in {{units}} during which the group was
                 declared ''SeverelyErrored'' during the
                 accumulation period.  Corresponds to
                 {{bibref|TR-159}}
                 ''oBondingGroup.aGroupPerf**SES''.";
            }
            leaf UnavailableSeconds {
              type uint32;
              description
                "The time in {{units}} during which the group was
                 declared ''Unavailable'' during the accumulation
                 period.  Corresponds to {{bibref|TR-159}}
                 ''oBondingGroup.aGroupPerf**UAS''.";
            }
          }

          container CurrentDay {
            description
              "Current day statistics for this bonding group.
            
               Note: The {{object}} parameters SHOULD NOT be
               reset when the interface statistics are reset via
               an interface disable / enable cycle.";
            leaf FailureReasons {
              type enumeration {
                enum "LowRate";
                enum "ExcessiveDelay";
                enum "InsufficientBuffers";
                enum "Other";
              }
              description
                "{{list}} Indicates the failure conditions that have
                 occurred during the accumulation period.
                 {{enum}}
              
                 Corresponds to {{bibref|G.998.1|section 11.4.3}}
                 ''Current Group Failure Reason''.";
            }
            leaf UpstreamRate {
              type uint32;
              description
                "The achieved upstream data rate in {{units}} (which
                 might change subject to dynamic link usage
                 conditions).  Corresponds to
                 {{bibref|G.998.1|section 11.4.2}} ''Achieved
                 Aggregate Data Rate''.";
            }
            leaf DownstreamRate {
              type uint32;
              description
                "The achieved downstream data rate in {{units}}
                 (which might change subject to dynamic link
                 usage conditions).  Corresponds to
                 {{bibref|G.998.1|section 11.4.2}} ''Achieved
                 Aggregate Data Rate''.";
            }
            leaf UpstreamPacketLoss {
              type uint32;
              description
                "The total number of upstream packets that were lost
                 at aggregation output from a bonding group
                 during the accumulation period.  Corresponds to
                 {{bibref|G.998.1|section 11.4.2}} ''Group Rx
                 Cell Loss Count''.";
            }
            leaf DownstreamPacketLoss {
              type uint32;
              description
                "The total number of downstream packets that were
                 lost at aggregation output from a bonding group
                 during the accumulation period.  Corresponds to
                 {{bibref|G.998.1|section 11.4.2}} ''Group Rx
                 Cell Loss Count''.";
            }
            leaf UpstreamDifferentialDelay {
              type uint32;
              description
                "The achieved upstream differential delay in
                 {{units}} (which might change subject to dynamic
                 link usage conditions).";
            }
            leaf DownstreamDifferentialDelay {
              type uint32;
              description
                "The achieved downstream differential delay in
                 {{units}} (which might change subject to dynamic
                 link usage conditions).";
            }
            leaf FailureCount {
              type uint32;
              description
                "The number of times that the group was declared
                 ''Unavailable'' during the accumulation period.
                 Corresponds to {{bibref|G.998.1|Section 11.4.3}}
                 ''Group Failure Count''.";
            }
            leaf ErroredSeconds {
              type uint32;
              description
                "The time in {{units}} during which the group was
                 declared ''Errored'' during the accumulation
                 period.  Corresponds to {{bibref|TR-159}}
                 ''oBondingGroup.aGroupPerf**ES''.";
            }
            leaf SeverelyErroredSeconds {
              type uint32;
              description
                "The time in {{units}} during which the group was
                 declared ''SeverelyErrored'' during the
                 accumulation period.  Corresponds to
                 {{bibref|TR-159}}
                 ''oBondingGroup.aGroupPerf**SES''.";
            }
            leaf UnavailableSeconds {
              type uint32;
              description
                "The time in {{units}} during which the group was
                 declared ''Unavailable'' during the accumulation
                 period.  Corresponds to {{bibref|TR-159}}
                 ''oBondingGroup.aGroupPerf**UAS''.";
            }
          }

          container QuarterHour {
            description
              "Current quarter hour statistics for this bonding
               group.
            
               Note: The {{object}} parameters SHOULD NOT be
               reset when the interface statistics are reset via
               an interface disable / enable cycle.";
            leaf FailureReasons {
              type enumeration {
                enum "LowRate";
                enum "ExcessiveDelay";
                enum "InsufficientBuffers";
                enum "Other";
              }
              description
                "{{list}} Indicates the failure conditions that have
                 occurred during the accumulation period.
                 {{enum}}
              
                 Corresponds to {{bibref|G.998.1|section 11.4.3}}
                 ''Current Group Failure Reason''.";
            }
            leaf UpstreamRate {
              type uint32;
              description
                "The achieved upstream data rate in {{units}} (which
                 might change subject to dynamic link usage
                 conditions).  Corresponds to
                 {{bibref|G.998.1|section 11.4.2}} ''Achieved
                 Aggregate Data Rate''.";
            }
            leaf DownstreamRate {
              type uint32;
              description
                "The achieved downstream data rate in {{units}}
                 (which might change subject to dynamic link
                 usage conditions).  Corresponds to
                 {{bibref|G.998.1|section 11.4.2}} ''Achieved
                 Aggregate Data Rate''.";
            }
            leaf UpstreamPacketLoss {
              type uint32;
              description
                "The total number of upstream packets that were lost
                 at aggregation output from a bonding group
                 during the accumulation period.  Corresponds to
                 {{bibref|G.998.1|section 11.4.2}} ''Group Rx
                 Cell Loss Count''.";
            }
            leaf DownstreamPacketLoss {
              type uint32;
              description
                "The total number of downstream packets that were
                 lost at aggregation output from a bonding group
                 during the accumulation period.  Corresponds to
                 {{bibref|G.998.1|section 11.4.2}} ''Group Rx
                 Cell Loss Count''.";
            }
            leaf UpstreamDifferentialDelay {
              type uint32;
              description
                "The achieved upstream differential delay in
                 {{units}} (which might change subject to dynamic
                 link usage conditions).";
            }
            leaf DownstreamDifferentialDelay {
              type uint32;
              description
                "The achieved downstream differential delay in
                 {{units}} (which might change subject to dynamic
                 link usage conditions).";
            }
            leaf FailureCount {
              type uint32;
              description
                "The number of times that the group was declared
                 ''Unavailable'' during the accumulation period.
                 Corresponds to {{bibref|G.998.1|Section 11.4.3}}
                 ''Group Failure Count''.";
            }
            leaf ErroredSeconds {
              type uint32;
              description
                "The time in {{units}} during which the group was
                 declared ''Errored'' during the accumulation
                 period.  Corresponds to {{bibref|TR-159}}
                 ''oBondingGroup.aGroupPerf**ES''.";
            }
            leaf SeverelyErroredSeconds {
              type uint32;
              description
                "The time in {{units}} during which the group was
                 declared ''SeverelyErrored'' during the
                 accumulation period.  Corresponds to
                 {{bibref|TR-159}}
                 ''oBondingGroup.aGroupPerf**SES''.";
            }
            leaf UnavailableSeconds {
              type uint32;
              description
                "The time in {{units}} during which the group was
                 declared ''Unavailable'' during the accumulation
                 period.  Corresponds to {{bibref|TR-159}}
                 ''oBondingGroup.aGroupPerf**UAS''.";
            }
          }
        }

        container Ethernet {
          config false;
          description
            "Ethernet-based bonding parameters {{bibref|G.998.2}}.
          
             This object MUST be present if, and only if,
             {{param|#.BondScheme}} is
             {{enum|Ethernet|#.BondScheme}}.";

          container Stats {
            description
              "{{bibref|G.998.2}} Ethernet-based bonding statistics.
            
               These relate to the {{bibref|G.998.2}} PME
               (Physical Medium Entity) Aggregation Function
               (PAF) and to its upper layer interface.  PAF lower
               layer interface statistics are in the
               {{object|##.BondedChannel.{i}.Ethernet.Stats}}
               objects.
            
               The CPE MUST reset the Stats parameters either
               when the interface becomes operationally down due
               to a previous administrative down (i.e.  the
               interface's {{param|##.Status}} parameter
               transitions to a down state after the interface is
               disabled) or when the interface becomes
               administratively up (i.e.  the interface's
               {{param|##.Enable}} parameter transitions from
               {{false}} to {{true}}).  Administrative and
               operational interface status is discussed in
               {{bibref|TR-181i2|section 4.2.2}}.";
            leaf PAFErrors {
              type uint32;
              description
                "Number of PAF errors.  Corresponds to
                 {{bibref|TR-159}} ''oBondETH.aEthRxErrors''.";
            }
            leaf PAFSmallFragments {
              type uint32;
              description
                "Number of PAF Small Fragment events.  Corresponds
                 to {{bibref|TR-159}}
                 ''oBondETH.aEthRxSmallFragments''.";
            }
            leaf PAFLargeFragments {
              type uint32;
              description
                "Number of PAF Large Fragment events.  Corresponds
                 to {{bibref|TR-159}}
                 ''oBondETH.aEthRxLargeFragments''.";
            }
            leaf PAFBadFragments {
              type uint32;
              description
                "Number of PAF Bad Fragment events.  Corresponds to
                 {{bibref|TR-159}}
                 ''oBondETH.aEthRxBadFragments''.";
            }
            leaf PAFLostFragments {
              type uint32;
              description
                "Number of PAF Lost Fragment events.  Corresponds to
                 {{bibref|TR-159}}
                 ''oBondETH.aEthRxLostFragments''.";
            }
            leaf PAFLateFragments {
              type uint32;
              description
                "Number of PAF Late Fragment events.";
            }
            leaf PAFLostStarts {
              type uint32;
              description
                "Number of PAF Lost Start events.  Corresponds to
                 {{bibref|TR-159}} ''oBondETH.aEthRxLostStarts''.";
            }
            leaf PAFLostEnds {
              type uint32;
              description
                "Number of PAF Lost End events.  Corresponds to
                 {{bibref|TR-159}} ''oBondETH.aEthRxLostEnds''.";
            }
            leaf PAFOverflows {
              type uint32;
              description
                "Number of PAF Overflow events.  Corresponds to
                 {{bibref|TR-159}} ''oBondETH.aEthRxOverflows''.";
            }
            leaf PauseFramesSent {
              type uint32;
              description
                "Number of pause frames sent, i.e.  on the transmit
                 side of the interface.";
            }
            leaf CRCErrorsReceived {
              type uint32;
              description
                "Number of CRC errors received, i.e.  on the receive
                 side of the interface.";
            }
            leaf AlignmentErrorsReceived {
              type uint32;
              description
                "Number of alignment errors received, i.e.  on the
                 receive side of the interface.";
            }
            leaf ShortPacketsReceived {
              type uint32;
              description
                "Number of short packets received, i.e.  on the
                 receive side of the interface.";
            }
            leaf LongPacketsReceived {
              type uint32;
              description
                "Number of long packets received, i.e.  on the
                 receive side of the interface.";
            }
            leaf OverflowErrorsReceived {
              type uint32;
              description
                "Number of overflow errors received, i.e.  on the
                 receive side of the interface.";
            }
            leaf FramesDropped {
              type uint32;
              description
                "Number of frames dropped, e.g.  because the receive
                 queue is full.";
            }
          }
        }
      }

      container Diagnostics {
        description
          "The DSL Diagnostics object.";

        container ADSLLineTest {
          description
            "This object is to provide diagnostic information for a
             CPE with an ADSL2 or ADSL2+ modem WAN interface, but
             MAY also be used for ADSL.";
          leaf DiagnosticsState {
            type enumeration {
              enum "None";
              enum "Requested";
              enum "Canceled";
              enum "Complete";
              enum "Error";
              enum "Error_Internal";
              enum "Error_Other";
            }
            description
              "{{issue|A10-DIAG|No error state in original version}}
            
               {{datatype|expand}}";
          }
          leaf Interface {
            type string {
              length "0..256";
            }
            description
              "{{reference}} This is the interface over which the
               test is to be performed.";
          }
          leaf ACTPSDds {
            type int32;
            config false;
            description
              "Downstream actual power spectral density.
               Interpretation of the value is as defined in ITU-T
               Rec.  G.997.1.
            
               Note: See ITU-T Recommendation {{bibref|G.997.1}}.";
          }
          leaf ACTPSDus {
            type int32;
            config false;
            description
              "Upstream actual power spectral density.
               Interpretation of the value is as defined in ITU-T
               Rec.  G.997.1.
            
               Note: See ITU-T Recommendation {{bibref|G.997.1}}.";
          }
          leaf ACTATPds {
            type int32;
            config false;
            description
              "Downstream actual aggregate transmitter power.
               Interpretation of the value is as defined in ITU-T
               Rec.  G.997.1.
            
               Note: See ITU-T Recommendation {{bibref|G.997.1}}.";
          }
          leaf ACTATPus {
            type int32;
            config false;
            description
              "Upstream actual aggregate transmitter power.
               Interpretation of the value is as defined in ITU-T
               Rec.  G.997.1.
            
               Note: See ITU-T Recommendation {{bibref|G.997.1}}.";
          }
          leaf HLINSCds {
            type int32;
            config false;
            description
              "Downstream linear representation scale.
               Interpretation of the value is as defined in ITU-T
               Rec.  G.997.1.
            
               Note: See ITU-T Recommendation {{bibref|G.997.1}}.
               For a multimode device operating in a mode in
               which this parameter does not apply, the value of
               this parameter SHOULD be set to 0.";
          }
          leaf HLINSCus {
            type int32;
            config false;
            description
              "Scaling used to represent the upstream linear channel
               characteristics.  Interpretation of the value is
               as defined in ITU-T Rec.  G.997.1.
            
               Note: See ITU-T Recommendation {{bibref|G.997.1}}.
               For a multimode device operating in a mode in
               which this parameter does not apply, the value of
               this parameter SHOULD be set to 0.";
          }
          leaf HLINGds {
            type uint32;
            config false;
            description
              "Number of sub-carriers per sub-carrier group in the
               downstream direction for {{param|HLINpsds}}.
               Valid values are 1, 2, 4, and 8.
            
               Note: See ITU-T Recommendation {{bibref|G.997.1}}.
               For a multimode device operating in a mode in
               which this parameter does not apply, the value of
               this parameter SHOULD be set to 1.";
          }
          leaf HLINGus {
            type uint32;
            config false;
            description
              "Number of sub-carriers per sub-carrier group in the
               downstream direction for {{param|HLINpsus}}.
               Valid values are 1, 2, 4, and 8.
            
               Note: See ITU-T Recommendation {{bibref|G.997.1}}.
               For a multimode device operating in a mode in
               which this parameter does not apply, the value of
               this parameter SHOULD be set to 1.";
          }
          leaf HLOGGds {
            type uint32;
            config false;
            description
              "Number of sub-carriers per sub-carrier group in the
               downstream direction for {{param|HLOGpsds}}.
               Valid values are 1, 2, 4, and 8.
            
               Note: See ITU-T Recommendation {{bibref|G.997.1}}.
               For a multimode device operating in a mode in
               which this parameter does not apply, the value of
               this parameter SHOULD be set to 1.";
          }
          leaf HLOGGus {
            type uint32;
            config false;
            description
              "Number of sub-carriers per sub-carrier group in the
               upstream direction for {{param|HLOGpsus}}.  Valid
               values are 1, 2, 4, and 8.
            
               Note: See ITU-T Recommendation {{bibref|G.997.1}}.
               For a multimode device operating in a mode in
               which this parameter does not apply, the value of
               this parameter SHOULD be set to 1.";
          }
          leaf HLOGpsds {
            type string;
            config false;
            description
              "{{list}} List items represent downstream logarithmic
               channel characteristics per sub-carrier group.
               The maximum number of elements is 256 for G.992.3,
               and 512 for G.992.5.  For G.993.2, the number of
               elements will depend on the value of
               {{param|HLOGGds}} but will not exceed 512.
               Interpretation of the values is as defined in
               ITU-T Rec.  G.997.1.
            
               Note: See ITU-T Recommendation {{bibref|G.997.1}}.
               For a multimode device operating in a mode in
               which this parameter does not apply, the value of
               this parameter SHOULD be set to ''None''.
            
               Note: {{param}} is measured during initialization
               and is not updated during Showtime.";
          }
          leaf HLOGpsus {
            type string;
            config false;
            description
              "{{list}} List items represent upstream logarithmic
               channel characteristics per sub-carrier group.
               The maximum number of elements is 64 for G.992.3
               and G.992.5.  For G.993.2, the number of elements
               will depend on the value of {{param|HLOGGus}} but
               will not exceed 512.  Interpretation of the values
               is as defined in ITU-T Rec.  G.997.1.
            
               Note: See ITU-T Recommendation {{bibref|G.997.1}}.
               For a multimode device operating in a mode in
               which this parameter does not apply, the value of
               this parameter SHOULD be set to ''None''.
            
               Note: {{param}} is measured during initialization
               and is not updated during Showtime.";
          }
          leaf HLOGMTds {
            type uint32;
            config false;
            description
              "Indicates the number of symbols over which
               {{param|HLOGpsds}} was measured.
            
               Note: See ITU-T Recommendation {{bibref|G.997.1}}.
               For a multimode device operating in a mode in
               which this parameter does not apply, the value of
               this parameter SHOULD be set to 0.";
          }
          leaf HLOGMTus {
            type uint32;
            config false;
            description
              "Indicates the number of symbols over which
               {{param|HLOGpsus}} was measured.
            
               Note: See ITU-T Recommendation {{bibref|G.997.1}}.
               For a multimode device operating in a mode in
               which this parameter does not apply, the value of
               this parameter SHOULD be set to 0.";
          }
          leaf LATNpbds {
            type string;
            config false;
            description
              "{{list}} List items represent downstream line
               attenuation per usable band, as computed during
               initialization.  Number of elements is dependent
               on the number of downstream bands but will exceed
               one only for G.993.2.  Interpretation of {{param}}
               is as defined in ITU-T Rec.  G.997.1.
            
               Note: See ITU-T Recommendation {{bibref|G.997.1}}.";
          }
          leaf LATNpbus {
            type string;
            config false;
            description
              "{{list}} List items represent upstream line
               attenuation per usable band, as computed during
               initialization.  Number of elements is dependent
               on the number of upstream bands but will exceed
               one only for G.993.2.  Interpretation of {{param}}
               is as defined in ITU-T Rec.  G.997.1.
            
               Note: See ITU-T Recommendation {{bibref|G.997.1}}.";
          }
          leaf SATNds {
            type string;
            config false;
            description
              "{{list}} List items represent downstream signal
               attenuation per usable band, as computed during
               the L0 (i.e., Showtime) state.  Number of elements
               is dependent on the number of downstream bands but
               will exceed one only for G.993.2.  Interpretation
               of {{param}} is as defined in ITU-T Rec.  G.997.1.
            
               Note: See ITU-T Recommendation {{bibref|G.997.1}}.";
          }
          leaf SATNus {
            type string;
            config false;
            description
              "{{list}} List items represent upstream signal
               attenuation per usable band, as computed during
               the L0 (i.e., Showtime) state.  Number of elements
               is dependent on the number of downstream bands but
               will exceed one only for G.993.2.  Interpretation
               of {{param}} is as defined in ITU-T Rec.  G.997.1.
            
               Note: See ITU-T Recommendation {{bibref|G.997.1}}.";
          }
          leaf HLINpsds {
            type int32;
            config false;
            description
              "{{list}} List items represent downstream linear
               channel characteristics per subcarrier group.
               Maximum number of complex pairs is 256 for
               G.992.3, and 512 for G.992.5.  For G.993.2, the
               number of pairs will depend on the value of
               {{param|HLINGds}} but will not exceed 512.
               Interpretation of the value is as defined in ITU-T
               Rec.  G.997.1.
            
               Note: HLIN is not applicable in PLOAM for G.992.1
               or G.992.2.
            
               Note: See ITU-T Recommendation {{bibref|G.997.1}}.
               For a multimode device operating in a mode in
               which this parameter does not apply, the value of
               this parameter SHOULD be set to ''None''.";
          }
          leaf HLINpsus {
            type string;
            config false;
            description
              "{{list}} List items represent upstream linear channel
               characteristics per sub-carrier group.  Maximum
               number of complex pairs is 64 for G.992.3, and
               G.992.5.  For G.993.2, the number of pairs will
               depend on the value of {{param|HLINGus}} but will
               not exceed 512.  Interpretation of the values is
               as defined in ITU-T Rec.  G.997.1.
            
               Note: HLIN is not applicable in PLOAM for G.992.1
               or G.992.2.
            
               Note: See ITU-T Recommendation {{bibref|G.997.1}}.
               For a multimode device operating in a mode in
               which this parameter does not apply, the value of
               this parameter SHOULD be set to ''None''.";
          }
          leaf QLNGds {
            type uint32;
            config false;
            description
              "Number of sub-carriers per sub-carrier group in the
               downstream direction for {{param|QLNpsds}}.  Valid
               values are 1, 2, 4, and 8.
            
               Note: See ITU-T Recommendation {{bibref|G.997.1}}.
               For a multimode device operating in a mode in
               which this parameter does not apply, the value of
               this parameter SHOULD be set to 1.";
          }
          leaf QLNGus {
            type uint32;
            config false;
            description
              "Number of sub-carriers per sub-carrier group in the
               upstream direction for {{param|QLNpsus}}.  Valid
               values are 1, 2, 4, and 8.
            
               Note: See ITU-T Recommendation {{bibref|G.997.1}}.
               For a multimode device operating in a mode in
               which this parameter does not apply, the value of
               this parameter SHOULD be set to 1.";
          }
          leaf QLNpsds {
            type int32;
            config false;
            description
              "{{list}} List items represent downstream quiet line
               noise per subcarrier group.  Maximum number of
               elements is 256 for G.992.3, 512 for G.992.5.  For
               G.993.2, the number of elements will depend on the
               value of {{param|QLNGds}} but will not exceed 512.
               Interpretation of the value is as defined in ITU-T
               Rec.  G.997.1.
            
               Note: QLN is not applicable in PLOAM for G.992.1
               or G.992.2.
            
               Note: See ITU-T Recommendation {{bibref|G.997.1}}.
               For a multimode device operating in a mode in
               which this parameter does not apply, the value of
               this parameter SHOULD be set to ''None''.";
          }
          leaf QLNpsus {
            type string;
            config false;
            description
              "{{list}} List items represent upstream quiet line
               noise per subcarrier group.  The maximum number of
               elements is 64 for G.992.3, and G.992.5.  For
               G.993.2, the number of elements will depend on the
               value of {{param|QLNGus}} but will not exceed 512.
               Interpretation of the values is as defined in
               ITU-T Rec.  G.997.1.
            
               Note: QLN is not applicable in PLOAM for G.992.1
               or G.992.2.
            
               Note: See ITU-T Recommendation {{bibref|G.997.1}}.
               For a multimode device operating in a mode in
               which this parameter does not apply, the value of
               this parameter SHOULD be set to ''None''.";
          }
          leaf QLNMTds {
            type uint32;
            config false;
            description
              "Indicates the number of symbols over which
               {{param|QLNpsds}} was measured.
            
               Note: See ITU-T Recommendation {{bibref|G.997.1}}.
               For a multimode device operating in a mode in
               which this parameter does not apply, the value of
               this parameter SHOULD be set to 0.";
          }
          leaf QLNMTus {
            type uint32;
            config false;
            description
              "Indicates the number of symbols over which
               {{param|QLNpsus}} was measured.
            
               Note: See ITU-T Recommendation {{bibref|G.997.1}}.
               For a multimode device operating in a mode in
               which this parameter does not apply, the value of
               this parameter SHOULD be set to 0.";
          }
          leaf SNRGds {
            type uint32;
            config false;
            description
              "Number of sub-carriers per sub-carrier group in the
               downstream direction for {{param|SNRpsds}}.  Valid
               values are 1, 2, 4, and 8.
            
               Note: See ITU-T Recommendation {{bibref|G.997.1}}.
               For a multimode device operating in a mode in
               which this parameter does not apply, the value of
               this parameter SHOULD be set to 1.";
          }
          leaf SNRGus {
            type uint32;
            config false;
            description
              "Number of sub-carriers per sub-carrier group in the
               upstream direction for {{param|SNRpsus}}.  Valid
               values are 1, 2, 4, and 8.
            
               Note: See ITU-T Recommendation {{bibref|G.997.1}}.
               For a multimode device operating in a mode in
               which this parameter does not apply, the value of
               this parameter SHOULD be set to 1.";
          }
          leaf SNRpsds {
            type int32;
            config false;
            description
              "{{list}} List items represent downstream SNR per
               subcarrier group.  Maximum number of elements is
               256 for G.992.3, 512 for G.992.5.  For G.993.2,
               the number of elements will depend on the value of
               {{param|SNRGds}} but will not exceed 512.
               Interpretation of the value is as defined in ITU-T
               Rec.  G.997.1.  Interpretation of the value is as
               defined in ITU-T Rec.  G.997.1.
            
               Note: SNRps is not applicable in PLOAM for G.992.1
               or G.992.2.
            
               Note: See ITU-T Recommendation {{bibref|G.997.1}}.
               For a multimode device operating in a mode in
               which this parameter does not apply, the value of
               this parameter SHOULD be set to ''None''.";
          }
          leaf SNRpsus {
            type string;
            config false;
            description
              "{{list}} List items represent upstream SNR per
               subcarrier group.  The maximum number of elements
               is 64 for G.992.3, and G.992.5.  For G.993.2, the
               number of elements will depend on the value of
               {{param|SNRGus}} but will not exceed 512.
               Interpretation of the values is as defined in
               ITU-T Rec.  G.997.1.
            
               Note: SNRps is not applicable in PLOAM for G.992.1
               or G.992.2.
            
               Note: See ITU-T Recommendation {{bibref|G.997.1}}.
               For a multimode device operating in a mode in
               which this parameter does not apply, the value of
               this parameter SHOULD be set to ''None''.";
          }
          leaf SNRMTds {
            type uint32;
            config false;
            description
              "Indicates the number of symbols over which
               {{param|SNRpsds}} was measured.
            
               Note: See ITU-T Recommendation {{bibref|G.997.1}}.
               For a multimode device operating in a mode in
               which this parameter does not apply, the value of
               this parameter SHOULD be set to 0.";
          }
          leaf SNRMTus {
            type uint32;
            config false;
            description
              "Indicates the number of symbols over which
               {{param|SNRpsus}} was measured.
            
               Note: See ITU-T Recommendation {{bibref|G.997.1}}.
               For a multimode device operating in a mode in
               which this parameter does not apply, the value of
               this parameter SHOULD be set to 0.";
          }
          leaf BITSpsds {
            type int32;
            config false;
            description
              "{{list}} List items represent downstream bit
               allocation per subcarrier group.  Maximum number
               of elements is 256 for G.992.3, 512 for G.992.5.
               Interpretation of the value is as defined in ITU-T
               Rec.  {{bibref|G.997.1}}.";
          }
          leaf BITSpsus {
            type string;
            config false;
            description
              "{{list}} List items represent upstream bit allocation
               per subcarrier group.  Maximum number of elements
               is 256 for G.992.3, 512 for G.992.5.
               Interpretation of the value is as defined in ITU-T
               Rec.  {{bibref|G.997.1}}.";
          }
        }
      }
    }

    container Optical {
      description
        "This object models optical interface technologies.  It
         defines an {{object|Interface}} object that models a
         layer 1 optical interface that is capable of
         transporting Ethernet packets.  The data model
         definition is based on parts of {{bibref|G.988}}.";

      list Interface {
        key "Alias";
        description
          "Optical interface table (a stackable interface object as
           described in {{bibref|TR-181i2|Section 4.2}}).  This
           table models physical optical interfaces.";
        leaf Enable {
          type boolean;
          description
            "Enables or disables the optical interface.
          
             This parameter is based on ''ifAdminStatus'' from
             {{bibref|RFC2863}}.";
        }
        leaf Status {
          type enumeration {
            enum "Up";
            enum "Down";
            enum "Unknown";
            enum "Dormant";
            enum "NotPresent";
            enum "LowerLayerDown";
            enum "Error";
          }
          config false;
          description
            "The current operational state of the optical interface
             (see {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the optical interface as assigned
             by the CPE.";
        }
        leaf LastChange {
          type uint32;
          config false;
          description
            "The accumulated time in {{units}} since the optical
             interface entered its current operational state.";
        }
        leaf LowerLayers {
          type string;
          description
            "{{list}} {{reference|an interface object that is
             stacked immediately below this interface object}}
             See {{bibref|TR-181i2|Section 4.2.1}}.
          
             Note: Since {{object}} is a layer 1 interface, it is
             expected that {{param}} will not be used.";
        }
        leaf Upstream {
          type boolean;
          config false;
          description
            "Indicates whether the interface points towards the
             Internet ({{true}}) or towards End Devices
             ({{false}}).
          
             For example:
          
             * For an Internet Gateway Device, {{param}} will be
             {{true}} for all WAN interfaces and {{false}} for
             all LAN interfaces.
          
             * For a standalone WiFi Access Point that is
             connected via Ethernet to an Internet Gateway
             Device, {{param}} will be {{true}} for the Ethernet
             interface and {{false}} for the WiFi Radio
             interface.
          
             * For an End Device, {{param}} will be {{true}} for
             all interfaces.";
        }
        leaf OpticalSignalLevel {
          type types:Dbm1000 {
            range "-65536..65534";
          }
          config false;
          description
            "Current measurement of total downstream optical signal
             level.
          
             {{datatype|expand}}
          
             Valid values are -65.536 dBm (coded as -65536), to
             65.534 dBm (coded as 65534) in 0.002 dB increments.
          
             This parameter is based on ''Optical signal level''
             from {{bibref|G.988|Section 9.2.1}}.";
        }
        leaf LowerOpticalThreshold {
          type types:Dbm1000 {
            range "-127000..0";
          }
          config false;
          description
            "Optical level that is used to declare the downstream
             low received optical power alarm.
          
             {{datatype|expand}}
          
             Valid values are -127.5 dBm (coded as -127500) to 0
             dBm (coded as 0) in 0.5 dB increments.  The value
             -127500 indicates the device's internal policy.
          
             This parameter is based on ''Lower optical
             threshold'' from {{bibref|G.988|section 9.2.1}}.";
        }
        leaf UpperOpticalThreshold {
          type types:Dbm1000 {
            range "-127000..0";
          }
          config false;
          description
            "Optical level that is used to declare the downstream
             high received optical power alarm.
          
             {{datatype|expand}}
          
             Valid values are -127.5 dBm (coded as -127500) to 0
             dBm (coded as 0) in 0.5 dB increments.  The value
             -127500 indicates the device's internal policy.
          
             This parameter is based on ''Upper optical
             threshold'' from {{bibref|G.988|section 9.2.1}}.";
        }
        leaf TransmitOpticalLevel {
          type types:Dbm1000 {
            range "-127000..0";
          }
          config false;
          description
            "Current measurement of mean optical launch power.
          
             {{datatype|expand}}
          
             Valid values are -127.5 dBm (coded as -127500) to 0
             dBm (coded as 0) in 0.5 dB increments.  The value
             -127500 indicates the device's internal policy.
          
             This parameter is based on ''Transmit optical
             level'' from {{bibref|G.988|section 9.2.1}}.";
        }
        leaf LowerTransmitPowerThreshold {
          type types:Dbm1000 {
            range "-63500..63500";
          }
          config false;
          description
            "Minimum mean optical launch power that is used to
             declare the low transmit optical power alarm.
          
             {{datatype|expand}}
          
             Valid values are -63.5 dBm (coded as -63500) to
             +63.5 dBm (coded as 63500) in 0.5 dB increments.
             The value -63500 indicates the device's internal
             policy.
          
             This parameter is based on ''Lower transmit power
             threshold'' from {{bibref|G.988|section 9.2.1}}.";
        }
        leaf UpperTransmitPowerThreshold {
          type types:Dbm1000 {
            range "-63500..63500";
          }
          config false;
          description
            "Maximum mean optical launch power that is used to
             declare the high transmit optical power alarm.
          
             {{datatype|expand}}
          
             Valid values are -63.5 dBm (coded as -63500) to
             +63.5 dBm (coded as 63500) in 0.5 dB increments.
             The value -63500 indicates the device's internal
             policy.
          
             This parameter is based on ''Upper transmit power
             threshold'' from {{bibref|G.988|section 9.2.1}}.";
        }

        container Stats {
          config false;
          description
            "Throughput statistics for this interface.
          
             The CPE MUST reset the interface's Stats parameters
             (unless otherwise stated in individual object or
             parameter descriptions) either when the interface
             becomes operationally down due to a previous
             administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2|section 4.2.2}}.";
          leaf BytesSent {
            type uint64;
            description
              "The total number of bytes transmitted out of the
               interface, including framing characters.";
          }
          leaf BytesReceived {
            type uint64;
            description
              "The total number of bytes received on the interface,
               including framing characters.";
          }
          leaf PacketsSent {
            type uint64;
            description
              "The total number of packets transmitted out of the
               interface.";
          }
          leaf PacketsReceived {
            type uint64;
            description
              "The total number of packets received on the
               interface.";
          }
          leaf ErrorsSent {
            type uint32;
            description
              "The total number of outbound packets that could not
               be transmitted because of errors.";
          }
          leaf ErrorsReceived {
            type uint32;
            description
              "The total number of inbound packets that contained
               errors preventing them from being delivered to a
               higher-layer protocol.";
          }
          leaf DiscardPacketsSent {
            type uint32;
            description
              "The total number of outbound packets which were
               chosen to be discarded even though no errors had
               been detected to prevent their being transmitted.
               One possible reason for discarding such a packet
               could be to free up buffer space.";
          }
          leaf DiscardPacketsReceived {
            type uint32;
            description
              "The total number of inbound packets which were chosen
               to be discarded even though no errors had been
               detected to prevent their being delivered.  One
               possible reason for discarding such a packet could
               be to free up buffer space.";
          }
        }
      }
    }

    container Cellular {
      description
        "This object models cellular interfaces and access points.";
      leaf RoamingEnabled {
        type boolean;
        description
          "Enables or disables roaming.";
      }
      leaf RoamingStatus {
        type enumeration {
          enum "Home";
          enum "Roaming";
        }
        config false;
        description
          "Current roaming status.";
      }

      list Interface {
        key "Alias";
        description
          "Cellular interface table (a stackable interface object as
           described in {{bibref|TR-181i2|Section 4.2}}).  Each
           instance of this object models a cellular modem with a
           single radio and a single {{object|USIM}}.";
        leaf Enable {
          type boolean;
          description
            "Enables or disables the interface.
          
             This parameter is based on ''ifAdminStatus'' from
             {{bibref|RFC2863}}.";
        }
        leaf Status {
          type enumeration {
            enum "Up";
            enum "Down";
            enum "Unknown";
            enum "Dormant";
            enum "NotPresent";
            enum "LowerLayerDown";
            enum "Error";
          }
          config false;
          description
            "The current operational state of the interface (see
             {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}}
          
             * SHOULD change to {{enum|Up}} if and only if the
             interface is able to transmit and receive network
             traffic.
          
             * SHOULD change to {{enum|Dormant}} if and only if
             the interface is operable but is waiting for
             external actions before it can transmit and receive
             network traffic (and subsequently change to
             {{enum|Up}} if still operable when the expected
             actions have completed)
          
             * SHOULD remain in the {{enum|Error}} state if there
             is an error or other fault condition detected on the
             interface
          
             * SHOULD remain in the {{enum|NotPresent}} state if
             the interface has missing (typically hardware)
             components; it SHOULD change to {{enum|Unknown}} if
             the state of the interface can not be determined for
             some reason.
          
             Because the interface includes layer 1 the
             {{enum|LowerLayerDown}} value SHOULD never be used.
          
             This parameter is based on ''ifOperStatus'' from
             {{bibref|RFC2863}}.";
        }
        leaf Name {
          type string {
            length "0..64";
          }
          config false;
          description
            "The textual name of the interface as assigned by the
             CPE.";
        }
        leaf LastChange {
          type uint32;
          config false;
          description
            "The accumulated time in {{units}} since the interface
             entered its current operational state.";
        }
        leaf LowerLayers {
          type string;
          description
            "{{list}} {{reference|an interface object that is
             stacked immediately below this interface object}}
             See {{bibref|TR-181i2|Section 4.2.1}}.
          
             Note: Since {{object}} is a layer 1 interface, it is
             expected that {{param}} will not be used.";
        }
        leaf Upstream {
          type boolean;
          config false;
          description
            "Indicates whether the interface points towards the
             Internet ({{true}}) or towards End Devices
             ({{false}}).
          
             For example:
          
             * For an Internet Gateway Device, {{param}} will be
             {{true}} for all WAN interfaces and {{false}} for
             all LAN interfaces.
          
             * For a standalone WiFi Access Point that is
             connected via Ethernet to an Internet Gateway
             Device, {{param}} will be {{true}} for the Ethernet
             interface and {{false}} for the WiFi Radio
             interface.
          
             * For an End Device, {{param}} will be {{true}} for
             all interfaces.";
        }
        leaf IMEI {
          type string {
            length "15";
            pattern "[0-9]{15,15}";
          }
          config false;
          description
            "International Mobile Station Equipment Identity number,
             represented as a 15 digit string (digits 0-9).";
        }
        leaf SupportedAccessTechnologies {
          type enumeration {
            enum "GPRS";
            enum "EDGE";
            enum "UMTS";
            enum "UMTSHSPA";
            enum "CDMA2000OneX";
            enum "CDMA2000HRPD";
            enum "LTE";
          }
          config false;
          description
            "Access technologies supported by the interface.";
        }
        leaf PreferredAccessTechnology {
          type string;
          default "Auto";
          description
            "Preferred access technology.";
        }
        leaf CurrentAccessTechnology {
          type string;
          config false;
          description
            "Access technology that is currently in use.";
        }
        leaf AvailableNetworks {
          type string {
            length "0..64";
          }
          config false;
          description
            "List of available networks.";
        }
        leaf NetworkRequested {
          type string {
            length "0..64";
          }
          default "";
          description
            "Name of the network which will be used, or {{empty}} if
             the network is selected automatically.";
        }
        leaf NetworkInUse {
          type string {
            length "0..64";
          }
          config false;
          description
            "The value is {{empty}} if no network is found, or if
             the network specified in {{param|NetworkRequested}}
             is not found.";
        }
        leaf RSSI {
          type int32;
          config false;
          description
            "The received signal strength in {{units}}.  The allowed
             values depend on {{param|CurrentAccessTechnology}}:
          
             * For {{enum|GPRS|SupportedAccessTechnologies}},
             {{enum|EDGE|SupportedAccessTechnologies}} the range
             is -111 {{units}} to -49 {{units}}
          
             * For {{enum|UMTS|SupportedAccessTechnologies}},
             {{enum|UMTSHSPA|SupportedAccessTechnologies}} the
             range is -117 {{units}} to -54 {{units}}
          
             * For {{enum|LTE|SupportedAccessTechnologies}} the
             range is -117 {{units}} to -25 {{units}}
          
             Note: An undetectable signal is indicated by the
             appropriate lower limit, e.g.  -117 {{units}} for
             LTE.";
        }
        leaf UpstreamMaxBitRate {
          type uint32;
          config false;
          description
            "The current maximum attainable data rate upstream
             (expressed in {{units}}).";
        }
        leaf DownstreamMaxBitRate {
          type uint32;
          config false;
          description
            "The current maximum attainable data rate downstream
             (expressed in {{units}}).";
        }

        container USIM {
          description
            "USIM (Universal Subscriber Identity Module or SIM card)
             parameters for the interface.";
          leaf Status {
            type enumeration {
              enum "None";
              enum "Available";
              enum "Valid";
              enum "Blocked";
              enum "Error";
            }
            config false;
            description
              "The current status of the USIM card.";
          }
          leaf IMSI {
            type string {
              length "14..15";
              pattern "[0-9]{14,15}";
            }
            config false;
            description
              "International Mobile Subscriber Identity represented
               as a string with either 14 or 15 digits (digits
               0-9).  The first 3 digits are the mobile country
               code (MCC), which are followed by the mobile
               network code (MNC), either 2 digits (European
               standard) or 3 digits (North American standard),
               followed by the mobile subscription identification
               number (MSIN).";
          }
          leaf ICCID {
            type string {
              length "6..20";
              pattern "[0-9]{6,20}";
            }
            config false;
            description
              "Integrated Circuit Card Identifier represented as a
               string of up to 20 digits (digits 0-9).  The
               number is composed of the following parts:
            
               * Major industry identifier (MII), 2 fixed digits,
               89 for telecommunication purposes.
            
               * Country code, 1–3 digits, as defined by ITU-T
               recommendation {{bibref|ITU-E.164}}.
            
               * identifier, 1–4 digits.
            
               * Individual account identification number.  Its
               length is variable, but every number under one IIN
               will have the same length.
            
               * Single check digit calculated from the other
               digits using the Luhn algorithm.
            
               For cards using an ICCID according to
               {{bibref|ITU-E.118}} the maximum length is 19
               Digits, for GSM cards 20 digits.";
          }
          leaf MSISDN {
            type string {
              length "14..15";
              pattern "[0-9]{14,15}";
            }
            config false;
            description
              "Mobile Subscriber Integrated Service Digital Network
               Number, a number uniquely identifying a
               subscription in a GSM, UMTS, or LTE mobile
               network.  {{bibref|ITU-E.164}}";
          }
          leaf PINCheck {
            type enumeration {
              enum "OnNetworkAccess";
              enum "Reboot";
              enum "Off";
            }
            description
              "Controls the PIN verification of the USIM card.";
          }
          leaf PIN {
            type string {
              length "0..4";
            }
            description
              "Allows the ACS to change the USIM PIN used for SIM
               card activation.";
          }
        }

        container Stats {
          config false;
          description
            "Throughput statistics for this interface.
          
             The CPE MUST reset the interface's Stats parameters
             (unless otherwise stated in individual object or
             parameter descriptions) either when the interface
             becomes operationally down due to a previous
             administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2|section 4.2.2}}.";
          leaf BytesSent {
            type types:StatsCounter64;
            description
              "The total number of bytes transmitted out of the
               interface, including framing characters.";
          }
          leaf BytesReceived {
            type types:StatsCounter64;
            description
              "The total number of bytes received on the interface,
               including framing characters.";
          }
          leaf PacketsSent {
            type types:StatsCounter64;
            description
              "The total number of packets transmitted out of the
               interface.";
          }
          leaf PacketsReceived {
            type types:StatsCounter64;
            description
              "The total number of packets received on the
               interface.";
          }
          leaf ErrorsSent {
            type types:StatsCounter64;
            description
              "The total number of outbound packets that could not
               be transmitted because of errors.";
          }
          leaf ErrorsReceived {
            type types:StatsCounter64;
            description
              "The total number of inbound packets that contained
               errors preventing them from being delivered to a
               higher-layer protocol.";
          }
          leaf UnicastPacketsSent {
            type types:StatsCounter64;
            description
              "The total number of packets requested for
               transmission which were not addressed to a
               multicast or broadcast address at this layer,
               including those that were discarded or not sent.";
          }
          leaf UnicastPacketsReceived {
            type types:StatsCounter64;
            description
              "The total number of received packets, delivered by
               this layer to a higher layer, which were not
               addressed to a multicast or broadcast address at
               this layer.";
          }
          leaf DiscardPacketsSent {
            type types:StatsCounter64;
            description
              "The total number of outbound packets which were
               chosen to be discarded even though no errors had
               been detected to prevent their being transmitted.
               One possible reason for discarding such a packet
               could be to free up buffer space.";
          }
          leaf DiscardPacketsReceived {
            type types:StatsCounter64;
            description
              "The total number of inbound packets which were chosen
               to be discarded even though no errors had been
               detected to prevent their being delivered.  One
               possible reason for discarding such a packet could
               be to free up buffer space.";
          }
          leaf MulticastPacketsSent {
            type types:StatsCounter64;
            description
              "The total number of packets that higher-level
               protocols requested for transmission and which
               were addressed to a multicast address at this
               layer, including those that were discarded or not
               sent.";
          }
          leaf MulticastPacketsReceived {
            type types:StatsCounter64;
            description
              "The total number of received packets, delivered by
               this layer to a higher layer, which were addressed
               to a multicast address at this layer.";
          }
          leaf BroadcastPacketsSent {
            type types:StatsCounter64;
            description
              "The total number of packets that higher-level
               protocols requested for transmission and which
               were addressed to a broadcast address at this
               layer, including those that were discarded or not
               sent.";
          }
          leaf BroadcastPacketsReceived {
            type types:StatsCounter64;
            description
              "The total number of received packets, delivered by
               this layer to a higher layer, which were addressed
               to a broadcast address at this layer.";
          }
          leaf UnknownProtoPacketsReceived {
            type types:StatsCounter64;
            description
              "The total number of packets received via the
               interface which were discarded because of an
               unknown or unsupported protocol.";
          }
        }
      }

      list AccessPoint {
        key "APN";
        description
          "Cellular Access Point table.  Each entry is identified by
           an {{param|APN}} (Access Point Name) that identifies a
           gateway between the mobile network and another
           computer network.";
        leaf Enable {
          type boolean;
          description
            "Enables or disables the Access Point.";
        }
        leaf APN {
          type string {
            length "0..64";
          }
          description
            "Access Point Name.";
        }
        leaf Username {
          type string {
            length "0..256";
          }
          description
            "Username used to authenticate the CPE when making a
             connection to the Access Point.";
        }
        leaf Password {
          type string {
            length "0..256";
          }
          description
            "Password used to authenticate the CPE when making a
             connection to the Access Point.";
        }
        leaf Proxy {
          type types:IPAddress;
          description
            "Proxy server IP address.";
        }
        leaf ProxyPort {
          type uint32 {
            range "1..65535";
          }
          description
            "Proxy server port.";
        }
        leaf Interface {
          type string;
          description
            "Reference to the interface with which the access point
             is associated.";
        }
      }
    }

    container ATM {
      description
        "Asynchronous Transfer Mode (ATM) object that contains the
         {{object|Link}} interface and
         {{object|Diagnostics.F5Loopback}} diagnostics.";

      list Link {
        key "Alias";
        description
          "ATM link-layer table (a stackable interface object as
           described in {{bibref|TR-181i2|Section 4.2}}).  Models
           an ATM PVC virtual circuit and the ATM Adaption Layer
           (AAL).  An ATM Link entry is typically stacked on top
           of either a {{object|.DSL.Channel.}} or a
           {{object|.DSL.BondingGroup.}} object.
        
           When an ''ATM Link'' interface is used, a lower-layer
           {{object|.DSL.Channel}} interface MUST be configured
           with ATM encapsulation (see
           {{param|.DSL.Channel.{i}.LinkEncapsulationUsed}}).";
        leaf Enable {
          type boolean;
          default "false";
          description
            "Enables or disables the link.
          
             This parameter is based on ''ifAdminStatus'' from
             {{bibref|RFC2863}}.";
        }
        leaf Status {
          type enumeration {
            enum "Up";
            enum "Down";
            enum "Unknown";
            enum "Dormant";
            enum "NotPresent";
            enum "LowerLayerDown";
            enum "Error";
          }
          config false;
          default "Down";
          description
            "The current operational state of the link (see
             {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the link as assigned by the CPE.";
        }
        leaf LastChange {
          type uint32;
          config false;
          description
            "The accumulated time in {{units}} since the link
             entered its current operational state.";
        }
        leaf LowerLayers {
          type string;
          default "";
          description
            "{{list}} {{reference|an interface object that is
             stacked immediately below this interface object}}
             See {{bibref|TR-181i2|Section 4.2.1}}.";
        }
        leaf LinkType {
          type enumeration {
            enum "EoA";
            enum "IPoA";
            enum "PPPoA";
            enum "CIP";
            enum "Unconfigured";
          }
          description
            "Indicates the type of connection and refers to the
             complete stack of protocol used for this connection.";
        }
        leaf AutoConfig {
          type boolean;
          config false;
          description
            "Indicates if the CPE is currently using some auto
             configuration mechanisms for this connection.  If
             this variable is {{true}}, all writable variables in
             this connection instance become read-only.  Any
             attempt to change one of these variables SHOULD fail
             and an error SHOULD be returned.";
        }
        leaf DestinationAddress {
          type string {
            length "0..256";
            pattern "\d+/\d+";
          }
          description
            "Destination address of this link, in the form
             \"VPI/VCI\" (e.g.  \"8/23\" or \"0/35\").";
        }
        leaf Encapsulation {
          type enumeration {
            enum "LLC";
            enum "VCMUX";
          }
          description
            "Identifies the connection encapsulation that will be
             used.";
        }
        leaf FCSPreserved {
          type boolean;
          description
            "This flag tells if a checksum SHOULD be added in the
             ATM payload.  It does not refer to the checksum of
             one of the ATM cells or AALX packets.  In case of
             LLC or VCMUX encapsulation, this ATM checksum is the
             FCS field described in {{bibref|RFC2684}}.  It is
             only applicable in the upstream direction.";
        }
        leaf VCSearchList {
          type string {
            pattern "\d+/\d+";
          }
          description
            "{{list}} Ordered list of VPI/VCI pairs to search if a
             link using the {{param|DestinationAddress}} cannot
             be established.  In the form \"VPI1/VCI1, VPI2/VCI2,
             ...\".  {{pattern}}
          
             Example:
          
             : ''0/35, 8/35, 1/35''";
        }
        leaf AAL {
          type enumeration {
            enum "AAL1";
            enum "AAL2";
            enum "AAL3";
            enum "AAL4";
            enum "AAL5";
          }
          config false;
          description
            "Describes the ATM Adaptation Layer (AAL) currently in
             use on the PVC.";
        }

        container Stats {
          config false;
          description
            "Throughput statistics for this interface.
          
             The CPE MUST reset the interface's Stats parameters
             (unless otherwise stated in individual object or
             parameter descriptions) either when the interface
             becomes operationally down due to a previous
             administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2|section 4.2.2}}.";
          leaf BytesSent {
            type uint64;
            description
              "The total number of bytes transmitted out of the
               interface, including framing characters.";
          }
          leaf BytesReceived {
            type uint64;
            description
              "The total number of bytes received on the interface,
               including framing characters.";
          }
          leaf PacketsSent {
            type uint64;
            description
              "The total number of packets transmitted out of the
               interface.";
          }
          leaf PacketsReceived {
            type uint64;
            description
              "The total number of packets received on the
               interface.";
          }
          leaf ErrorsSent {
            type uint32;
            description
              "The total number of outbound packets that could not
               be transmitted because of errors.";
          }
          leaf ErrorsReceived {
            type uint32;
            description
              "The total number of inbound packets that contained
               errors preventing them from being delivered to a
               higher-layer protocol.";
          }
          leaf UnicastPacketsSent {
            type uint64;
            description
              "The total number of packets requested for
               transmission which were not addressed to a
               multicast or broadcast address at this layer,
               including those that were discarded or not sent.";
          }
          leaf UnicastPacketsReceived {
            type uint64;
            description
              "The total number of received packets, delivered by
               this layer to a higher layer, which were not
               addressed to a multicast or broadcast address at
               this layer.";
          }
          leaf DiscardPacketsSent {
            type uint32;
            description
              "The total number of outbound packets which were
               chosen to be discarded even though no errors had
               been detected to prevent their being transmitted.
               One possible reason for discarding such a packet
               could be to free up buffer space.";
          }
          leaf DiscardPacketsReceived {
            type uint32;
            description
              "The total number of inbound packets which were chosen
               to be discarded even though no errors had been
               detected to prevent their being delivered.  One
               possible reason for discarding such a packet could
               be to free up buffer space.";
          }
          leaf MulticastPacketsSent {
            type uint64;
            description
              "The total number of packets that higher-level
               protocols requested for transmission and which
               were addressed to a multicast address at this
               layer, including those that were discarded or not
               sent.";
          }
          leaf MulticastPacketsReceived {
            type uint64;
            description
              "The total number of received packets, delivered by
               this layer to a higher layer, which were addressed
               to a multicast address at this layer.";
          }
          leaf BroadcastPacketsSent {
            type uint64;
            description
              "The total number of packets that higher-level
               protocols requested for transmission and which
               were addressed to a broadcast address at this
               layer, including those that were discarded or not
               sent.";
          }
          leaf BroadcastPacketsReceived {
            type uint64;
            description
              "The total number of received packets, delivered by
               this layer to a higher layer, which were addressed
               to a broadcast address at this layer.";
          }
          leaf UnknownProtoPacketsReceived {
            type uint32;
            description
              "The total number of packets received via the
               interface which were discarded because of an
               unknown or unsupported protocol.";
          }
          leaf TransmittedBlocks {
            type uint32;
            description
              "The current count of successfully transmitted cells.";
          }
          leaf ReceivedBlocks {
            type uint32;
            description
              "The current count of successfully received cells.";
          }
          leaf CRCErrors {
            type uint32;
            description
              "Count of the ATM layer cyclic redundancy check (CRC)
               errors.
            
               This refers to CRC errors at the ATM adaptation
               layer (AAL).  The AAL in use is indicated by the
               {{param|#.AAL}} parameter.  The value of the
               {{param}} parameter MUST be 0 for AAL types that
               have no CRCs.";
          }
          leaf HECErrors {
            type uint32;
            description
              "Count of the number of Header Error Check related
               errors at the ATM layer.";
          }
        }

        container QoS {
          description
            "The ATM Link QoS object.";
          leaf QoSClass {
            type enumeration {
              enum "UBR";
              enum "CBR";
              enum "GFR";
              enum "VBR-nrt";
              enum "VBR-rt";
              enum "UBR+";
              enum "ABR";
            }
            description
              "Describes the ATM Quality Of Service (QoS) being used
               on the VC.";
          }
          leaf PeakCellRate {
            type uint32;
            description
              "Specifies the upstream peak cell rate in {{units}}.";
          }
          leaf MaximumBurstSize {
            type uint32;
            description
              "Specifies the upstream maximum burst size in
               {{units}}.";
          }
          leaf SustainableCellRate {
            type uint32;
            description
              "Specifies the upstream sustainable cell rate, in
               {{units}}.";
          }
        }
      }

      container Diagnostics {
        description
          "The ATM Diagnostics object.";

        container F5Loopback {
          description
            "This object provides access to an ATM-layer F5 OAM
             loopback test.";
          leaf DiagnosticsState {
            type enumeration {
              enum "None";
              enum "Requested";
              enum "Canceled";
              enum "Complete";
              enum "Error";
              enum "Error_Internal";
              enum "Error_Other";
            }
            description
              "{{issue|A10-DIAG|No error state in original version}}
            
               {{datatype|expand}}";
          }
          leaf Interface {
            type string {
              length "0..256";
            }
            description
              "{{reference}} This is the interface over which the
               test is to be performed.";
          }
          leaf NumberOfRepetitions {
            type uint32 {
              range "1..max";
            }
            description
              "Number of repetitions of the ping test to perform
               before reporting the results.";
          }
          leaf Timeout {
            type uint32 {
              range "1..max";
            }
            description
              "Timeout in {{units}} for the ping test.";
          }
          leaf SuccessCount {
            type uint32;
            config false;
            description
              "Result parameter indicating the number of successful
               pings (those in which a successful response was
               received prior to the timeout) in the most recent
               ping test.";
          }
          leaf FailureCount {
            type uint32;
            config false;
            description
              "Result parameter indicating the number of failed
               pings in the most recent ping test.";
          }
          leaf AverageResponseTime {
            type uint32;
            config false;
            description
              "Result parameter indicating the average response time
               in {{units}} over all repetitions with successful
               responses of the most recent ping test.  If there
               were no successful responses, this value MUST be
               zero.";
          }
          leaf MinimumResponseTime {
            type uint32;
            config false;
            description
              "Result parameter indicating the minimum response time
               in {{units}} over all repetitions with successful
               responses of the most recent ping test.  If there
               were no successful responses, this value MUST be
               zero.";
          }
          leaf MaximumResponseTime {
            type uint32;
            config false;
            description
              "Result parameter indicating the maximum response time
               in {{units}} over all repetitions with successful
               responses of the most recent ping test.  If there
               were no successful responses, this value MUST be
               zero.";
          }
        }
      }
    }

    container PTM {
      description
        "Packet Transfer Mode ({{bibref|G.993.1|Annex H}}).  This
         object contains the {{object|Link}} interface.";

      list Link {
        key "Alias";
        description
          "PTM link-layer table (a stackable interface object as
           described in {{bibref|TR-181i2|Section 4.2}}).  Models
           a layer 2 variable-sized packet interface.  A PTM Link
           entry is typically stacked on top of either a
           {{object|.DSL.Channel.}} or a
           {{object|.DSL.BondingGroup.}} object.
        
           When a ''PTM Link'' interface is used, a lower-layer
           {{object|.DSL.Channel}} interface MUST be configured
           with PTM encapsulation (see
           {{param|.DSL.Channel.{i}.LinkEncapsulationUsed}}).";
        leaf Enable {
          type boolean;
          default "false";
          description
            "Enables or disables the link.
          
             This parameter is based on ''ifAdminStatus'' from
             {{bibref|RFC2863}}.";
        }
        leaf Status {
          type enumeration {
            enum "Up";
            enum "Down";
            enum "Unknown";
            enum "Dormant";
            enum "NotPresent";
            enum "LowerLayerDown";
            enum "Error";
          }
          config false;
          default "Down";
          description
            "The current operational state of the link (see
             {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the link as assigned by the CPE.";
        }
        leaf LastChange {
          type uint32;
          config false;
          description
            "The accumulated time in {{units}} since the link
             entered its current operational state.";
        }
        leaf LowerLayers {
          type string;
          default "";
          description
            "{{list}} {{reference|an interface object that is
             stacked immediately below this interface object}}
             See {{bibref|TR-181i2|Section 4.2.1}}.";
        }
        leaf MACAddress {
          type types:MACAddress;
          config false;
          description
            "The MAC Address of the interface.
          
             Note: This is not necessarily the same as the
             Ethernet header source or destination MAC address,
             which is associated with the IP interface and is
             modeled via the
             {{param|.Ethernet.Link.{i}.MACAddress}} parameter.";
        }

        container Stats {
          config false;
          description
            "Throughput statistics for this interface.
          
             The CPE MUST reset the interface's Stats parameters
             (unless otherwise stated in individual object or
             parameter descriptions) either when the interface
             becomes operationally down due to a previous
             administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2|section 4.2.2}}.";
          leaf BytesSent {
            type uint64;
            description
              "The total number of bytes transmitted out of the
               interface, including framing characters.";
          }
          leaf BytesReceived {
            type uint64;
            description
              "The total number of bytes received on the interface,
               including framing characters.";
          }
          leaf PacketsSent {
            type uint64;
            description
              "The total number of packets transmitted out of the
               interface.";
          }
          leaf PacketsReceived {
            type uint64;
            description
              "The total number of packets received on the
               interface.";
          }
          leaf ErrorsSent {
            type uint32;
            description
              "The total number of outbound packets that could not
               be transmitted because of errors.";
          }
          leaf ErrorsReceived {
            type uint32;
            description
              "The total number of inbound packets that contained
               errors preventing them from being delivered to a
               higher-layer protocol.";
          }
          leaf UnicastPacketsSent {
            type uint64;
            description
              "The total number of packets requested for
               transmission which were not addressed to a
               multicast or broadcast address at this layer,
               including those that were discarded or not sent.";
          }
          leaf UnicastPacketsReceived {
            type uint64;
            description
              "The total number of received packets, delivered by
               this layer to a higher layer, which were not
               addressed to a multicast or broadcast address at
               this layer.";
          }
          leaf DiscardPacketsSent {
            type uint32;
            description
              "The total number of outbound packets which were
               chosen to be discarded even though no errors had
               been detected to prevent their being transmitted.
               One possible reason for discarding such a packet
               could be to free up buffer space.";
          }
          leaf DiscardPacketsReceived {
            type uint32;
            description
              "The total number of inbound packets which were chosen
               to be discarded even though no errors had been
               detected to prevent their being delivered.  One
               possible reason for discarding such a packet could
               be to free up buffer space.";
          }
          leaf MulticastPacketsSent {
            type uint64;
            description
              "The total number of packets that higher-level
               protocols requested for transmission and which
               were addressed to a multicast address at this
               layer, including those that were discarded or not
               sent.";
          }
          leaf MulticastPacketsReceived {
            type uint64;
            description
              "The total number of received packets, delivered by
               this layer to a higher layer, which were addressed
               to a multicast address at this layer.";
          }
          leaf BroadcastPacketsSent {
            type uint64;
            description
              "The total number of packets that higher-level
               protocols requested for transmission and which
               were addressed to a broadcast address at this
               layer, including those that were discarded or not
               sent.";
          }
          leaf BroadcastPacketsReceived {
            type uint64;
            description
              "The total number of received packets, delivered by
               this layer to a higher layer, which were addressed
               to a broadcast address at this layer.";
          }
          leaf UnknownProtoPacketsReceived {
            type uint32;
            description
              "The total number of packets received via the
               interface which were discarded because of an
               unknown or unsupported protocol.";
          }
        }
      }
    }

    container Ethernet {
      description
        "Ethernet object.  This object models several Ethernet
         interface objects, each representing a different stack
         layer, including: {{object|Interface}}, {{object|Link}},
         and {{object|VLANTermination}}.  {{object|Interface}} is
         media-specific and models a port, the PHY layer, and the
         MAC layer.  {{object|Link}} is media-independent and
         models the Logical Link Control (LLC) layer.  An
         \"outer\" {{object|VLANTermination}}, when present, is
         expected to be stacked on top of {{object|Link}} objects
         to receive and send frames with a configured VLANID.";

      list RMONStats {
        key "Interface VLANID Queue";
        description
          "Ethernet statistics based on the {{bibref|RFC2819}}
           ''RMON-MIB'' ''etherStatsTable'', with some extensions
           inspired by {{bibref|G.988|Section 9.3.32}}.
        
           Each instance is associated with an interface capable
           of transporting Ethernet-encapsulated packets, and
           contains a set of unidirectional Ethernet statistics.
        
           The statistics are sampled either on ingress or on
           egress.  This is determined as follows:
        
           * If the instance is associated with an egress queue
           (or queues) via the {{param|Queue}} parameter or by
           setting {{param|AllQueues}} to {{true}} then data is
           sampled on egress.  In this case {{param|Bytes}} etc
           measure the data that has been sent on the interface,
           possibly filtered by {{param|Queue}} or
           {{param|VLANID}}.
        
           * Otherwise data is sampled on ingress.  In this case
           {{param|Bytes}} etc measure the data that has been
           received on the interface, possibly filtered by
           {{param|VLANID}}.
        
           When sampling on egress, the term ''received'' means
           ''received by the queuing sub-system''.
        
           Multiple instances can be associated with a single
           interface: individual instances can be configured to
           collect data associated with the entire interface, or
           with a particular VLAN and/or queue.
        
           The CPE MUST reset each instances's Stats parameters
           whenever the instance is disabled and re-enabled.
           Whether this reset occurs when the instance becomes
           operationally disabled ({{param|Status}} =
           {{enum|Disabled|Status}}) or administratively enabled
           ({{param|Enable}} = {{true}}) is a local matter to the
           CPE.  This is similar to the behavior of interface
           statistics, e.g.  as specified for
           {{object|Device.Ethernet.Interface.{i}.Stats}}.
           Furthermore, this instance's Stats parameters MUST be
           reset whenever the referenced interface's Stats
           parameters are reset, or when the referenced queue or
           VLAN is disabled and re-enabled.
        
           For enabled table entries, if {{param|Interface}}
           references an interface that is not capable of
           transporting Ethernet-encapsulated packets, or if
           {{param|Queue}} references a queue that is not
           instantiated on {{param|Interface}}, or if
           {{param|Queue}} is not a valid reference and
           {{param|AllQueues}} is {{false}}, the table entry is
           inoperable and the CPE MUST set {{param|Status}} to
           {{enum|Error_Misconfigured|Status}}.
        
           Note: The {{object}} table includes unique key
           parameters that are strong references.  If a strongly
           referenced object is deleted, the CPE will set the
           referencing parameter to {{empty}}.  However, doing so
           under these circumstances might cause the updated
           {{object}} row to then violate the table's unique key
           constraint; if this occurs, the CPE MUST set
           {{param|Status}} to
           {{enum|Error_Misconfigured|Status}} and disable the
           offending {{object}} row.";
        leaf Enable {
          type boolean;
          default "false";
          description
            "Enables or disables this instance.";
        }
        leaf Status {
          type enumeration {
            enum "Disabled";
            enum "Enabled";
            enum "Error_Misconfigured";
            enum "Error";
          }
          config false;
          default "Disabled";
          description
            "The status of this instance.  {{enum}}
          
             The {{enum|Error_Misconfigured}} value indicates
             that a necessary configuration value is undefined or
             invalid.
          
             The {{enum|Error}} value MAY be used by the CPE to
             indicate a locally defined error condition.";
        }
        leaf Name {
          type string {
            length "0..64";
          }
          config false;
          description
            "The textual name of the {{object}} entry as assigned by
             the CPE.";
        }
        leaf Interface {
          type string;
          default "";
          description
            "The interface associated with this instance.
             {{reference|an interface that is capable of
             transporting Ethernet-encapsulated packets}}
          
             The term \"capable of transporting
             Ethernet-encapsulated packets\" means \"has an
             Ethernet header\" and therefore refers to any
             interface that is at or below an
             ''Ethernet''.{{object|#.Link}} instance in the
             interface stack.";
        }
        leaf VLANID {
          type uint32 {
            range "0..4094";
          }
          default "0";
          description
            "Filter criterion.
          
             The VLAN ID for which statistics are to be
             collected.
          
             A zero value indicates that all packets, whether or
             not they have a VLAN header, will be considered.
          
             A non-zero value indicates that only packets that
             have the the specified VLAN ID will be considered.";
        }
        leaf Queue {
          type string;
          default "";
          description
            "Filter criterion.
          
             The egress queue with which this instance is
             associated.
          
             Only packets that are sent to the referenced queue
             will be considered.";
        }
        leaf AllQueues {
          type boolean;
          default "false";
          description
            "Indicates whether this instance applies to all queues.
             If {{true}}, the value of {{param|Queue}} is ignored
             since all egress queues are indicated.";
        }
        leaf DropEvents {
          type uint32;
          config false;
          default "0";
          description
            "The total number of events in which packets were
             dropped due to lack of resources.  Note that this
             number is not necessarily the number of packets
             dropped; it is just the number of times this
             condition has been detected.
          
             This parameter is based on ''etherStatsDropEvents''
             from {{bibref|RFC2819}}.";
        }
        leaf Bytes {
          type uint64;
          config false;
          default "0";
          description
            "The total number of {{units}} (including those in bad
             packets) received (excluding framing bits but
             including FCS bytes).
          
             This parameter is based on ''etherStatsOctets'' from
             {{bibref|RFC2819}}.";
        }
        leaf Packets {
          type uint64;
          config false;
          default "0";
          description
            "The total number of {{units}} (including bad packets,
             broadcast packets, and multicast packets) received.
          
             This parameter is based on ''etherStatsPkts'' from
             {{bibref|RFC2819}}.";
        }
        leaf BroadcastPackets {
          type uint64;
          config false;
          default "0";
          description
            "The total number of good {{units}} received that were
             directed to the broadcast address.  Note that this
             does not include multicast packets.
          
             This parameter is based on
             ''etherStatsBroadcastPkts'' from {{bibref|RFC2819}}.";
        }
        leaf MulticastPackets {
          type uint64;
          config false;
          default "0";
          description
            "The total number of good {{units}} received that were
             directed to a multicast address.  Note that this
             number does not include packets directed to the
             broadcast address.
          
             This parameter is based on
             ''etherStatsMulticastPkts'' from {{bibref|RFC2819}}.";
        }
        leaf CRCErroredPackets {
          type uint32;
          config false;
          default "0";
          description
            "The total number of {{units}} received that had a
             length (excluding framing bits, but including FCS
             bytes) of between 64 and 1518 bytes, inclusive, but
             had either a bad Frame Check Sequence (FCS) with an
             integral number of bytes (FCS Error) or a bad FCS
             with a non-integral number of bytes (Alignment
             Error).
          
             This parameter is based on
             ''etherStatsCRCAlignErrors'' from
             {{bibref|RFC2819}}.";
        }
        leaf UndersizePackets {
          type uint32;
          config false;
          default "0";
          description
            "The total number of {{units}} received that were less
             than 64 bytes long (excluding framing bits, but
             including FCS bytes) and were otherwise well formed.
          
             This parameter is based on
             ''etherStatsUndersizePkts'' from {{bibref|RFC2819}}.";
        }
        leaf OversizePackets {
          type uint32;
          config false;
          default "0";
          description
            "The total number of {{units}} received that were longer
             than 1518 bytes (excluding framing bits, but
             including FCS bytes) and were otherwise well formed.
          
             This parameter is based on
             ''etherStatsOversizePkts'' from {{bibref|RFC2819}}.";
        }
        leaf Packets64Bytes {
          type uint64;
          config false;
          default "0";
          description
            "The total number of {{units}} (including bad packets)
             received that were 64 bytes in length (excluding
             framing bits but including FCS bytes).
          
             This parameter is based on
             ''etherStatsPkts64Octets'' from {{bibref|RFC2819}}.";
        }
        leaf Packets65to127Bytes {
          type uint64;
          config false;
          default "0";
          description
            "The total number of {{units}} (including bad packets)
             received that were between 65 and 127 bytes in
             length inclusive (excluding framing bits but
             including FCS bytes).
          
             This parameter is based on
             ''etherStatsPkts65to127Octets'' from
             {{bibref|RFC2819}}.";
        }
        leaf Packets128to255Bytes {
          type uint64;
          config false;
          default "0";
          description
            "The total number of {{units}} (including bad packets)
             received that were between 128 and 255 bytes in
             length inclusive (excluding framing bits but
             including FCS bytes).
          
             This parameter is based on
             ''etherStatsPkts6128to255Octets'' from
             {{bibref|RFC2819}}.";
        }
        leaf Packets256to511Bytes {
          type uint64;
          config false;
          default "0";
          description
            "The total number of {{units}} (including bad packets)
             received that were between 256 and 511 bytes in
             length inclusive (excluding framing bits but
             including FCS bytes).
          
             This parameter is based on
             ''etherStatsPkts256to511Octets'' from
             {{bibref|RFC2819}}.";
        }
        leaf Packets512to1023Bytes {
          type uint64;
          config false;
          default "0";
          description
            "The total number of {{units}} (including bad packets)
             received that were between 512 and 1023 bytes in
             length inclusive (excluding framing bits but
             including FCS bytes).
          
             This parameter is based on
             ''etherStatsPkts512to1023Octets'' from
             {{bibref|RFC2819}}.";
        }
        leaf Packets1024to1518Bytes {
          type uint64;
          config false;
          default "0";
          description
            "The total number of {{units}} (including bad packets)
             received that were between 1024 and 1518 bytes in
             length inclusive (excluding framing bits but
             including FCS bytes).
          
             This parameter is based on
             ''etherStatsPkts1024to1518Octets'' from
             {{bibref|RFC2819}}.";
        }
      }

      list Interface {
        key "Alias";
        description
          "Ethernet interface table (a stackable interface object as
           described in {{bibref|TR-181i2|Section 4.2}}).  This
           table models physical Ethernet ports, but in terms of
           the interface stack it also models the PHY and MAC
           level Ethernet interface.";
        leaf Enable {
          type boolean;
          description
            "Enables or disables the interface.
          
             This parameter is based on ''ifAdminStatus'' from
             {{bibref|RFC2863}}.";
        }
        leaf Status {
          type enumeration {
            enum "Up";
            enum "Down";
            enum "Unknown";
            enum "Dormant";
            enum "NotPresent";
            enum "LowerLayerDown";
            enum "Error";
          }
          config false;
          description
            "The current operational state of the interface (see
             {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the interface as assigned by the
             CPE.";
        }
        leaf LastChange {
          type uint32;
          config false;
          description
            "The accumulated time in {{units}} since the interface
             entered its current operational state.";
        }
        leaf LowerLayers {
          type string;
          description
            "{{list}} {{reference|an interface object that is
             stacked immediately below this interface object}}
             See {{bibref|TR-181i2|Section 4.2.1}}.
          
             Note: Since {{object}} is a layer 1 interface, it is
             expected that {{param}} will not be used.";
        }
        leaf Upstream {
          type boolean;
          config false;
          description
            "Indicates whether the interface points towards the
             Internet ({{true}}) or towards End Devices
             ({{false}}).
          
             For example:
          
             * For an Internet Gateway Device, {{param}} will be
             {{true}} for all WAN interfaces and {{false}} for
             all LAN interfaces.
          
             * For a standalone WiFi Access Point that is
             connected via Ethernet to an Internet Gateway
             Device, {{param}} will be {{true}} for the Ethernet
             interface and {{false}} for the WiFi Radio
             interface.
          
             * For an End Device, {{param}} will be {{true}} for
             all interfaces.";
        }
        leaf MACAddress {
          type types:MACAddress;
          config false;
          description
            "The MAC Address of the interface.
          
             Note: This is not necessarily the same as the
             Ethernet header source or destination MAC address,
             which is associated with the IP interface and is
             modeled via the
             {{param|.Ethernet.Link.{i}.MACAddress}} parameter.";
        }
        leaf MaxBitRate {
          type int32 {
            range "-1..max";
          }
          description
            "The maximum upstream and downstream PHY bit rate
             supported by this interface (expressed in
             {{units}}).
          
             A value of -1 indicates automatic selection of the
             maximum bit rate.";
        }
        leaf CurrentBitRate {
          type uint32;
          config false;
          description
            "The current upstream and downstream PHY bit rate on
             this interface (expressed in {{units}}).
          
             A value of 0 indicates that the current bit rate is
             unknown.";
        }
        leaf DuplexMode {
          type enumeration {
            enum "Half";
            enum "Full";
            enum "Auto";
          }
          description
            "The duplex mode available to this connection.";
        }
        leaf EEECapability {
          type boolean;
          config false;
          description
            "Indicates whether this physical ethernet port supports
             Energy Efficient Ethernet as specified in
             {{bibref|802.3-2012_section6|Section 78}}.";
        }
        leaf EEEEnable {
          type boolean;
          description
            "Whether Energy Efficient Ethernet
             {{bibref|802.3-2012_section6|Section 78}} support is
             currently enabled.  When enabled, this ethernet port
             will be capable of entering or exiting Low Power
             Idle (LPI) mode.";
        }

        container Stats {
          config false;
          description
            "Throughput statistics for this interface.
          
             The CPE MUST reset the interface's Stats parameters
             (unless otherwise stated in individual object or
             parameter descriptions) either when the interface
             becomes operationally down due to a previous
             administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2|section 4.2.2}}.";
          leaf BytesSent {
            type uint64;
            description
              "The total number of bytes transmitted out of the
               interface, including framing characters.";
          }
          leaf BytesReceived {
            type uint64;
            description
              "The total number of bytes received on the interface,
               including framing characters.";
          }
          leaf PacketsSent {
            type uint64;
            description
              "The total number of packets transmitted out of the
               interface.";
          }
          leaf PacketsReceived {
            type uint64;
            description
              "The total number of packets received on the
               interface.";
          }
          leaf ErrorsSent {
            type uint32;
            description
              "The total number of outbound packets that could not
               be transmitted because of errors.";
          }
          leaf ErrorsReceived {
            type uint32;
            description
              "The total number of inbound packets that contained
               errors preventing them from being delivered to a
               higher-layer protocol.";
          }
          leaf UnicastPacketsSent {
            type uint64;
            description
              "The total number of packets requested for
               transmission which were not addressed to a
               multicast or broadcast address at this layer,
               including those that were discarded or not sent.";
          }
          leaf UnicastPacketsReceived {
            type uint64;
            description
              "The total number of received packets, delivered by
               this layer to a higher layer, which were not
               addressed to a multicast or broadcast address at
               this layer.";
          }
          leaf DiscardPacketsSent {
            type uint32;
            description
              "The total number of outbound packets which were
               chosen to be discarded even though no errors had
               been detected to prevent their being transmitted.
               One possible reason for discarding such a packet
               could be to free up buffer space.";
          }
          leaf DiscardPacketsReceived {
            type uint32;
            description
              "The total number of inbound packets which were chosen
               to be discarded even though no errors had been
               detected to prevent their being delivered.  One
               possible reason for discarding such a packet could
               be to free up buffer space.";
          }
          leaf MulticastPacketsSent {
            type uint64;
            description
              "The total number of packets that higher-level
               protocols requested for transmission and which
               were addressed to a multicast address at this
               layer, including those that were discarded or not
               sent.";
          }
          leaf MulticastPacketsReceived {
            type uint64;
            description
              "The total number of received packets, delivered by
               this layer to a higher layer, which were addressed
               to a multicast address at this layer.";
          }
          leaf BroadcastPacketsSent {
            type uint64;
            description
              "The total number of packets that higher-level
               protocols requested for transmission and which
               were addressed to a broadcast address at this
               layer, including those that were discarded or not
               sent.";
          }
          leaf BroadcastPacketsReceived {
            type uint64;
            description
              "The total number of received packets, delivered by
               this layer to a higher layer, which were addressed
               to a broadcast address at this layer.";
          }
          leaf UnknownProtoPacketsReceived {
            type uint32;
            description
              "The total number of packets received via the
               interface which were discarded because of an
               unknown or unsupported protocol.";
          }
        }
      }

      list Link {
        key "MACAddress";
        description
          "Ethernet link layer table (a stackable interface object
           as described in {{bibref|TR-181i2|Section 4.2}}).
           Table entries model the Logical Link Control (LLC)
           layer.  It is expected that an ''Ethernet Link''
           interface can be stacked above any lower-layer
           interface object capable of carrying Ethernet frames.";
        leaf Enable {
          type boolean;
          default "false";
          description
            "Enables or disables the link.
          
             This parameter is based on ''ifAdminStatus'' from
             {{bibref|RFC2863}}.";
        }
        leaf Status {
          type enumeration {
            enum "Up";
            enum "Down";
            enum "Unknown";
            enum "Dormant";
            enum "NotPresent";
            enum "LowerLayerDown";
            enum "Error";
          }
          config false;
          default "Down";
          description
            "The current operational state of the link (see
             {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the link as assigned by the CPE.";
        }
        leaf LastChange {
          type uint32;
          config false;
          description
            "The accumulated time in {{units}} since the link
             entered its current operational state.";
        }
        leaf LowerLayers {
          type string;
          default "";
          description
            "{{list}} {{reference|an interface object that is
             stacked immediately below this interface object}}
             See {{bibref|TR-181i2|Section 4.2.1}}.";
        }
        leaf MACAddress {
          type types:MACAddress;
          config false;
          description
            "The MAC address used for packets sent via this
             interface.  Provides the source MAC address for
             outgoing traffic and the destination MAC address for
             incoming traffic.";
        }
        leaf PriorityTagging {
          type boolean;
          default "false";
          description
            "Enables or disables priority tagging on this Ethernet
             Link.
          
             When {{true}}, egress frames leaving this interface
             will be priority tagged with the frame's associated
             priority value, which will either be derived
             directly from the ingress frame or else set via
             {{param|.QoS.Classification.{i}.EthernetPriorityMark}}
             or
             {{param|.QoS.Classification.{i}.InnerEthernetPriorityMark}}.
          
             When {{false}}, egress frames leaving this interface
             will be untagged.
          
             The parameter does not affect reception of ingress
             frames.";
        }

        container Stats {
          config false;
          description
            "Throughput statistics for this interface.
          
             The CPE MUST reset the interface's Stats parameters
             (unless otherwise stated in individual object or
             parameter descriptions) either when the interface
             becomes operationally down due to a previous
             administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2|section 4.2.2}}.";
          leaf BytesSent {
            type uint64;
            description
              "The total number of bytes transmitted out of the
               interface, including framing characters.";
          }
          leaf BytesReceived {
            type uint64;
            description
              "The total number of bytes received on the interface,
               including framing characters.";
          }
          leaf PacketsSent {
            type uint64;
            description
              "The total number of packets transmitted out of the
               interface.";
          }
          leaf PacketsReceived {
            type uint64;
            description
              "The total number of packets received on the
               interface.";
          }
          leaf ErrorsSent {
            type uint32;
            description
              "The total number of outbound packets that could not
               be transmitted because of errors.";
          }
          leaf ErrorsReceived {
            type uint32;
            description
              "The total number of inbound packets that contained
               errors preventing them from being delivered to a
               higher-layer protocol.";
          }
          leaf UnicastPacketsSent {
            type uint64;
            description
              "The total number of packets requested for
               transmission which were not addressed to a
               multicast or broadcast address at this layer,
               including those that were discarded or not sent.";
          }
          leaf UnicastPacketsReceived {
            type uint64;
            description
              "The total number of received packets, delivered by
               this layer to a higher layer, which were not
               addressed to a multicast or broadcast address at
               this layer.";
          }
          leaf DiscardPacketsSent {
            type uint32;
            description
              "The total number of outbound packets which were
               chosen to be discarded even though no errors had
               been detected to prevent their being transmitted.
               One possible reason for discarding such a packet
               could be to free up buffer space.";
          }
          leaf DiscardPacketsReceived {
            type uint32;
            description
              "The total number of inbound packets which were chosen
               to be discarded even though no errors had been
               detected to prevent their being delivered.  One
               possible reason for discarding such a packet could
               be to free up buffer space.";
          }
          leaf MulticastPacketsSent {
            type uint64;
            description
              "The total number of packets that higher-level
               protocols requested for transmission and which
               were addressed to a multicast address at this
               layer, including those that were discarded or not
               sent.";
          }
          leaf MulticastPacketsReceived {
            type uint64;
            description
              "The total number of received packets, delivered by
               this layer to a higher layer, which were addressed
               to a multicast address at this layer.";
          }
          leaf BroadcastPacketsSent {
            type uint64;
            description
              "The total number of packets that higher-level
               protocols requested for transmission and which
               were addressed to a broadcast address at this
               layer, including those that were discarded or not
               sent.";
          }
          leaf BroadcastPacketsReceived {
            type uint64;
            description
              "The total number of received packets, delivered by
               this layer to a higher layer, which were addressed
               to a broadcast address at this layer.";
          }
          leaf UnknownProtoPacketsReceived {
            type uint32;
            description
              "The total number of packets received via the
               interface which were discarded because of an
               unknown or unsupported protocol.";
          }
        }
      }

      list VLANTermination {
        key "Alias";
        description
          "VLAN Termination table (a stackable interface object as
           described in {{bibref|TR-181i2|Section 4.2}}).  A VLAN
           Termination entry is typically stacked on top of a
           {{object|#.Link}} object to receive and send frames
           with the configured {{param|VLANID}}.";
        leaf Enable {
          type boolean;
          default "false";
          description
            "Enables or disables the VLANTermination entry.
          
             This parameter is based on ''ifAdminStatus'' from
             {{bibref|RFC2863}}.";
        }
        leaf Status {
          type enumeration {
            enum "Up";
            enum "Down";
            enum "Unknown";
            enum "Dormant";
            enum "NotPresent";
            enum "LowerLayerDown";
            enum "Error";
          }
          config false;
          default "Down";
          description
            "The current operational state of the VLANTermination
             entry (see {{bibref|TR-181i2|Section 4.2.2}}).
             {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the VLANTermination entry as
             assigned by the CPE.";
        }
        leaf LastChange {
          type uint32;
          config false;
          description
            "The accumulated time in {{units}} since the
             VLANTermination entered its current operational
             state.";
        }
        leaf LowerLayers {
          type string;
          default "";
          description
            "{{list}} {{reference|an interface object that is
             stacked immediately below this interface object}}
             See {{bibref|TR-181i2|Section 4.2.1}}.";
        }
        leaf VLANID {
          type uint32 {
            range "1..4094";
          }
          description
            "The VLAN ID for this {{object}} entry (as defined in
             {{bibref|802.1Q-2011}}).  Only ingress frames with
             this VLAN ID will be passed to higher protocol
             layers; frames sent from higher protocol layers will
             be tagged with this VLAN ID.";
        }
        leaf TPID {
          type uint32;
          default "33024";
          description
            "The Tag Protocol Identifier (TPID) assigned to this
             {{object}}.  The TPID is an EtherType value used to
             identify the frame as a tagged frame.
          
             Standard {{bibref|802.1Q-2011|Table 9.1}} TPID
             values are:
          
             *S-TAG 0x88A8 = 34984
          
             *C-TAG 0x8100 = 33024
          
             Non-Standard TPID values are:
          
             *S-TAG 0x9100 = 37120";
        }

        container Stats {
          config false;
          description
            "Throughput statistics for this interface.
          
             The CPE MUST reset the interface's Stats parameters
             (unless otherwise stated in individual object or
             parameter descriptions) either when the interface
             becomes operationally down due to a previous
             administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2|section 4.2.2}}.";
          leaf BytesSent {
            type uint64;
            description
              "The total number of bytes transmitted out of the
               interface, including framing characters.";
          }
          leaf BytesReceived {
            type uint64;
            description
              "The total number of bytes received on the interface,
               including framing characters.";
          }
          leaf PacketsSent {
            type uint64;
            description
              "The total number of packets transmitted out of the
               interface.";
          }
          leaf PacketsReceived {
            type uint64;
            description
              "The total number of packets received on the
               interface.";
          }
          leaf ErrorsSent {
            type uint32;
            description
              "The total number of outbound packets that could not
               be transmitted because of errors.";
          }
          leaf ErrorsReceived {
            type uint32;
            description
              "The total number of inbound packets that contained
               errors preventing them from being delivered to a
               higher-layer protocol.";
          }
          leaf UnicastPacketsSent {
            type uint64;
            description
              "The total number of packets requested for
               transmission which were not addressed to a
               multicast or broadcast address at this layer,
               including those that were discarded or not sent.";
          }
          leaf UnicastPacketsReceived {
            type uint64;
            description
              "The total number of received packets, delivered by
               this layer to a higher layer, which were not
               addressed to a multicast or broadcast address at
               this layer.";
          }
          leaf DiscardPacketsSent {
            type uint32;
            description
              "The total number of outbound packets which were
               chosen to be discarded even though no errors had
               been detected to prevent their being transmitted.
               One possible reason for discarding such a packet
               could be to free up buffer space.";
          }
          leaf DiscardPacketsReceived {
            type uint32;
            description
              "The total number of inbound packets which were chosen
               to be discarded even though no errors had been
               detected to prevent their being delivered.  One
               possible reason for discarding such a packet could
               be to free up buffer space.";
          }
          leaf MulticastPacketsSent {
            type uint64;
            description
              "The total number of packets that higher-level
               protocols requested for transmission and which
               were addressed to a multicast address at this
               layer, including those that were discarded or not
               sent.";
          }
          leaf MulticastPacketsReceived {
            type uint64;
            description
              "The total number of received packets, delivered by
               this layer to a higher layer, which were addressed
               to a multicast address at this layer.";
          }
          leaf BroadcastPacketsSent {
            type uint64;
            description
              "The total number of packets that higher-level
               protocols requested for transmission and which
               were addressed to a broadcast address at this
               layer, including those that were discarded or not
               sent.";
          }
          leaf BroadcastPacketsReceived {
            type uint64;
            description
              "The total number of received packets, delivered by
               this layer to a higher layer, which were addressed
               to a broadcast address at this layer.";
          }
          leaf UnknownProtoPacketsReceived {
            type uint32;
            description
              "The total number of packets received via the
               interface which were discarded because of an
               unknown or unsupported protocol.";
          }
        }
      }
    }

    container USB {
      description
        "Universal Serial Bus ({{bibref|USB1.0}}, {{bibref|USB2.0}},
         {{bibref|USB3.0}}).  This object contains the
         {{object|Interface}}, {{object|Port}}, and
         {{object|USBHosts}} objects.";

      list Interface {
        key "Alias";
        description
          "USB interface table (a stackable interface object as
           described in {{bibref|TR-181i2|Section 4.2}}).  This
           table models master and slave USB physical interfaces
           that support carrying Ethernet frames, e.g.  via the
           USB Communication Device Class.";
        leaf Enable {
          type boolean;
          description
            "Enables or disables the interface.
          
             This parameter is based on ''ifAdminStatus'' from
             {{bibref|RFC2863}}.";
        }
        leaf Status {
          type enumeration {
            enum "Up";
            enum "Down";
            enum "Unknown";
            enum "Dormant";
            enum "NotPresent";
            enum "LowerLayerDown";
            enum "Error";
          }
          config false;
          description
            "The current operational state of the interface (see
             {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the interface as assigned by the
             CPE.";
        }
        leaf LastChange {
          type uint32;
          config false;
          description
            "The accumulated time in {{units}} since the interface
             entered its current operational state.";
        }
        leaf LowerLayers {
          type string;
          description
            "{{list}} {{reference|an interface object that is
             stacked immediately below this interface object}}
             See {{bibref|TR-181i2|Section 4.2.1}}.
          
             Note: Since {{object}} is a layer 1 interface, it is
             expected that {{param}} will not be used.";
        }
        leaf Upstream {
          type boolean;
          config false;
          description
            "Indicates whether the interface points towards the
             Internet ({{true}}) or towards End Devices
             ({{false}}).
          
             For example:
          
             * For an Internet Gateway Device, {{param}} will be
             {{true}} for all WAN interfaces and {{false}} for
             all LAN interfaces.
          
             * For a standalone WiFi Access Point that is
             connected via Ethernet to an Internet Gateway
             Device, {{param}} will be {{true}} for the Ethernet
             interface and {{false}} for the WiFi Radio
             interface.
          
             * For an End Device, {{param}} will be {{true}} for
             all interfaces.";
        }
        leaf MACAddress {
          type types:MACAddress;
          config false;
          description
            "The MAC Address of the interface.
          
             Note: This is not necessarily the same as the
             Ethernet header source or destination MAC address,
             which is associated with the IP interface and is
             modeled via the
             {{param|.Ethernet.Link.{i}.MACAddress}} parameter.";
        }
        leaf MaxBitRate {
          type uint32;
          config false;
          description
            "The maximum PHY bit rate supported by this interface
             (expressed in {{units}}).";
        }
        leaf Port {
          type string {
            length "0..256";
          }
          config false;
          description
            "{{reference}} This is the USB port associated with this
             interface object.";
        }

        container Stats {
          config false;
          description
            "Throughput statistics for this interface.
          
             The CPE MUST reset the interface's Stats parameters
             (unless otherwise stated in individual object or
             parameter descriptions) either when the interface
             becomes operationally down due to a previous
             administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2|section 4.2.2}}.";
          leaf BytesSent {
            type uint64;
            description
              "The total number of bytes transmitted out of the
               interface, including framing characters.";
          }
          leaf BytesReceived {
            type uint64;
            description
              "The total number of bytes received on the interface,
               including framing characters.";
          }
          leaf PacketsSent {
            type uint64;
            description
              "The total number of packets transmitted out of the
               interface.";
          }
          leaf PacketsReceived {
            type uint64;
            description
              "The total number of packets received on the
               interface.";
          }
          leaf ErrorsSent {
            type uint32;
            description
              "The total number of outbound packets that could not
               be transmitted because of errors.";
          }
          leaf ErrorsReceived {
            type uint32;
            description
              "The total number of inbound packets that contained
               errors preventing them from being delivered to a
               higher-layer protocol.";
          }
          leaf UnicastPacketsSent {
            type uint64;
            description
              "The total number of packets requested for
               transmission which were not addressed to a
               multicast or broadcast address at this layer,
               including those that were discarded or not sent.";
          }
          leaf UnicastPacketsReceived {
            type uint64;
            description
              "The total number of received packets, delivered by
               this layer to a higher layer, which were not
               addressed to a multicast or broadcast address at
               this layer.";
          }
          leaf DiscardPacketsSent {
            type uint32;
            description
              "The total number of outbound packets which were
               chosen to be discarded even though no errors had
               been detected to prevent their being transmitted.
               One possible reason for discarding such a packet
               could be to free up buffer space.";
          }
          leaf DiscardPacketsReceived {
            type uint32;
            description
              "The total number of inbound packets which were chosen
               to be discarded even though no errors had been
               detected to prevent their being delivered.  One
               possible reason for discarding such a packet could
               be to free up buffer space.";
          }
          leaf MulticastPacketsSent {
            type uint64;
            description
              "The total number of packets that higher-level
               protocols requested for transmission and which
               were addressed to a multicast address at this
               layer, including those that were discarded or not
               sent.";
          }
          leaf MulticastPacketsReceived {
            type uint64;
            description
              "The total number of received packets, delivered by
               this layer to a higher layer, which were addressed
               to a multicast address at this layer.";
          }
          leaf BroadcastPacketsSent {
            type uint64;
            description
              "The total number of packets that higher-level
               protocols requested for transmission and which
               were addressed to a broadcast address at this
               layer, including those that were discarded or not
               sent.";
          }
          leaf BroadcastPacketsReceived {
            type uint64;
            description
              "The total number of received packets, delivered by
               this layer to a higher layer, which were addressed
               to a broadcast address at this layer.";
          }
          leaf UnknownProtoPacketsReceived {
            type uint32;
            description
              "The total number of packets received via the
               interface which were discarded because of an
               unknown or unsupported protocol.";
          }
        }
      }

      list Port {
        key "Name";
        config false;
        description
          "USB Port table.  This table models master and slave USB
           physical ports on the device.";
        leaf Name {
          type string {
            length "0..64";
          }
          description
            "The textual name of the port.";
        }
        leaf Standard {
          type string {
            length "0..4";
          }
          description
            "USB specification version supported by the Port.
             Example: \"1.1\"";
        }
        leaf Type {
          type enumeration {
            enum "Host";
            enum "Hub";
            enum "Device";
          }
          description
            "Type of the USB connection.";
        }
        leaf Receptacle {
          type enumeration {
            enum "Standard-A";
            enum "Standard-B";
            enum "Powered-B";
            enum "Micro-AB";
            enum "Micro-B";
          }
          description
            "Receptacle of the port.";
        }
        leaf Rate {
          type enumeration {
            enum "Low";
            enum "Full";
            enum "High";
            enum "Super";
          }
          description
            "Current speed of the USB connection.  {{enum}}";
        }
        leaf Power {
          type enumeration {
            enum "Self";
            enum "Bus";
            enum "Unknown";
          }
          description
            "Power configuration of the USB connection.  {{enum}}
          
             Only applies when {{param|Type}} is
             {{enum|Device|Type}}.  In other cases value is
             {{enum|Unknown}}.";
        }
      }

      container USBHosts {
        description
          "This object models the CPE's USB Host controllers.
        
           See {{bibref|TR-157|Appendix I}} for Theory of
           Operation.";

        list Host {
          key "Name";
          description
            "Table of CPE USB Host controllers.";
          leaf Enable {
            type boolean;
            description
              "Enables or disables the USB Host controller.";
          }
          leaf Name {
            type string {
              length "0..64";
            }
            config false;
            description
              "User-readable host controller name.";
          }
          leaf Type {
            type enumeration {
              enum "OHCI";
              enum "EHCI";
              enum "UHCI";
              enum "xHCI";
            }
            config false;
            description
              "Type of USB Host";
          }
          leaf Reset {
            type boolean;
            description
              "When set to {{true}}, reset the Host Controller and
               apply the reset signaling (see
               {{bibref|USB2.0|Chapter 7.1.7.5}}) to all of the
               Host Controller Hub downstream ports.
            
               The value is not saved in the device's state and
               setting it to {{false}} has no effect.";
          }
          leaf PowerManagementEnable {
            type boolean;
            description
              "When set to {{true}}, {{param}} enables the Host
               Controller to invoke Power Management policy, i.e.
               controlled Suspend (see {{bibref|USB2.0}},
               Chapters 4.3.2, 7.1.7.6, and 11.9).
            
               When set to {{false}} {{param}} immediately
               disables the Host controller Power Management
               policy.";
          }
          leaf USBVersion {
            type string {
              length "0..4";
            }
            config false;
            description
              "USB specification version with which the controller
               complies.  Example: \"1.1\"";
          }

          list Device {
            key "DeviceNumber";
            config false;
            description
              "Table of connected USB devices.";
            leaf DeviceNumber {
              type uint32;
              description
                "Device number on USB bus.";
            }
            leaf USBVersion {
              type string {
                length "0..4";
              }
              description
                "USB specification version with which the device
                 complies.  Example: \"1.1\"";
            }
            leaf DeviceClass {
              type yang:hex-string {
                length "0..1";
              }
              description
                "Class Code as assigned by USB-IF.
              
                 When 0x00, each device specifies its own class
                 code.  When 0xFF, the class code is vendor
                 specified.";
            }
            leaf DeviceSubClass {
              type yang:hex-string {
                length "0..1";
              }
              description
                "Subclass code (assigned by USB-IF).";
            }
            leaf DeviceVersion {
              type uint32 {
                range "min..65535";
              }
              description
                "Device release number.";
            }
            leaf DeviceProtocol {
              type yang:hex-string {
                length "0..1";
              }
              description
                "Protocol code (assigned by USB-IF).";
            }
            leaf ProductID {
              type uint32 {
                range "min..65535";
              }
              description
                "Product ID (assigned by manufacturer).";
            }
            leaf VendorID {
              type uint32 {
                range "min..65535";
              }
              description
                "Vendor ID (assigned by USB-IF).";
            }
            leaf Manufacturer {
              type string {
                length "0..64";
              }
              description
                "Device Manufacturer string descriptor.";
            }
            leaf ProductClass {
              type string {
                length "0..64";
              }
              description
                "Device Product Class string descriptor.";
            }
            leaf SerialNumber {
              type string {
                length "0..64";
              }
              description
                "Device SerialNumber string descriptor.";
            }
            leaf Port {
              type uint32 {
                range "min..255";
              }
              description
                "Hub port on parent device.
              
                 0 when no parent.";
            }
            leaf USBPort {
              type string;
              description
                "{{reference}} This is a reference to the USB host
                 device to which this (external) USB device is
                 connected.";
            }
            leaf Rate {
              type enumeration {
                enum "Low";
                enum "Full";
                enum "High";
                enum "Super";
              }
              description
                "Speed of the USB device.  {{enum}}
              
                 Internal signaling between the connected USB
                 device and the USB Host Controller provide the
                 information needed to determine the negotiated
                 rate.";
            }
            leaf Parent {
              type string;
              description
                "{{reference}} This is a reference to the parent USB
                 device (e.g.  hub device).
              
                 This is {{empty}} for a device connected to the
                 Host controller (root hub).";
            }
            leaf MaxChildren {
              type uint32;
              description
                "Number of ports.  Only applies for hub device,
                 equal to 0 for other devices.";
            }
            leaf IsSuspended {
              type boolean;
              description
                "When {{true}} the associated Device is in a
                 suspended (i.e.  low-power) state (see
                 {{bibref|USB2.0|Chapter 11.9}}).
              
                 When {{false}} the associated Device is in any
                 of the other states specified by the USB 2.0
                 Device State Machine (see
                 {{bibref|USB2.0|Chapter 9.1.1}}).";
            }
            leaf IsSelfPowered {
              type boolean;
              description
                "When {{true}} the associated device is at least
                 partly powered by a local source (see
                 {{bibref|USB2.0|Chapter 9.4.5}}).
              
                 When {{false}} the associated device draws all
                 the current it needs from the USB bus.";
            }

            list Configuration {
              key "ConfigurationNumber";
              description
                "Table of device configurations.";
              leaf ConfigurationNumber {
                type uint32;
                description
                  "The identifier for each Device Configuration.";
              }

              list Interface {
                key "InterfaceNumber";
                description
                  "Table of device interface descriptors.";
                leaf InterfaceNumber {
                  type uint32 {
                    range "min..255";
                  }
                  description
                    "Number of this interface (from USB interface
                     descriptor).";
                }
                leaf InterfaceClass {
                  type yang:hex-string {
                    length "0..1";
                  }
                  description
                    "Class Code as assigned by USB-IF.
                  
                     When 0x00, each interface specifies its own
                     class code.  When 0xFF, the class code is
                     vendor specified.";
                }
                leaf InterfaceSubClass {
                  type yang:hex-string {
                    length "0..1";
                  }
                  description
                    "Subclass code (assigned by USB-IF).";
                }
                leaf InterfaceProtocol {
                  type yang:hex-string {
                    length "0..1";
                  }
                  description
                    "Protocol code (assigned by USB-IF).";
                }
              }
            }
          }
        }
      }
    }

    container HPNA {
      description
        "HPNA object that contains the {{object|Interface}} and
         {{object|Diagnostics}} objects.  The HPNA (also known as
         HomePNA) industry standard {{bibref|G.9954}} defines
         peer to peer communication for home networking over
         existing coax cables and telephone wiring within the
         home.";

      list Interface {
        key "Alias";
        description
          "HPNA interface table (a stackable interface object as
           described in {{bibref|TR-181i2|Section 4.2}}).  Each
           table entry models the PHY and MAC levels of an HPNA
           interface {{bibref|G.9954}}.";
        leaf Enable {
          type boolean;
          description
            "Enables or disables the interface.
          
             This parameter is based on ''ifAdminStatus'' from
             {{bibref|RFC2863}}.";
        }
        leaf Status {
          type enumeration {
            enum "Up";
            enum "Down";
            enum "Unknown";
            enum "Dormant";
            enum "NotPresent";
            enum "LowerLayerDown";
            enum "Error";
          }
          config false;
          description
            "The current operational state of the interface (see
             {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the interface as assigned by the
             CPE.";
        }
        leaf LastChange {
          type uint32;
          config false;
          description
            "The accumulated time in {{units}} since the interface
             entered its current operational state.";
        }
        leaf LowerLayers {
          type string;
          description
            "{{list}} {{reference|an interface object that is
             stacked immediately below this interface object}}
             See {{bibref|TR-181i2|Section 4.2.1}}.
          
             Note: Since {{object}} is a layer 1 interface, it is
             expected that {{param}} will not be used.";
        }
        leaf Upstream {
          type boolean;
          config false;
          description
            "Indicates whether the interface points towards the
             Internet ({{true}}) or towards End Devices
             ({{false}}).
          
             For example:
          
             * For an Internet Gateway Device, {{param}} will be
             {{true}} for all WAN interfaces and {{false}} for
             all LAN interfaces.
          
             * For a standalone WiFi Access Point that is
             connected via Ethernet to an Internet Gateway
             Device, {{param}} will be {{true}} for the Ethernet
             interface and {{false}} for the WiFi Radio
             interface.
          
             * For an End Device, {{param}} will be {{true}} for
             all interfaces.";
        }
        leaf MACAddress {
          type types:MACAddress;
          config false;
          description
            "The MAC Address of the interface.
          
             Note: This is not necessarily the same as the
             Ethernet header source or destination MAC address,
             which is associated with the IP interface and is
             modeled via the
             {{param|.Ethernet.Link.{i}.MACAddress}} parameter.";
        }
        leaf FirmwareVersion {
          type string {
            length "0..64";
          }
          config false;
          description
            "This interface's firmware version.";
        }
        leaf NodeID {
          type uint32;
          config false;
          description
            "The Node ID of this interface.";
        }
        leaf IsMaster {
          type boolean;
          config false;
          description
            "Whether this interface is the HPNA network master.";
        }
        leaf Synced {
          type boolean;
          config false;
          description
            "Whether this interface is synchronized with the HPNA
             network master.  If this interface is the HPNA
             network master, {{param}} MUST be {{true}}.";
        }
        leaf TotalSyncTime {
          type uint32;
          config false;
          description
            "Total time in {{units}} (since device reset) that this
             interface has been up and synchronized to the HPNA
             network master.";
        }
        leaf MaxBitRate {
          type uint32;
          config false;
          description
            "The maximum HPNA PHY bit rate (expressed in {{units}})
             of this interface.";
        }
        leaf NetworkUtilization {
          type uint32 {
            range "0..1000";
          }
          config false;
          description
            "Current HPNA network utilization (expressed in
             {{units}}).";
        }
        leaf PossibleConnectionTypes {
          type enumeration {
            enum "Phone";
            enum "Coax";
          }
          config false;
          description
            "{{list}} List items indicate the types of connections
             possible for this interface.  {{enum}}";
        }
        leaf ConnectionType {
          type string;
          description
            "{{list}} Connection type(s) for which the HPNA protocol
             is active.";
        }
        leaf PossibleSpectralModes {
          type enumeration {
            enum "A";
            enum "B";
            enum "C";
            enum "D";
          }
          config false;
          description
            "{{list}} List items indicate the spectral modes
             possible for this interface.  {{enum}}";
        }
        leaf SpectralMode {
          type string;
          description
            "Spectral mode for which the HPNA protocol is active.";
        }
        leaf MTU {
          type uint32;
          description
            "Maximum Transmission Unit for this HPNA interface
             (expressed in {{units}}).";
        }
        leaf NoiseMargin {
          type uint32;
          description
            "The desired noise margin for which the local HPNA
             interface has been configured (expressed in
             {{units}}).";
        }
        leaf DefaultNonLARQPER {
          type uint32;
          description
            "The desired packet error rate for which the local HPNA
             interface has been configured (expressed in 1E-8,
             e.g.  PER of 1.27E-6 will be presented as 127).";
        }
        leaf LARQEnable {
          type boolean;
          description
            "Enable or disable the Limited Automatic Repeat Request
             (LARQ) mechanism.";
        }
        leaf MinMulticastRate {
          type uint32;
          description
            "The minimum multicast (and broadcast) rate that can be
             negotiated on the HPNA network directly accessible
             via this interface (expressed in {{units}}).";
        }
        leaf NegMulticastRate {
          type uint32;
          config false;
          description
            "The negotiated multicast (and broadcast) rate on the
             HPNA network directly accessible via this interface
             (expressed in {{units}}).";
        }
        leaf MasterSelectionMode {
          type enumeration {
            enum "Automatic";
            enum "ForceEndpoint";
            enum "ForceMaster";
          }
          description
            "Master selection mode.  {{enum}}";
        }

        container Stats {
          config false;
          description
            "Throughput statistics for this interface.
          
             The CPE MUST reset the interface's Stats parameters
             (unless otherwise stated in individual object or
             parameter descriptions) either when the interface
             becomes operationally down due to a previous
             administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2|section 4.2.2}}.";
          leaf BytesSent {
            type uint64;
            description
              "The total number of bytes transmitted out of the
               interface, including framing characters.";
          }
          leaf BytesReceived {
            type uint64;
            description
              "The total number of bytes received on the interface,
               including framing characters.";
          }
          leaf PacketsSent {
            type uint64;
            description
              "The total number of packets transmitted out of the
               interface.";
          }
          leaf PacketsReceived {
            type uint64;
            description
              "The total number of packets received on the
               interface.";
          }
          leaf ErrorsSent {
            type uint32;
            description
              "The total number of outbound packets that could not
               be transmitted because of errors.";
          }
          leaf ErrorsReceived {
            type uint32;
            description
              "The total number of inbound packets that contained
               errors preventing them from being delivered to a
               higher-layer protocol.";
          }
          leaf UnicastPacketsSent {
            type uint64;
            description
              "The total number of packets requested for
               transmission which were not addressed to a
               multicast or broadcast address at this layer,
               including those that were discarded or not sent.";
          }
          leaf UnicastPacketsReceived {
            type uint64;
            description
              "The total number of received packets, delivered by
               this layer to a higher layer, which were not
               addressed to a multicast or broadcast address at
               this layer.";
          }
          leaf DiscardPacketsSent {
            type uint32;
            description
              "The total number of outbound packets which were
               chosen to be discarded even though no errors had
               been detected to prevent their being transmitted.
               One possible reason for discarding such a packet
               could be to free up buffer space.";
          }
          leaf DiscardPacketsReceived {
            type uint32;
            description
              "The total number of inbound packets which were chosen
               to be discarded even though no errors had been
               detected to prevent their being delivered.  One
               possible reason for discarding such a packet could
               be to free up buffer space.";
          }
          leaf MulticastPacketsSent {
            type uint64;
            description
              "The total number of packets that higher-level
               protocols requested for transmission and which
               were addressed to a multicast address at this
               layer, including those that were discarded or not
               sent.";
          }
          leaf MulticastPacketsReceived {
            type uint64;
            description
              "The total number of received packets, delivered by
               this layer to a higher layer, which were addressed
               to a multicast address at this layer.";
          }
          leaf BroadcastPacketsSent {
            type uint64;
            description
              "The total number of packets that higher-level
               protocols requested for transmission and which
               were addressed to a broadcast address at this
               layer, including those that were discarded or not
               sent.";
          }
          leaf BroadcastPacketsReceived {
            type uint64;
            description
              "The total number of received packets, delivered by
               this layer to a higher layer, which were addressed
               to a broadcast address at this layer.";
          }
          leaf UnknownProtoPacketsReceived {
            type uint32;
            description
              "The total number of packets received via the
               interface which were discarded because of an
               unknown or unsupported protocol.";
          }
        }

        container QoS {
          description
            "QoS configuration object.";

          list FlowSpec {
            key "Alias";
            description
              "Flow specification table.
            
               The {{object|.QoS.Classification}} table is used
               to classify ingress traffic, where
               {{param|.QoS.Classification.{i}.TrafficClass}} is
               one of the classification result outputs.  This
               ''TrafficClass'' value can be used to look up the
               appropriate {{object}} entry (i.e.  the {{object}}
               entry whose {{param|TrafficClasses}} list contains
               a matching traffic class).
            
               For enabled table entries, if
               {{param|TrafficClasses}} is {{empty}} then the
               table entry is inoperable and the CPE MUST set
               {{param|Status}} to
               {{enum|Error_Misconfigured|Status}}.";
            leaf Enable {
              type boolean;
              default "false";
              description
                "Enables or disables the table entry.";
            }
            leaf Status {
              type enumeration {
                enum "Disabled";
                enum "Enabled";
                enum "Error_Misconfigured";
                enum "Error";
              }
              config false;
              default "Disabled";
              description
                "The status of this entry.  {{enum}}
              
                 The {{enum|Error_Misconfigured}} value indicates
                 that a necessary configuration value is
                 undefined or invalid.
              
                 The {{enum|Error}} value MAY be used by the CPE
                 to indicate a locally defined error condition.";
            }
            leaf TrafficClasses {
              type uint32;
              default "";
              description
                "{{list}} This list identifies the set of traffic
                 classes associated with this flow spec.";
            }
            leaf FlowType {
              type enumeration {
                enum "CBR";
                enum "VBR";
                enum "VBR-NRT";
                enum "BE";
              }
              default "BE";
              description
                "Flow type.  {{enum}}";
            }
            leaf Priority {
              type uint32 {
                range "0..7";
              }
              default "0";
              description
                "Flow queue network priority.
              
                 Priority 0 is the lowest priority.";
            }
            leaf Latency {
              type uint32 {
                range "0..999";
              }
              default "0";
              description
                "Maximum latency of the flow (expressed in
                 {{units}}).
              
                 Value 0 means no latency requirements.";
            }
            leaf Jitter {
              type uint32 {
                range "0..999";
              }
              default "0";
              description
                "Maximum jitter of the flow (expressed in
                 {{units}}).
              
                 Value 0 means no jitter requirements.";
            }
            leaf PacketSize {
              type uint32 {
                range "0..max";
              }
              default "0";
              description
                "Typical packet size.
              
                 Value 0 means undefined packet size.";
            }
            leaf MinRate {
              type uint32;
              default "0";
              description
                "Minimum required rate in Kbps.
              
                 Value 0 means no MinRate requirements.";
            }
            leaf AvgRate {
              type uint32;
              default "0";
              description
                "Average required rate in Kbps.
              
                 Value 0 means no AvgRate requirements.";
            }
            leaf MaxRate {
              type uint32;
              default "0";
              description
                "Maximum required rate in Kbps.
              
                 Value 0 means no MaxRate requirements.";
            }
            leaf PER {
              type uint32;
              default "0";
              description
                "The desired packet error rate (expressed in 1E-8,
                 e.g.  PER of 1.27E-6 will be presented as 127).
              
                 Value 0 means no PER requirements.";
            }
            leaf Timeout {
              type uint32;
              default "0";
              description
                "Flow inactivity tear down timeout (expressed in
                 {{units}}).
              
                 Value 0 means unlimited timeout.";
            }
          }
        }

        list AssociatedDevice {
          key "MACAddress";
          description
            "This table provides information about other HPNA
             devices that are directly accessible via this HPNA
             interface.";
          leaf MACAddress {
            type types:MACAddress;
            config false;
            description
              "The physical address of this node.";
          }
          leaf NodeID {
            type uint32;
            config false;
            description
              "The Node ID of this node.";
          }
          leaf IsMaster {
            type boolean;
            config false;
            description
              "Whether this node is the HPNA network master.";
          }
          leaf Synced {
            type boolean;
            config false;
            description
              "Whether this node is synchronized with the HPNA
               network master.  If this node is the HPNA network
               master, {{param}} MUST be {{true}}.";
          }
          leaf TotalSyncTime {
            type uint32;
            config false;
            description
              "Total time in {{units}} (since device reset) that
               this node has been up and synchronized to the HPNA
               network master.";
          }
          leaf MaxBitRate {
            type uint32;
            config false;
            description
              "This node's maximum HPNA PHY bit rate (expressed in
               {{units}}).";
          }
          leaf PHYDiagnosticsEnable {
            type boolean;
            description
              "Enable / disable PHY throughput diagnostics mode on
               this node.  All devices that are enabled will
               participate in the HPNA network PHY throughput
               diagnostics process.";
          }
          leaf Active {
            type boolean;
            config false;
            description
              "Whether or not this node is currently present in the
               HPNA network.
            
               The ability to list inactive nodes is OPTIONAL.
               If the CPE includes inactive nodes in this table,
               {{param}} MUST be set to {{false}} for each
               inactive node.  The length of time an inactive
               node remains listed in this table is a local
               matter to the CPE.";
          }
        }
      }

      container Diagnostics {
        description
          "The HPNA Diagnostics object.";

        container PHYThroughput {
          description
            "HPNA PHY throughput diagnostics configuration and
             results.
          
             When diagnostics are requested, all HPNA nodes for
             which the
             {{param|##.Interface.{i}.AssociatedDevice.{i}.PHYDiagnosticsEnable}}
             parameter is set enter PHY diagnostics mode.";
          leaf DiagnosticsState {
            type enumeration {
              enum "None";
              enum "Requested";
              enum "Canceled";
              enum "Complete";
              enum "Error";
              enum "Error_FailToEnableCert";
              enum "Error_CertCmdTimeout";
              enum "Error_UnknownErr";
              enum "Error_UnsupportedOpcode";
              enum "Error_InvalidParam";
              enum "Error_UnsupportedCmdSegment";
              enum "Error_UnsupportedDataGen";
              enum "Error_InvalidSequence";
              enum "Error_InvalidFrame";
              enum "Eror_InvalidOpcode";
            }
            description
              "{{issue|A10-DIAG|No error state in original version}}
            
               {{datatype|expand}}";
          }
          leaf Interface {
            type string {
              length "0..256";
            }
            description
              "{{reference}} This is the interface over which the
               test is to be performed.";
          }
          leaf NumPacketsInBurst {
            type uint32;
            description
              "Number of test packet in burst to be send during PHY
               diagnostics test from each HPNA device to other
               HPNA device in the HPNA network.";
          }
          leaf BurstInterval {
            type uint32;
            description
              "Test packet burst interval length (expressed in
               {{units}}).";
          }
          leaf TestPacketPayloadLength {
            type uint32 {
              range "0..1480";
            }
            description
              "Payload length in the test packets.";
          }
          leaf PayloadEncoding {
            type uint32;
            description
              "HPNA payload encoding in PHY diagnostics.  0 is used
               for negotiated payload between devices according
               to line conditions.";
          }
          leaf PayloadDataGen {
            type uint32;
            description
              "Test packets payload data generator value.";
          }
          leaf PayloadType {
            type enumeration {
              enum "Pattern";
              enum "IncrementByte";
            }
            description
              "Test packets payload type.  {{enum}}
            
               In Pattern mode the PayloadDataGen value is
               repeated pattern in the payload.
            
               In IncrementByte mode LSByte in PayloadDataGen is
               used as first payload and next bytes in payload
               are incremented.";
          }
          leaf PriorityLevel {
            type uint32 {
              range "0..7";
            }
            description
              "Priority level of PHY diagnostics packets (0 lowest
               -7 highest).";
          }

          list Result {
            key "SrcMACAddress DestMACAddress";
            config false;
            description
              "PHY throughput diagnostics results.
            
               Each result object corresponds to unidirectional
               traffic between two PHY diagnostics-enabled nodes
               (so there are two such objects for each such
               pair).";
            leaf SrcMACAddress {
              type types:MACAddress;
              description
                "HPNA source MAC address.";
            }
            leaf DestMACAddress {
              type types:MACAddress;
              description
                "HPNA destination MAC address.";
            }
            leaf PHYRate {
              type uint32;
              description
                "PHY diagnostics HPNA PHY rate (expressed in
                 {{units}}).";
            }
            leaf BaudRate {
              type uint32;
              description
                "PHY Baud rate (expressed in {{units}}).";
            }
            leaf SNR {
              type uint32;
              description
                "PHY diagnostics SNR (expressed in {{units}}).";
            }
            leaf PacketsReceived {
              type uint32;
              description
                "Number of received packets in PHY diagnostics mode.";
            }
            leaf Attenuation {
              type uint32;
              description
                "Measured attenuation (expressed in {{units}}).";
            }
          }
        }

        container PerformanceMonitoring {
          description
            "HPNA performance monitoring configuration and results.
          
             Performance monitoring results are sampled from all
             nodes in the HPNA network.  All packet related
             counters are sampled synchronized at all nodes in
             the HPNA network in order to derive packet loss
             calculations in the HPNA network.";
          leaf DiagnosticsState {
            type enumeration {
              enum "None";
              enum "Requested";
              enum "Canceled";
              enum "Complete";
              enum "Error";
              enum "Error_SampleIntervalTooSmall";
            }
            description
              "{{issue|A10-DIAG|No error state in original version}}
            
               {{datatype|expand}}";
          }
          leaf Interface {
            type string {
              length "0..256";
            }
            description
              "{{reference}} This is the interface over which the
               test is to be performed.";
          }
          leaf SampleInterval {
            type uint32;
            description
              "Time in {{units}} between automatic collection of
               performance monitoring data.  A value of zero
               disables automatic collection of data.
            
               The CPE MAY impose a minimum sample interval, in
               which case an attempt to set a (non-zero) interval
               that is less than this minimum MUST set the
               interval to the minimum and MUST NOT be regarded
               as an error.
            
               If SampleInterval is a simple fraction of a day,
               e.g.  900 (a quarter of an hour) or 3600 (an
               hour), the CPE MAY choose to align sample
               intervals with time of day, but is not required to
               do so.";
          }

          container Nodes {
            config false;
            description
              "Per-node HPNA performance monitoring results.
            
               When automatic collection is enabled, i.e.
               {{param|#.SampleInterval}} is non-zero, the
               \"current\" interval is defined by the most recent
               automatic sample and the most recent subsequent
               manual sample, if any.
            
               When automatic collection is disabled, i.e.
               SampleInterval is zero, the \"current\" interval
               is defined by the three most recent manual
               samples.
            
               Note: Packets in statistics counters are Ethernet
               packets.";
            leaf CurrentStart {
              type yang:date-and-time;
              description
                "Start time for the current interval.
              
                 When automatic collection is enabled, i.e.
                 SampleInterval is non-zero, the current interval
                 started at the most recent automatic sample.
              
                 When automatic collection is disabled, i.e.
                 SampleInterval is zero, the current interval
                 started two manual samples ago.";
            }
            leaf CurrentEnd {
              type yang:date-and-time;
              description
                "End time for the current interval.
              
                 When automatic collection is enabled, i.e.
                 SampleInterval is non-zero, the current interval
                 ended at the most recent manual sample since the
                 most recent automatic sample.  If there has been
                 no such manual sample, the current interval is
                 empty.
              
                 When automatic collection is disabled, i.e.
                 SampleInterval is zero, the current interval
                 ended at the most recent manual sample.";
            }

            list Node {
              key "MACAddress";
              min-elements 1;
              description
                "Per-node HPNA performance monitoring results during
                 the current sample interval.  Each table entry
                 contains the results collected between an HPNA
                 node (as indicated by {{param|MACAddress}}) and
                 the local HPNA interface (as indicated by
                 {{param|##.Interface}}).
              
                 Note: Packet counters indicate the number of
                 packets received between
                 {{param|#.CurrentStart}} and
                 {{param|#.CurrentEnd}}.";
              leaf MACAddress {
                type types:MACAddress;
                description
                  "The MAC address of the HPNA node.";
              }
              leaf BytesSent {
                type uint64;
                description
                  "The total number of bytes sent by host equipment
                   for transmission on the HPNA interface.";
              }
              leaf BytesReceived {
                type uint64;
                description
                  "The total number of received bytes on the HPNA
                   interface destined for the host equipment.";
              }
              leaf PacketsSent {
                type uint64;
                description
                  "The total number of packets sent by host
                   equipment for transmission on the HPNA
                   interface.  Number includes also short error
                   packets and control packets.";
              }
              leaf PacketsReceived {
                type uint64;
                description
                  "The total number of good packets received on the
                   HPNA interface destined for the host
                   equipment.";
              }
              leaf BroadcastPacketsSent {
                type uint64;
                description
                  "The number of broadcast packets transmitted on
                   the HPNA interface.";
              }
              leaf BroadcastPacketsReceived {
                type uint64;
                description
                  "The number of broadcast packets received on the
                   HPNA interface.";
              }
              leaf MulticastPacketsSent {
                type uint64;
                description
                  "The number of multicast packets transmitted on
                   the HPNA interface.";
              }
              leaf MulticastPacketsReceived {
                type uint64;
                description
                  "The number of multicast packets received on the
                   HPNA interface.";
              }
              leaf PacketsCrcErrored {
                type uint32;
                description
                  "The number of packets received on the HPNA
                   interface with CRC errors.";
              }
              leaf PacketsCrcErroredHost {
                type uint32;
                description
                  "The number of CRC error packets received on the
                   HPNA interface destined for the host
                   equipment.";
              }
              leaf PacketsShortErrored {
                type uint32;
                description
                  "The number of packets received on the HPNA
                   interface that are too short to be valid.";
              }
              leaf PacketsShortErroredHost {
                type uint32;
                description
                  "The number packets sent by the host equipment
                   that are too short to be valid.";
              }
              leaf RxPacketsDropped {
                type uint32;
                description
                  "The number of received packets dropped due to
                   lack of resources.";
              }
              leaf TxPacketsDropped {
                type uint32;
                description
                  "The number packets sent by the host equipment for
                   transmission on the HPNA interface but dropped
                   due to lack of resources.";
              }
              leaf ControlRequestLocal {
                type uint32;
                description
                  "The number of HPNA control request packets from
                   local host.";
              }
              leaf ControlReplyLocal {
                type uint32;
                description
                  "The number of HPNA control reply packets to local
                   host.";
              }
              leaf ControlRequestRemote {
                type uint32;
                description
                  "The number of HPNA control request packets from
                   remote host.";
              }
              leaf ControlReplyRemote {
                type uint32;
                description
                  "The number of HPNA control reply packets to
                   remote host.";
              }
              leaf PacketsSentWire {
                type uint64;
                description
                  "The total number of packets transmitted to wire.";
              }
              leaf BroadcastPacketsSentWire {
                type uint64;
                description
                  "The total number of broadcast packets transmitted
                   to wire.";
              }
              leaf MulticastPacketsSentWire {
                type uint64;
                description
                  "The total number of multicast packets transmitted
                   to wire.";
              }
              leaf PacketsInternalControl {
                type uint32;
                description
                  "The number of HPNA control request packets from
                   internal node.";
              }
              leaf BroadcastPacketsInternalControl {
                type uint32;
                description
                  "The number of HPNA broadcast control request
                   packets from internal node.";
              }
              leaf PacketsReceivedQueued {
                type uint32;
                description
                  "The number of received packets queued on host
                   output queues.";
              }
              leaf PacketsReceivedForwardUnknown {
                type uint32;
                description
                  "The number of packets received and forwarded to
                   unknown hosts.";
              }
              leaf NodeUtilization {
                type uint32 {
                  range "0..1000";
                }
                description
                  "The node utilization (expressed in {{units}}).";
              }
            }
          }

          container Channels {
            config false;
            description
              "Per-channel HPNA performance monitoring results.
            
               Note: channels are unidirectional.";
            leaf TimeStamp {
              type yang:date-and-time;
              description
                "Time at which channel data was last collected.";
            }

            list Channel {
              key "HostSrcMACAddress HostDestMACAddress";
              description
                "Per-channel HPNA performance monitoring results.";
              leaf HostSrcMACAddress {
                type types:MACAddress;
                description
                  "The host source MAC address associated with the
                   channel.";
              }
              leaf HostDestMACAddress {
                type types:MACAddress;
                description
                  "The host destination MAC address associated with
                   the channel.";
              }
              leaf HPNASrcMACAddress {
                type types:MACAddress;
                description
                  "The HPNA source MAC address associated with the
                   channel.";
              }
              leaf HPNADestMACAddress {
                type types:MACAddress;
                description
                  "The HPNA destination MAC address associated with
                   the channel.";
              }
              leaf PHYRate {
                type uint32;
                description
                  "Channel PHY rate (expressed in {{units}}).";
              }
              leaf BaudRate {
                type uint32;
                description
                  "PHY Baud rate (expressed in {{units}}).";
              }
              leaf SNR {
                type uint32;
                description
                  "Channel actual SNR measured in receiver side
                   (expressed in {{units}}).";
              }
              leaf PacketsSent {
                type uint32;
                description
                  "Number of packets sent in the channel.";
              }
              leaf PacketsReceived {
                type uint32;
                description
                  "Pre-LARQ number of packets received in the
                   channel.";
              }
              leaf LARQPacketsReceived {
                type uint32;
                description
                  "Post-LARQ number of packets received in the
                   channel.  Valid only if LARQ is enabled.";
              }
              leaf FlowSpec {
                type string {
                  length "0..256";
                }
                description
                  "{{reference}} Identifies the ''FlowSpec''
                   associated with the channel.  This parameter
                   is only used for channels that correspond to
                   egress traffic from the local HPNA interface.
                
                   {{null}} means that the channel is not
                   associated with any specified flow
                   specification in the QoS object.";
              }
            }
          }
        }
      }
    }

    container MoCA {
      description
        "MoCA object that contains the {{object|Interface}} table
         {{bibref|MoCAv1.0}} {{bibref|MoCAv1.1}}.";

      list Interface {
        key "Alias";
        description
          "MoCA interface table (a stackable interface object as
           described in {{bibref|TR-181i2|Section 4.2}}).  Each
           table entry models the PHY and MAC levels of a MoCA
           interface {{bibref|MoCAv1.0}} {{bibref|MoCAv1.1}}.";
        leaf Enable {
          type boolean;
          description
            "Enables or disables the interface.
          
             This parameter is based on ''ifAdminStatus'' from
             {{bibref|RFC2863}}.";
        }
        leaf Status {
          type enumeration {
            enum "Up";
            enum "Down";
            enum "Unknown";
            enum "Dormant";
            enum "NotPresent";
            enum "LowerLayerDown";
            enum "Error";
          }
          config false;
          description
            "The current operational state of the interface (see
             {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the interface as assigned by the
             CPE.";
        }
        leaf LastChange {
          type uint32;
          config false;
          description
            "The accumulated time in {{units}} since the interface
             entered its current operational state.";
        }
        leaf LowerLayers {
          type string;
          description
            "{{list}} {{reference|an interface object that is
             stacked immediately below this interface object}}
             See {{bibref|TR-181i2|Section 4.2.1}}.
          
             Note: Since {{object}} is a layer 1 interface, it is
             expected that {{param}} will not be used.";
        }
        leaf Upstream {
          type boolean;
          config false;
          description
            "Indicates whether the interface points towards the
             Internet ({{true}}) or towards End Devices
             ({{false}}).
          
             For example:
          
             * For an Internet Gateway Device, {{param}} will be
             {{true}} for all WAN interfaces and {{false}} for
             all LAN interfaces.
          
             * For a standalone WiFi Access Point that is
             connected via Ethernet to an Internet Gateway
             Device, {{param}} will be {{true}} for the Ethernet
             interface and {{false}} for the WiFi Radio
             interface.
          
             * For an End Device, {{param}} will be {{true}} for
             all interfaces.";
        }
        leaf MACAddress {
          type types:MACAddress;
          config false;
          description
            "The MAC Address of the interface.
          
             Note: This is not necessarily the same as the
             Ethernet header source or destination MAC address,
             which is associated with the IP interface and is
             modeled via the
             {{param|.Ethernet.Link.{i}.MACAddress}} parameter.";
        }
        leaf FirmwareVersion {
          type string {
            length "0..64";
          }
          config false;
          description
            "This interface's firmware version.
          
             This parameter is based on ''mocaIfSoftwareVersion''
             from {{bibref|MOCA11-MIB}}.";
        }
        leaf MaxBitRate {
          type uint32;
          config false;
          description
            "The maximum MoCA PHY bit rate (expressed in {{units}}).";
        }
        leaf MaxIngressBW {
          type uint32;
          config false;
          description
            "The maximum bandwidth of this interface for flows onto
             the MoCA network in {{units}}.
          
             This parameter is based on
             ''mocaIfMaxIngressNodeBw'' from
             {{bibref|MOCA11-MIB}}.";
        }
        leaf MaxEgressBW {
          type uint32;
          config false;
          description
            "The maximum bandwidth of this interface for flows from
             the MoCA network in {{units}}.
          
             This parameter is based on ''mocaIfMaxEgressNodeBw''
             from {{bibref|MOCA11-MIB}}.";
        }
        leaf HighestVersion {
          type string {
            length "0..64";
            pattern "\d+(\.\d+)*";
          }
          config false;
          description
            "Identifies the highest MoCA version that this interface
             supports.
          
             This element MUST be in the form of dot-delimited
             integers, where each successive integer represents a
             more minor category of variation.  For example, 1.0,
             where the components mean major.minor revision
             number.  {{pattern}}
          
             This parameter is based on ''mocaIfMocaVersion''
             from {{bibref|MOCA11-MIB}}.";
        }
        leaf CurrentVersion {
          type string {
            length "0..64";
            pattern "\d+(\.\d+)*";
          }
          config false;
          description
            "Identifies the MoCA version that the MoCA network is
             currently running.
          
             This element MUST be in the form of dot-delimited
             integers, where each successive integer represents a
             more minor category of variation.  For example, 1.0,
             where the components mean major.minor revision
             number.  {{pattern}}
          
             This parameter is based on ''mocaIfNetworkVersion''
             from {{bibref|MOCA11-MIB}}.";
        }
        leaf NetworkCoordinator {
          type uint32;
          config false;
          description
            "The Node ID of the current Network Coordinator (NC) for
             the MoCA network.
          
             This parameter is based on ''mocaIfNC'' from
             {{bibref|MOCA11-MIB}}.";
        }
        leaf NodeID {
          type uint32;
          config false;
          description
            "The Node ID of this interface.
          
             This parameter is based on ''mocaIfNodeID'' from
             {{bibref|MOCA11-MIB}}.";
        }
        leaf MaxNodes {
          type boolean;
          config false;
          description
            "The maximum network node capability supported by the
             interface.  If {{param}} is {{true}} then the
             interface supports 16 nodes (the maximum for a MoCA
             1.1 network).  If {{param}} is false then the
             interface supports 8 nodes (the maximum for a MoCA
             1.0 network).";
        }
        leaf PreferredNC {
          type boolean;
          description
            "Whether this interface is a preferred Network
             Coordinator (NC).
          
             This parameter is based on ''mocaIfPreferredNC''
             from {{bibref|MOCA11-MIB}}.";
        }
        leaf BackupNC {
          type uint32;
          config false;
          description
            "The Node ID of the backup Network Coordinator node.
          
             This parameter is based on ''mocaIfBackupNC'' from
             {{bibref|MOCA11-MIB}}.";
        }
        leaf PrivacyEnabledSetting {
          type boolean;
          description
            "The configured privacy mode.  This indicates whether
             link-layer security is enabled ({{true}}) or
             disabled ({{false}}) for network admission.
          
             The configured privacy setting MAY NOT match the
             current operational state
             ({{param|PrivacyEnabled}}), since this setting is
             only applied during network formation or admission.";
        }
        leaf PrivacyEnabled {
          type boolean;
          config false;
          description
            "Indicates whether link-layer security is enabled or
             disabled.
          
             This parameter is based on ''mocaIfPrivacyEnable''
             from {{bibref|MOCA11-MIB}}.";
        }
        leaf FreqCapabilityMask {
          type yang:hex-string {
            length "8";
          }
          config false;
          description
            "Hexadecimal encoded 64-bit mask of supported
             frequencies.  This is the bit map of the spectrum
             that the interface supports, and each bit represents
             25 MHz of spectrum.  The least significant bit of
             the rightmost character corresponds to 800MHz, which
             is the lowest frequency.
          
             For example, an interface that supports 1150 MHz
             through 1500 MHz would have a value of
             0x000000001FFFC000.
          
             This parameter is based on ''mocaIfCapabilityMask''
             from {{bibref|MOCA11-MIB}}.";
        }
        leaf FreqCurrentMaskSetting {
          type yang:hex-string {
            length "8";
          }
          description
            "The configured hexadecimal encoded 64-bit mask of
             enabled frequencies for network admission.
          
             The configured frequencies MAY NOT match the current
             operational state ({{param|FreqCurrentMask}}), since
             this setting is only applied during network
             formation or admission.";
        }
        leaf FreqCurrentMask {
          type yang:hex-string {
            length "8";
          }
          config false;
          description
            "Hexadecimal encoded 64-bit mask of used frequencies.
             This is the bit map of the spectrum that can be used
             and is a subset of the {{param|FreqCapabilityMask}}.
             Each bit represents 25 MHz of spectrum.  The least
             significant bit of the rightmost character
             corresponds to 800MHz, which is the lowest
             frequency.
          
             This parameter is based on ''mocaIfChannelMask''
             from {{bibref|MOCA11-MIB}}.";
        }
        leaf CurrentOperFreq {
          type uint32;
          config false;
          description
            "Current Operational Frequency.  The RF frequency in Hz
             to which the MoCA interface is currently tuned.
             This parameter is only valid when {{param|Status}}
             is {{enum|Up|Status}}.
          
             This parameter is based on ''mocaIfRFChannel'' from
             {{bibref|MOCA11-MIB}}.";
        }
        leaf LastOperFreq {
          type uint32;
          config false;
          description
            "Last Operational Frequency.  The RF frequency in Hz to
             which the MoCA interface was tuned when last in the
             {{enum|Up|Status}} state.
          
             This parameter is based on ''mocaIfLOF'' from
             {{bibref|MOCA11-MIB}}.";
        }
        leaf KeyPassphrase {
          type string {
            length "12..17";
            pattern "\d+";
          }
          description
            "MoCA Password.  The value consists of numeric
             characters (0-9).  {{pattern}}
          
             This parameter is based on ''mocaIfPassword'' from
             {{bibref|MOCA11-MIB}}.";
        }
        leaf TxPowerLimit {
          type uint32;
          description
            "Transmit Power attenuation in dB relative to the
             maximum transmit power.
          
             The MoCA interface SHOULD have {{param|Enable}} set
             to {{false}} for any change in this configuration.
             If the parameter is modified when {{param|Enable}}
             is {{true}} then this change might take several
             minutes to complete.
          
             This parameter is based on ''mocaIfTxPowerLimit''
             from {{bibref|MOCA11-MIB}}.";
        }
        leaf PowerCntlPhyTarget {
          type uint32;
          description
            "Target PHY rate in Mbps for the power control
             algorithm.
          
             The MoCA interface SHOULD have {{param|Enable}} set
             to {{false}} for any change in this configuration.
             If the parameter is modified when {{param|Enable}}
             is {{true}} then this change might take several
             minutes to complete.
          
             This parameter is based on
             ''mocaIfPowerControlTargetRate'' from
             {{bibref|MOCA11-MIB}}.";
        }
        leaf BeaconPowerLimit {
          type uint32;
          description
            "Beacon Transmit Power attenuation in {{units}} relative
             to the maximum transmit power.
          
             The MoCA interface SHOULD have {{param|Enable}} set
             to {{false}} for any change in this configuration.
             If the parameter is modified when {{param|Enable}}
             is {{true}} then this change might take several
             minutes to complete.
          
             This parameter is based on
             ''mocaIfBeaconPowerLimit'' from
             {{bibref|MOCA11-MIB}}.";
        }
        leaf NetworkTabooMask {
          type yang:hex-string {
            length "8";
          }
          config false;
          description
            "Hexadecimal encoded 64-bit mask of MoCA taboo channels
             identified for the home network.  This is the bit
             map of the spectrum that the interface supports, and
             each bit represents 25 MHz of spectrum.  The least
             significant bit of the rightmost character
             corresponds to 800MHz, which is the lowest
             frequency.
          
             This parameter is based on
             ''mocaIfTabooChannelMask'' from
             {{bibref|MOCA11-MIB}}.";
        }
        leaf NodeTabooMask {
          type yang:hex-string {
            length "8";
          }
          config false;
          description
            "Hexadecimal encoded 64-bit mask of supported
             frequencies.  This is the bit map of the spectrum
             that the interface supports, and each bit represents
             25 MHz of spectrum.  The least significant bit of
             the rightmost character corresponds to 800MHz, which
             is the lowest frequency.
          
             This parameter is based on
             ''mocaIfNodeTabooChannelMask'' from
             {{bibref|MOCA11-MIB}}.";
        }
        leaf TxBcastRate {
          type uint32;
          config false;
          description
            "The broadcast PHY transmit rate in {{units}} for this
             interface.
          
             This parameter is based on ''mocaIfTxGcdRate'' from
             {{bibref|MOCA11-MIB}}.";
        }
        leaf TxBcastPowerReduction {
          type uint32;
          config false;
          description
            "Transmit Power attenuation in {{units}} relative to the
             maximum transmit power for broadcast transmissions.
          
             This parameter is based on
             ''mocaIfTxGcdPowerReduction'' from
             {{bibref|MOCA11-MIB}}.";
        }
        leaf QAM256Capable {
          type boolean;
          config false;
          description
            "Whether this interface supports the 256 QAM feature.
          
             This parameter is based on ''mocaIfQAM256Capable''
             from {{bibref|MOCA11-MIB}}.";
        }
        leaf PacketAggregationCapability {
          type uint32 {
            range "0..10";
          }
          config false;
          description
            "The packet aggregation capability supported by the
             interface.  Standard values are 0 (no support), 6 (6
             {{units}}) or 10 (10 {{units}}).
          
             This parameter is based on
             ''mocaIfPacketsAggrCapability'' from
             {{bibref|MOCA11-MIB}}.";
        }

        container Stats {
          config false;
          description
            "Throughput statistics for this interface.
          
             The CPE MUST reset the interface's Stats parameters
             (unless otherwise stated in individual object or
             parameter descriptions) either when the interface
             becomes operationally down due to a previous
             administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2|section 4.2.2}}.";
          leaf BytesSent {
            type uint64;
            description
              "The total number of bytes transmitted out of the
               interface, including framing characters.";
          }
          leaf BytesReceived {
            type uint64;
            description
              "The total number of bytes received on the interface,
               including framing characters.";
          }
          leaf PacketsSent {
            type uint64;
            description
              "The total number of packets transmitted out of the
               interface.";
          }
          leaf PacketsReceived {
            type uint64;
            description
              "The total number of packets received on the
               interface.";
          }
          leaf ErrorsSent {
            type uint32;
            description
              "The total number of outbound packets that could not
               be transmitted because of errors.";
          }
          leaf ErrorsReceived {
            type uint32;
            description
              "The total number of inbound packets that contained
               errors preventing them from being delivered to a
               higher-layer protocol.";
          }
          leaf UnicastPacketsSent {
            type uint64;
            description
              "The total number of packets requested for
               transmission which were not addressed to a
               multicast or broadcast address at this layer,
               including those that were discarded or not sent.";
          }
          leaf UnicastPacketsReceived {
            type uint64;
            description
              "The total number of received packets, delivered by
               this layer to a higher layer, which were not
               addressed to a multicast or broadcast address at
               this layer.";
          }
          leaf DiscardPacketsSent {
            type uint32;
            description
              "The total number of outbound packets which were
               chosen to be discarded even though no errors had
               been detected to prevent their being transmitted.
               One possible reason for discarding such a packet
               could be to free up buffer space.";
          }
          leaf DiscardPacketsReceived {
            type uint32;
            description
              "The total number of inbound packets which were chosen
               to be discarded even though no errors had been
               detected to prevent their being delivered.  One
               possible reason for discarding such a packet could
               be to free up buffer space.";
          }
          leaf MulticastPacketsSent {
            type uint64;
            description
              "The total number of packets that higher-level
               protocols requested for transmission and which
               were addressed to a multicast address at this
               layer, including those that were discarded or not
               sent.";
          }
          leaf MulticastPacketsReceived {
            type uint64;
            description
              "The total number of received packets, delivered by
               this layer to a higher layer, which were addressed
               to a multicast address at this layer.";
          }
          leaf BroadcastPacketsSent {
            type uint64;
            description
              "The total number of packets that higher-level
               protocols requested for transmission and which
               were addressed to a broadcast address at this
               layer, including those that were discarded or not
               sent.";
          }
          leaf BroadcastPacketsReceived {
            type uint64;
            description
              "The total number of received packets, delivered by
               this layer to a higher layer, which were addressed
               to a broadcast address at this layer.";
          }
          leaf UnknownProtoPacketsReceived {
            type uint32;
            description
              "The total number of packets received via the
               interface which were discarded because of an
               unknown or unsupported protocol.";
          }
        }

        container QoS {
          config false;
          description
            "The QoS object provides information on MoCA
             parameterized QoS for this interface
             {{bibref|MoCAv1.1}}.";
          leaf EgressNumFlows {
            type uint32;
            description
              "The number of QoS flows that this interface has from
               the MoCA network.
            
               This parameter is based on
               ''mocaIfEgressNodeNumFlows'' from
               {{bibref|MOCA11-MIB}}.";
          }
          leaf IngressNumFlows {
            type uint32;
            description
              "The number of QoS flows that this interface has onto
               the MoCA network.
            
               This parameter is based on
               ''mocaIfIngressNodeNumFlows'' from
               {{bibref|MOCA11-MIB}}.";
          }

          list FlowStats {
            key "FlowID";
            description
              "The flow statistics table provides information on the
               MoCA parameterized QoS flows this interface has
               allocated onto the MoCA network.";
            leaf FlowID {
              type uint32;
              description
                "The flow ID used to identify a flow in the network.
              
                 This parameter is based on ''mocaIfFlowID'' from
                 {{bibref|MOCA11-MIB}}.";
            }
            leaf PacketDA {
              type types:MACAddress;
              description
                "The Destination Address (DA) for the packets in
                 this flow.
              
                 This parameter is based on ''mocaIfPacketDA''
                 from {{bibref|MOCA11-MIB}}.";
            }
            leaf MaxRate {
              type uint32;
              description
                "Maximum required rate in {{units}}.
              
                 This parameter is based on
                 ''mocaIfPeakDataRate'' from
                 {{bibref|MOCA11-MIB}}.";
            }
            leaf MaxBurstSize {
              type uint32;
              description
                "Maximum burst size.
              
                 This parameter is based on ''mocaIfBurstSize''
                 from {{bibref|MOCA11-MIB}}.";
            }
            leaf LeaseTime {
              type uint32;
              description
                "Flow lease time (expressed in {{units}}).
              
                 A {{param}} of 0 means unlimited lease time.
              
                 This parameter is based on ''mocaIfLeaseTime''
                 from {{bibref|MOCA11-MIB}}.";
            }
            leaf LeaseTimeLeft {
              type uint32;
              description
                "Flow lease time remaining (expressed in {{units}}).
              
                 If {{param|LeaseTime}} is 0 then a {{param}} of
                 0 means unlimited lease time; otherwise, a
                 {{param}} of 0 means expired.
              
                 This parameter is based on
                 ''mocaIfLeaseTimeLeft'' from
                 {{bibref|MOCA11-MIB}}.";
            }
            leaf FlowPackets {
              type uint32;
              description
                "The number of packets transmitted for this flow.
              
                 This parameter is based on
                 ''mocaIfTxPacketsFlow'' from
                 {{bibref|MOCA11-MIB}}.";
            }
          }
        }

        list AssociatedDevice {
          key "MACAddress";
          config false;
          description
            "This table contains information about other MoCA
             devices currently associated with this MoCA
             interface.";
          leaf MACAddress {
            type types:MACAddress;
            description
              "The MAC address of the associated device's MoCA
               interface.";
          }
          leaf NodeID {
            type uint32;
            description
              "The Node ID of this remote device.
            
               This parameter is based on ''mocaNodeIndex'' from
               {{bibref|MOCA11-MIB}}.";
          }
          leaf PreferredNC {
            type boolean;
            description
              "Whether this remote device is a preferred Network
               Coordinator (NC).
            
               This parameter is based on ''mocaNodePreferredNC''
               from {{bibref|MOCA11-MIB}}.";
          }
          leaf HighestVersion {
            type string {
              length "0..64";
              pattern "\d+(\.\d+)*";
            }
            description
              "Identifies the highest MoCA version that this remote
               device supports.
            
               This element MUST be in the form of dot-delimited
               integers, where each successive integer represents
               a more minor category of variation.  For example,
               1.0, where the components mean major.minor
               revision number.  {{pattern}}
            
               This parameter is based on ''mocaNodeMocaVersion''
               from {{bibref|MOCA11-MIB}}.";
          }
          leaf PHYTxRate {
            type uint32;
            description
              "The PHY transmit rate (in {{units}}) to this remote
               device.
            
               This parameter is based on ''mocaMeshTxRate'' from
               {{bibref|MOCA11-MIB}}.";
          }
          leaf PHYRxRate {
            type uint32;
            description
              "The PHY receive rate (in {{units}}) from this remote
               device.";
          }
          leaf TxPowerControlReduction {
            type uint32;
            description
              "The reduction in transmitter level (in {{units}}) due
               to power control.
            
               This parameter is based on
               ''mocaNodeTxPowerReduction'' from
               {{bibref|MOCA11-MIB}}.";
          }
          leaf RxPowerLevel {
            type uint32;
            description
              "The power level (in {{units}}) received at the MoCA
               interface from this remote device.
            
               This parameter is based on ''mocaNodeRxPower''
               from {{bibref|MOCA11-MIB}}.";
          }
          leaf TxBcastRate {
            type uint32;
            description
              "The broadcast PHY transmit rate (in {{units}}) from
               this remote device.
            
               This parameter is based on ''mocaNodeTxGcdRate''
               from {{bibref|MOCA11-MIB}}.";
          }
          leaf RxBcastPowerLevel {
            type uint32;
            description
              "The power level (in {{units}}) received at the MoCA
               interface from this remote device.
            
               This parameter is based on ''mocaNodeRxGcdPower''
               from {{bibref|MOCA11-MIB}}.";
          }
          leaf TxPackets {
            type uint32;
            description
              "The number of packets transmitted to this remote
               device (Note: Includes Broadcast, Multicast and
               Unicast packets).";
          }
          leaf RxPackets {
            type uint32;
            description
              "The number of packets received from this remote
               device (Note: Includes Broadcast, Multicast and
               Unicast packets).
            
               This parameter is based on ''mocaNodeRxPackets''
               from {{bibref|MOCA11-MIB}}.";
          }
          leaf RxErroredAndMissedPackets {
            type uint32;
            description
              "The number of errored and missed packets received
               from this remote device.
            
               This parameter is based on ''mocaNodeRxDrops''
               from {{bibref|MOCA11-MIB}}.";
          }
          leaf QAM256Capable {
            type boolean;
            description
              "Whether this remote device supports the 256 QAM
               feature.
            
               This parameter is based on
               ''mocaNodeQAM256Capable'' from
               {{bibref|MOCA11-MIB}}.";
          }
          leaf PacketAggregationCapability {
            type uint32 {
              range "0..10";
            }
            description
              "The packet aggregation capability supported by the
               remote device.  Standard values are 0 (no
               support), 6 (6 {{units}}) or 10 (10 {{units}}).
            
               This parameter is based on
               ''mocaNodePacketsAggrCapability'' from
               {{bibref|MOCA11-MIB}}.";
          }
          leaf RxSNR {
            type uint32;
            description
              "The signal to noise level (in {{units}}) received at
               this interface from this remote device.
            
               This parameter is based on ''mocaNodeSNR'' from
               {{bibref|MOCA11-MIB}}.";
          }
          leaf Active {
            type boolean;
            description
              "Whether or not this remote device is currently
               present in the MoCA network.
            
               The ability to list inactive nodes is OPTIONAL.
               If the CPE includes inactive nodes in this table,
               {{param}} MUST be set to {{false}} for each
               inactive node.  The length of time an inactive
               node remains listed in this table is a local
               matter to the CPE.";
          }
        }
      }
    }

    container Ghn {
      description
        "G.hn object that contains an {{object|Interface}} table for
         G.hn supported CPE.  The ITU-T G.hn specifications
         {{bibref|G.9960}} and {{bibref|G.9961}} define Physical
         and MAC Layers for communication between two or more
         G.hn nodes in the home network over multiple wired media
         such as power line, phone line and coaxial cable.";

      list Interface {
        key "Alias";
        description
          "G.hn interface table (a stackable interface object as
           described in {{bibref|TR-181i2|Section 4.2}}).  Each
           table entry models the PHY {{bibref|G.9960}} and MAC
           {{bibref|G.9961}} layers of a G.hn interface.";
        leaf Enable {
          type boolean;
          description
            "Enables or disables the interface.
          
             This parameter is based on ''ifAdminStatus'' from
             {{bibref|RFC2863}}.";
        }
        leaf Status {
          type enumeration {
            enum "Up";
            enum "Down";
            enum "Unknown";
            enum "Dormant";
            enum "NotPresent";
            enum "LowerLayerDown";
            enum "Error";
          }
          config false;
          description
            "The current operational state of the interface (see
             {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the interface as assigned by the
             CPE.";
        }
        leaf LastChange {
          type uint32;
          config false;
          description
            "The accumulated time in {{units}} since the interface
             entered its current operational state.";
        }
        leaf LowerLayers {
          type string;
          description
            "{{list}} {{reference|an interface object that is
             stacked immediately below this interface object}}
             See {{bibref|TR-181i2|Section 4.2.1}}.
          
             Note: Since {{object}} is a layer 1 interface, it is
             expected that {{param}} will not be used.";
        }
        leaf Upstream {
          type boolean;
          config false;
          description
            "Indicates whether the interface points towards the
             Internet ({{true}}) or towards End Devices
             ({{false}}).
          
             For example:
          
             * For an Internet Gateway Device, {{param}} will be
             {{true}} for all WAN interfaces and {{false}} for
             all LAN interfaces.
          
             * For a standalone WiFi Access Point that is
             connected via Ethernet to an Internet Gateway
             Device, {{param}} will be {{true}} for the Ethernet
             interface and {{false}} for the WiFi Radio
             interface.
          
             * For an End Device, {{param}} will be {{true}} for
             all interfaces.";
        }
        leaf MACAddress {
          type types:MACAddress;
          config false;
          description
            "The MAC Address of the interface, denoted as node MAC
             address or REGID in {{bibref|G.9961}}.
          
             Note: This is not necessarily the same as the
             Ethernet header source or destination MAC address,
             which is associated with the IP interface and is
             modeled via the
             {{param|.Ethernet.Link.{i}.MACAddress}} parameter.";
        }
        leaf FirmwareVersion {
          type string {
            length "0..64";
          }
          config false;
          description
            "The firmware version of the interface.";
        }
        leaf ConnectionType {
          status deprecated;
          type enumeration {
            enum "Powerline";
            enum "Phone";
            enum "Coax";
          }
          config false;
          description
            "This parameter is DEPRECATED because it has been
             replaced by {{param|MediumType}}.";
        }
        leaf MaxTransmitRate {
          type uint32;
          config false;
          description
            "The maximum PHY data rate that the interface is capable
             of transmitting (expressed in {{units}}).";
        }
        leaf TargetDomainNames {
          type string {
            length "0..32";
          }
          description
            "{{list}} Identifies the target domains configured by
             the user, as described in {{bibref|G.9961|Section
             8.6.1}}.  When registering or re-registering, the
             G.hn interface SHOULD try to register to one of
             these domains in the given order.";
        }
        leaf DomainName {
          type string {
            length "0..32";
          }
          config false;
          description
            "This is the domain name to which the interface is
             currently registered.
          
             {{empty}} indicates that the interface is currently
             not registered.";
        }
        leaf DomainNameIdentifier {
          type uint32;
          config false;
          description
            "The Domain Name Identifier, a shortened version of
             {{param|DomainName}}, denoted as DNI in
             {{bibref|G.9961|Section 8.6.11.2.1}}.";
        }
        leaf DomainId {
          type uint32;
          config false;
          description
            "The Domain Identifier of the domain to which the
             interface is registered, denoted as DOD in
             {{bibref|G.9961}}.";
        }
        leaf DeviceId {
          type uint32;
          config false;
          description
            "The Device Identifier assigned by the Domain Master,
             denoted as DEVICE_ID in {{bibref|G.9961}}.
          
             The value 0 indicates that the device is not
             currently registered.";
        }
        leaf MaxBitRate {
          type uint32;
          config false;
          description
            "The maximum PHY bit rate supported by this interface
             (expressed in {{units}}).";
        }
        leaf NodeTypeDMCapable {
          type boolean;
          config false;
          description
            "Indicates whether this interface has the capability to
             act as Domain Master in the G.hn domain.";
        }
        leaf DMRequested {
          type boolean;
          description
            "Indicates a request to force the role of the G.hn
             interface to Domain Master (DM) for the G.hn domain
             it is connected to.  The selection of the Domain
             Master follows the procedures described in
             {{bibref|G.9961|Clause 8.6.6}}.";
        }
        leaf IsDM {
          type boolean;
          config false;
          description
            "Indicates whether this G.hn interface is currently the
             Domain Master (DM) for the G.hn domain it is
             connected to, as described in {{bibref|G.9961|Clause
             8.6}}.";
        }
        leaf NodeTypeSCCapable {
          type boolean;
          config false;
          description
            "Indicates whether this interface has the capability to
             act as Security Controller in the G.hn domain.";
        }
        leaf SCRequested {
          type boolean;
          description
            "Indicates a request to force the role of the G.hn
             interface to Security Controller (SC) for the G.hn
             domain it is connected to.  The selection of the
             Security Controller follows the procedures described
             in {{bibref|G.9961|Clause 9.2}}.";
        }
        leaf IsSC {
          type boolean;
          config false;
          description
            "Indicates whether this G.hn interface is currently the
             Security Controller (SC) for the G.hn domain it is
             connected to, as described in {{bibref|G.9961|Clause
             9.2}}.";
        }
        leaf StandardVersions {
          type string;
          config false;
          description
            "The standard versions that the interface supports.  The
             list MUST have an even number of items.  The first
             item of each pair represents an ITU-T G.hn
             Recommendation while the second element of each pair
             represents the amendment version of the indicated
             Recommendation that this interface supports (the
             value 0 corresponds to the base Recommendation).
          
             For example, to indicate support for the G.9960 base
             document and G.9961 amendment 1, the corresponding
             list would be \"G9960,0,G9961,1\".";
        }
        leaf MaxBandPlan {
          type uint32;
          config false;
          description
            "The largest bandplan that the interface can support, as
             defined in {{bibref|G.9961|Clause 8.8.5.5}}.";
        }
        leaf MediumType {
          type enumeration {
            enum "PowerLineBaseband";
            enum "PhoneLineBaseband";
            enum "CoaxBaseband";
            enum "CoaxRF";
            enum "PlasticOpticalFiber";
          }
          config false;
          description
            "The medium type that the interface currently operates
             on.  Refer to {{bibref|G.9962|Table 7-5}}.";
        }
        leaf TAIFG {
          type uint32;
          config false;
          description
            "The Acknowledgement InterFrame Gap, or TAIFG, as
             defined in {{bibref|G.9961|Clause 8.4}}.  It is
             represented as multiples of {{units}}.";
        }
        leaf NotchedAmateurRadioBands {
          type yang:hex-string {
            length "0..2";
          }
          description
            "A bit map representing usage of international amateur
             bands (0 = masked, 1 = unmasked).  The LSB
             represents the lowest band (1.8-2.0 MHz), the second
             LSB represents the second lowest band (3.5-4.0 MHz),
             and so on.  The maximum value for this parameter is
             0x03FF, i.e.  it is a 10-bit quantity represented in
             16 bits and the top 6 bits are always zero.
          
             International Radio amateur bands are described in
             {{bibref|G.9964|Table D-1}} and conveyed by the
             Domain Master in the Amateur radio band descriptor
             (see {{bibref|G.9961|Table 8-77}}).";
        }
        leaf PHYThroughputDiagnosticsEnable {
          type string;
          description
            "Comma-separated list of DeviceIDs of nodes that need to
             enable their PHY throughput diagnostics mode.  All
             devices that are enabled will participate in the
             G.hn network PHY throughput diagnostics process.";
        }
        leaf PerformanceMonitoringDiagnosticsEnable {
          type string;
          description
            "Comma-separated list of DeviceIDs of nodes that need to
             enable their Performance Monitoring diagnostics mode
             on this node.  All devices that are enabled will
             participate in the G.hn network Performance
             Monitoring diagnostics process.";
        }
        leaf NodeTypeDMConfig {
          type boolean;
          description
            "Requests the interface to become the Domain Master in
             the G.hn domain.
          
             This parameter is valid only if
             {{param|NodeTypeDMCapable}} is {{true}}.
          
             Note that, if more than one node is configured to
             act as Domain Master, G.hn specifies a protocol to
             ensure only one device actually becomes DM.";
        }
        leaf NodeTypeDMStatus {
          type boolean;
          config false;
          description
            "Indicates whether the interface is acting as Domain
             Master ({{true}}) or not ({{false}}).
          
             See Note in {{param|NodeTypeDMConfig}} regarding the
             possibility of more than one node being configured
             with {{param|NodeTypeDMConfig}} = {{true}}.";
        }
        leaf NodeTypeSCStatus {
          type boolean;
          config false;
          description
            "Indicates whether the interface is acting as Security
             Controller ({{true}}) or not ({{false}}).";
        }

        container DMInfo {
          description
            "This object specifies management parameters pertaining
             to the domain functionality (Domain Master function;
             see {{bibref|G.9961|Clause 8.6}}).  The object
             exists only on G.hn interfaces that are currently
             the Domain Master, i.e.  for which parameter
             {{param|#.IsDM}} is {{true}}.";
          leaf DomainName {
            type yang:hex-string {
              length "0..32";
            }
            description
              "This is the domain name to which the interface is
               currently registered.  {{empty}} indicates that
               the interface is currently not registered.";
          }
          leaf DomainNameIdentifier {
            type yang:hex-string {
              length "0..2";
            }
            config false;
            description
              "The Domain Name Identifier, a shortened version of
               {{param|DomainName}}, denoted as DNI in
               {{bibref|G.9961|Section 8.6.11.2.1}}.";
          }
          leaf DomainId {
            type uint32;
            config false;
            description
              "The Domain Identifier of the domain to which the
               interface is registered, denoted as DOD in
               {{bibref|G.9961}}.";
          }
          leaf MACCycleDuration {
            type uint32 {
              range "0 | 10..200";
            }
            description
              "The MAC cycle duration, as specified in
               {{bibref|G.9961|Clause 8.4}}.  It is represented
               as multiples of {{units}}.  In the case of power
               line, writing to this parameter has no effect and
               it reads back as 0, which is a special value
               indicating that the MAC cycle is synchronized with
               2 AC cycles as defined in {{bibref|G.9961|Clause
               8.6.3.1}}.";
          }
          leaf SCDeviceId {
            type uint32;
            description
              "The DEVICE_ID of the Security Controller selected by
               the Domain Master.";
          }
          leaf SCMACAddress {
            type types:MACAddress;
            description
              "The REGID of the Security Controller selected by the
               Domain Master.";
          }
          leaf ReregistrationTimePeriod {
            type uint32 {
              range "5..63";
            }
            description
              "The time interval for periodic re-registration, as
               specified in {{bibref|G.9961|Clause 8.8.5.8}}.  It
               is represented as multiples of {{units}}.";
          }
          leaf TopologyPeriodicInterval {
            type uint32 {
              range "0..255";
            }
            description
              "The time interval that a node sends out the periodic
               topology update using TM_NodeTopologyChange.ind
               message, as specified in {{bibref|G.9961|Clause
               8.8.5.8.1}}.  It is represented as multiples of
               {{units}}.  The special value 0 represents an
               infinite interval (i.e., no periodic topology
               update).";
          }
          leaf MinSupportedBandplan {
            type uint32;
            description
              "Indicates the value of the minimal bandplan
               capability for a node that is allowed to register
               to the domain.";
          }
          leaf MaxSupportedBandplan {
            type uint32;
            description
              "Indicates the value of the minimal bandplan
               capability for a node that is allowed to register
               to the domain.";
          }
        }

        container SCInfo {
          description
            "This object specifies management parameters pertaining
             to the Security Controller functionality (Security
             Controller function; see {{bibref|G.9961|Clause
             9.2}}).  The object exists only on G.hn interfaces
             that are currently the Security Controller, i.e.
             for which parameter {{param|#.IsSC}} is {{true}}.";
          leaf ModesSupported {
            type enumeration {
              enum "NN";
              enum "NMK";
            }
            config false;
            description
              "The security modes that the Security Controller can
               support.  Refer to {{bibref|G.9961|Clause 9.2}}.";
          }
          leaf ModeEnabled {
            type string;
            description
              "The security mode in which the Security Controller is
               operating.";
          }
          leaf MICSize {
            type enumeration {
              enum "4-byte MIC";
              enum "8-byte MIC";
              enum "16-byte MIC";
            }
            description
              "The selected MIC size used in the domain.";
          }
          leaf Location {
            type boolean;
            config false;
            description
              "Indicates whether the Security Controller is above
               the L1 reference point.  It is set to {{true}} if
               the Security Controller is above the L1 reference
               point, and set to {{false}} otherwise.";
          }
        }

        list SMMaskedBand {
          key "BandNumber";
          max-elements 32;
          description
            "Specifies the list of masked bands to be applied to the
             G.hn interface.  This information is conveyed by the
             Domain Master in the SM descriptor as specified in
             {{bibref|G.9961|Table 8-77}}.
          
             Instances of this object are expected to exist only
             on G.hn interfaces that are currently the Domain
             Master, i.e.  for which parameter {{param|#.IsDM}}
             is {{true}}.";
          leaf Enable {
            type boolean;
            description
              "Enables or disables the {{object}}.";
          }
          leaf BandNumber {
            type uint32;
            description
              "The masked band number.";
          }
          leaf StartSubCarrier {
            type uint32;
            description
              "Index of the lowest frequency sub-carrier in the band
               to be masked as specified in {{bibref|G.9961|Table
               8-79}}.  This parameter is writable only on the
               interface which acts as the Domain Master.";
          }
          leaf StopSubCarrier {
            type uint32;
            description
              "Index of the highest frequency sub-carrier in the
               band to be masked as specified in Table 8-79 in
               {{bibref|G.9961}}.  This parameter is writable
               only on the interface which acts as the Domain
               Master.";
          }
        }

        container Stats {
          config false;
          description
            "Throughput statistics for this interface at the
             different G.hn reference points described in
             {{bibref|G.9961|Clause 8.1}}.
          
             The CPE MUST reset the interface's Stats parameters
             (unless otherwise stated in individual object or
             parameter descriptions) either when the interface
             becomes operationally down due to a previous
             administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2|section 4.2.2}}.";
          leaf BytesSent {
            type types:StatsCounter64;
            description
              "The total number of bytes transmitted out of the
               interface, including framing characters.
            
               More specifically, this is the total number of
               MPDU bytes transmitted or retransmitted by the
               node through a physical medium (i.e., PMI defined
               in {{bibref|G.9960|Clause 5.2.1}}), which
               correspond to data LPDUs (i.e., data packets) and
               framing overhead (e.g., LFH, LPH, LPCS defined in
               {{bibref|G.9961|Clause 8.1}}).  It does not
               include transmitted bytes contributed by
               management LPDUs (i.e., management packets).
            
               Note: LPDUs in mixed LLC frame blocks are
               considered data LPDUs.";
          }
          leaf BytesReceived {
            type types:StatsCounter64;
            description
              "The total number of bytes received on the interface,
               including framing characters.
            
               More specifically, this is the total number of
               MPDU bytes received by the node through a physical
               medium, which correspond to data LPDUs and framing
               overhead.  It does not include received bytes
               contributed by management LPDUs.  It can include
               blocks with errors.
            
               Note: LPDUs in mixed LLC frame blocks are
               considered data LPDUs.";
          }
          leaf PacketsSent {
            type types:StatsCounter64;
            description
              "The total number of packets transmitted out of the
               interface.
            
               More specifically, this is the total number of
               APDUs requested for transmission by a higher layer
               (i.e., outbound APDUs at the x1 reference point
               defined in {{bibref|G.9960|Clause 5.2.1}}) that
               were transmitted by the node through the physical
               medium.  It does not include transmitted LCDUs.";
          }
          leaf PacketsReceived {
            type types:StatsCounter64;
            description
              "The total number of packets received on the
               interface.
            
               More specifically, this is the total number of
               APDUs delivered to a higher layer (i.e., inbound
               APDUs at the x1 reference point) that were
               received by the node through the physical medium.
               It does not include received LCDUs.";
          }
          leaf ErrorsSent {
            type types:StatsCounter32;
            description
              "The total number of outbound packets that could not
               be transmitted because of errors.
            
               More specifically, this is the total number of
               APDUs that were requested for transmission by a
               higher layer (i.e., outbound APDUs at the x1
               reference point defined in {{bibref|G.9960|Clause
               5.2.1}}) but could not be transmitted because of
               errors (e.g., APDUs containing CRC errors).";
          }
          leaf ErrorsReceived {
            type types:StatsCounter32;
            description
              "The total number of inbound packets that contained
               errors preventing them from being delivered to a
               higher-layer protocol.
            
               More specifically, this is the total number of
               received APDUs that contained errors preventing
               them from being delivered to a higher layer (i.e.,
               inbound APDUs at the x1 reference point defined in
               {{bibref|G.9960|Clause 5.2.1}}).  The possible
               causes of error are: incorrect CRC, incorrect MIC,
               incorrect MIC size, and incorrect size of packet.";
          }
          leaf UnicastPacketsSent {
            type types:StatsCounter64;
            description
              "The total number of packets requested for
               transmission which were not addressed to a
               multicast or broadcast address at this layer,
               including those that were discarded or not sent.
            
               More specifically, this is the total number of
               APDUs that were requested for transmission by a
               higher layer (i.e., outbound APDUs at the x1
               reference point) and which were addressed to a
               unicast address at this layer.  It includes APDUs
               that were discarded or not sent.";
          }
          leaf UnicastPacketsReceived {
            type types:StatsCounter64;
            description
              "The total number of received packets, delivered by
               this layer to a higher layer, which were not
               addressed to a multicast or broadcast address at
               this layer.
            
               More specifically, this is the total number of
               received APDUs that were delivered to a higher
               layer (i.e., inbound APDUs at the x1 reference
               point) and which were addressed to a unicast
               address at this layer.";
          }
          leaf DiscardPacketsSent {
            type types:StatsCounter32;
            description
              "The total number of outbound packets which were
               chosen to be discarded even though no errors had
               been detected to prevent their being transmitted.
               One possible reason for discarding such a packet
               could be to free up buffer space.
            
               More specifically, this is the total number of
               APDUs that were requested for transmission by a
               higher layer (i.e., outbound APDUs at the x1
               reference point) but chosen to be discarded even
               though no errors had been detected to prevent
               their being transmitted (e.g., buffer overflow).";
          }
          leaf DiscardPacketsReceived {
            type types:StatsCounter32;
            description
              "The total number of inbound packets which were chosen
               to be discarded even though no errors had been
               detected to prevent their being delivered.  One
               possible reason for discarding such a packet could
               be to free up buffer space.
            
               More specifically, this is the total number of
               received APDUs that were chosen to be discarded
               even though no errors had been detected to prevent
               their being delivered.";
          }
          leaf MulticastPacketsSent {
            type types:StatsCounter64;
            description
              "The total number of packets that higher-level
               protocols requested for transmission and which
               were addressed to a multicast address at this
               layer, including those that were discarded or not
               sent.
            
               More specifically, this is the total number of
               APDUs that were requested for transmission by a
               higher layer (i.e., outbound APDUs at the x1
               reference point) and which were addressed to a
               multicast address at this layer.  It includes
               APDUs that were discarded or not sent.";
          }
          leaf MulticastPacketsReceived {
            type types:StatsCounter64;
            description
              "The total number of received packets, delivered by
               this layer to a higher layer, which were addressed
               to a multicast address at this layer.
            
               More specifically, this is the total number of
               received APDUs that were delivered to a higher
               layer (i.e., inbound APDUs at the x1 reference
               point) and which were addressed to a multicast
               address at this layer.";
          }
          leaf BroadcastPacketsSent {
            type types:StatsCounter64;
            description
              "The total number of packets that higher-level
               protocols requested for transmission and which
               were addressed to a broadcast address at this
               layer, including those that were discarded or not
               sent.
            
               More specifically, this is the total number of
               APDUs that were requested for transmission by a
               higher layer (i.e., outbound APDUs at the x1
               reference point) and which were addressed to a
               broadcast address at this layer.  It includes
               APDUs that were discarded or not sent.";
          }
          leaf BroadcastPacketsReceived {
            type types:StatsCounter64;
            description
              "The total number of received packets, delivered by
               this layer to a higher layer, which were addressed
               to a broadcast address at this layer.
            
               More specifically, this is the total number of
               received APDUs that were delivered to a higher
               layer (i.e., inbound APDUs at the x1 reference
               point) and which were addressed to a broadcast
               address at this layer.";
          }
          leaf UnknownProtoPacketsReceived {
            type types:StatsCounter32;
            description
              "The total number of packets received via the
               interface which were discarded because of an
               unknown or unsupported protocol.
            
               More specifically, this is the total number of
               APDUs received by the management that were
               discarded because of an unknown or unsupported
               protocol.";
          }
          leaf MgmtBytesSent {
            type types:StatsCounter64;
            description
              "The total number of MPDU bytes transmitted by the
               node through a physical medium, which correspond
               to management LPDUs and framing overhead.";
          }
          leaf MgmtBytesReceived {
            type types:StatsCounter64;
            description
              "The total number of MPDU bytes received by the node
               through a physical medium, which correspond to
               management LPDUs and framing overhead.";
          }
          leaf MgmtPacketsSent {
            type types:StatsCounter64;
            description
              "The total number of LCDUs requested for transmission
               by a management layer (i.e., outbound LCDUs
               generated in LLC defined in {{bibref|G.9961|Clause
               8.1.3}}) that were transmitted by the node through
               a physical medium.";
          }
          leaf MgmtPacketsReceived {
            type types:StatsCounter64;
            description
              "The total number of LCDUs delivered to a management
               layer (i.e., inbound LCDUs) that were received by
               the node through a physical medium.";
          }
          leaf BlocksSent {
            type types:StatsCounter64;
            description
              "The total number of LPDUs that were transmitted by
               the node through a physical medium, regardless of
               new or retransmitted LPDUs.";
          }
          leaf BlocksReceived {
            type types:StatsCounter64;
            description
              "The total number of LPDUs that were received by the
               node through a physical medium, with or without
               errors.";
          }
          leaf BlocksResent {
            type types:StatsCounter32;
            description
              "The total number of LPDUs that were retransmitted.";
          }
          leaf BlocksErrorsReceived {
            type types:StatsCounter32;
            description
              "The total number of received LPDUs that contained
               errors.
            
               Note the following relationships hold:
            
               * PacketsSent + ErrorsSent + DiscardPacketsSent =
               UnicastPacketsSent + MulticastPacketsSent +
               BroadcastPacketsSent.
            
               * PacketsReceived = UnicastPacketsReceived +
               MulticastPacketsReceived +
               BroadcastPacketsReceived.
            
               * Retransmission rate = BlocksResent / BlocksSent.
            
               * Block error rate = BlocksErrorReceived /
               BlocksReceived.";
          }
        }

        list AssociatedDevice {
          key "MACAddress";
          config false;
          description
            "This table contains information about other G.hn
             devices connected to this G.hn interface.";
          leaf MACAddress {
            type types:MACAddress;
            description
              "MAC address of remote G.hn device.
            
               This is denoted as REGID in {{bibref|G.9961}}.";
          }
          leaf DeviceId {
            type uint32;
            description
              "Device Id (as defined in G.hn) for the remote G.hn
               device, denoted as DEVICE_ID in {{bibref|G.9961}}.";
          }
          leaf TxPhyRate {
            type uint32;
            description
              "The PHY transmit Rate (expressed in {{units}}) to
               this remote device, denoted as PHY data rate in
               {{bibref|G.9961}}.
            
               Refer to Note 1 of {{bibref|G.9961|Table 8-48}}.
               To convert from the value in the table, divide by
               32K (32768) and round down.";
          }
          leaf RxPhyRate {
            type uint32;
            description
              "The PHY receive Rate (expressed in {{units}}) from
               this remote device, denoted as PHY data rate in
               {{bibref|G.9961}}.
            
               Refer to Note 1 of {{bibref|G.9961|Table 8-48}}.
               To convert from the value in the table, divide by
               32K (32768) and round down.";
          }
          leaf Active {
            type boolean;
            description
              "Whether or not this device is currently present in
               the G.hn domain.
            
               The ability to list inactive nodes is OPTIONAL.
               If the CPE includes inactive nodes in this table,
               {{param}} MUST be set to {{false}} for each
               inactive node.  The length of time an inactive
               node remains listed in this table is a local
               matter to the CPE.
            
               If {{param}} is {{true}}, it indicates that the
               Status of the remote device is 0, 1, or 2 (see
               {{bibref|G.9961|Table 7-3}}).";
          }
        }
      }

      container Diagnostics {
        description
          "The G.hn Diagnostics object.";

        container PHYThroughput {
          description
            "G.hn PHY throughput diagnostics configuration and
             results.
          
             When diagnostics are requested, all G.hn nodes for
             which the
             {{param|##.Interface.{i}.PHYThroughputDiagnosticsEnable}}
             parameter is set enter PHY diagnostics mode.";
          leaf DiagnosticsState {
            type enumeration {
              enum "None";
              enum "Requested";
              enum "Canceled";
              enum "Complete";
              enum "Error";
            }
            description
              "{{datatype|expand}}";
          }
          leaf Interface {
            type string;
            description
              "The interface over which the test is to be performed.";
          }
          leaf DiagnoseMACAddress {
            type types:MACAddress;
            description
              "The MAC address of the originating G.hn interface of
               the link that is being diagnosed.
            
               Note: This MAC address might belong to another
               node of the domain.";
          }

          list Result {
            key "DestinationMACAddress";
            config false;
            description
              "PHY throughput diagnostics results.";
            leaf DestinationMACAddress {
              type types:MACAddress;
              description
                "MAC address of the destination node of the link
                 being measured.";
            }
            leaf LinkState {
              type enumeration {
                enum "Direct";
                enum "NonDirect";
              }
              description
                "Indicates the state of the link between the G.hn
                 Interface with MAC address
                 {{param|#.DiagnoseMACAddress}} and the G.hn
                 Interface with MAC address
                 {{param|DestinationMACAddress}}.";
            }
            leaf TxPhyRate {
              type uint32;
              description
                "PHY data rate in transmit direction in the link
                 between the G.hn Interface with MAC address
                 {{param|#.DiagnoseMACAddress}} and the G.hn
                 Interface with MAC address
                 {{param|DestinationMACAddress}}.  It is
                 represented in {{units}} as defined in Note 1 to
                 {{bibref|G.9961|Table 8-48}}.  To convert from
                 the value in the table, divide by 32K (32768)
                 and round down.";
            }
            leaf RxPhyRate {
              type uint32;
              description
                "PHY data rate in receive direction in the link
                 between the G.hn Interface with MAC address
                 {{param|#.DiagnoseMACAddress}} and the G.hn
                 Interface with MAC address
                 {{param|DestinationMACAddress}}.  It is
                 represented in {{units}} as defined in Note 1 to
                 {{bibref|G.9961|Table 8-48}}.  To convert from
                 the value in the table, divide by 32K (32768)
                 and round down.";
            }
          }
        }

        container PerformanceMonitoring {
          description
            "G.hn Performance Monitoring diagnostics configuration
             and results.
          
             When diagnostics are requested, all G.hn nodes for
             which the
             {{param|##.Interface.{i}.PerformanceMonitoringDiagnosticsEnable}}
             parameter is set enter PHY diagnostics mode.";
          leaf DiagnosticsState {
            type enumeration {
              enum "None";
              enum "Requested";
              enum "Canceled";
              enum "Complete";
              enum "Error";
            }
            description
              "{{datatype|expand}}";
          }
          leaf Interface {
            type string;
            description
              "The interface over which the test is to be performed.";
          }
          leaf DiagnoseMACAddress {
            type types:MACAddress;
            description
              "The MAC address of the originating G.hn interface of
               the link that is being diagnosed.
            
               Note: This MAC address might belong to another
               node of the domain.";
          }
          leaf SampleInterval {
            type uint32;
            description
              "Time in {{units}} between automatic collection of
               performance monitoring data.  A value of zero
               disables automatic collection of data.
            
               The node MAY impose a minimum sample interval, in
               which case an attempt to set a (non-zero) interval
               that is less than this minimum MUST set the
               interval to the minimum and MUST NOT be regarded
               as an error.
            
               If SampleInterval is a simple fraction of a day,
               e.g.  900 (a quarter of an hour) or 3600 (an
               hour), the device MAY choose to align sample
               intervals with time of day, but is not required to
               do so.";
          }
          leaf SNRGroupLength {
            type uint32 {
              range "1 | 2 | 4 | 8 | 16 | 32 | 64 | 128 | 256";
            }
            description
              "The number of sub-carriers in a group to be used for
               averaging SNR values when providing SNR
               information for a channel.";
          }

          container Nodes {
            config false;
            description
              "Per-node G.hn performance monitoring results.
            
               When automatic collection is enabled, i.e.
               {{param|#.SampleInterval}} is non-zero, the
               \"current\" interval is defined by the most recent
               automatic sample and the most recent subsequent
               manual sample, if any.
            
               When automatic collection is disabled, i.e.
               SampleInterval is zero, the \"current\" interval
               is defined by the three most recent manual
               samples.
            
               Note: Packets in statistics counters are Ethernet
               packets.";
            leaf CurrentStart {
              type yang:date-and-time;
              description
                "Start time for the current interval.
              
                 When automatic collection is enabled, i.e.
                 SampleInterval is non-zero, the current interval
                 started at the most recent automatic sample.
              
                 When automatic collection is disabled, i.e.
                 SampleInterval is zero, the current interval
                 started two manual samples ago.";
            }
            leaf CurrentEnd {
              type yang:date-and-time;
              description
                "End time for the current interval.
              
                 When automatic collection is enabled, i.e.
                 SampleInterval is non-zero, the current interval
                 ended at the most recent manual sample since the
                 most recent automatic sample.  If there has been
                 no such manual sample, the current interval is
                 empty.
              
                 When automatic collection is disabled, i.e.
                 SampleInterval is zero, the current interval
                 ended at the most recent manual sample.";
            }

            list Node {
              key "DestinationMACAddress";
              min-elements 1;
              description
                "Per-node G.hn performance monitoring results during
                 the current sample interval.  Each table entry
                 contains the results collected between the G.hn
                 nodes with MAC addresses
                 {{param|##.DiagnoseMACAddress}}) and
                 {{param|DestinationMACAddress}}).
              
                 Note: Packet counters indicate the number of
                 packets received between
                 {{param|#.CurrentStart}} and
                 {{param|#.CurrentEnd}}.";
              leaf DestinationMACAddress {
                type types:MACAddress;
                description
                  "MAC address of the destination node of the link
                   being measured.";
              }
              leaf BytesSent {
                type types:StatsCounter64;
                description
                  "The total number of MPDU bytes transmitted or
                   retransmitted by the node through a physical
                   medium (i.e., PMI defined in
                   {{bibref|G.9960|Clause 5.2.1}}), which
                   correspond to data LPDUs (i.e., data packets)
                   and framing overhead (e.g., LFH, LPH, LPCS
                   defined in {{bibref|G.9961|Clause 8.1}}).  It
                   does not include transmitted bytes contributed
                   by management LPDUs (i.e., management
                   packets).
                
                   Note: LPDUs in mixed LLC frame blocks are
                   considered data LPDUs.";
              }
              leaf BytesReceived {
                type types:StatsCounter64;
                description
                  "The total number of MPDU bytes received by the
                   node through a physical medium, which
                   correspond to data LPDUs and framing overhead.
                   It does not include received bytes contributed
                   by management LPDUs.  It might include blocks
                   with errors.
                
                   Note: LPDUs in mixed LLC frame blocks are
                   considered data LPDUs.";
              }
              leaf PacketsSent {
                type types:StatsCounter64;
                description
                  "The total number of APDUs requested for
                   transmission by a higher layer (i.e., outbound
                   APDUs at the x1 reference point defined in
                   {{bibref|G.9960|Clause 5.2.1}}) that were
                   transmitted by the node through the physical
                   medium.  It does not include transmitted
                   LCDUs.";
              }
              leaf PacketsReceived {
                type types:StatsCounter64;
                description
                  "The total number of APDUs delivered to a higher
                   layer (i.e., inbound APDUs at the x1 reference
                   point) that were received by the node through
                   the physical medium.  It does not include
                   received LCDUs.";
              }
              leaf ErrorsSent {
                type types:StatsCounter32;
                description
                  "The total number of APDUs that were requested for
                   transmission by a higher layer (i.e., outbound
                   APDUs at the x1 reference point defined in
                   {{bibref|G.9960|Clause 5.2.1}}).  This
                   parameter represents the total number of LCDUs
                   requested for transmission by a management
                   layer (i.e., outbound LCDUs generated in LLC
                   defined in in {{bibref|G.9961|Clause 8.1.3}})
                   that were transmitted by the node through a
                   physical medium) but could not be transmitted
                   because of errors (e.g., APDUs containing CRC
                   errors).";
              }
              leaf ErrorsReceived {
                type types:StatsCounter32;
                description
                  "The total number of received APDUs that contained
                   errors preventing them from being delivered to
                   a higher layer (i.e., inbound APDUs at the x1
                   reference point defined in
                   {{bibref|G.9960|Clause 5.2.1}}).  The possible
                   causes of error are: incorrect CRC, incorrect
                   MIC, incorrect MIC size, and incorrect size of
                   packet.";
              }
              leaf UnicastPacketsSent {
                type types:StatsCounter64;
                description
                  "The total number of APDUs that were requested for
                   transmission by a higher layer (i.e., outbound
                   APDUs at the x1 reference point) and which
                   were addressed to a unicast address at this
                   layer.  It includes APDUs that were discarded
                   or not sent.";
              }
              leaf UnicastPacketsReceived {
                type types:StatsCounter64;
                description
                  "The total number of received APDUs that were
                   delivered to a higher layer (i.e., inbound
                   APDUs at the x1 reference point) and which
                   were addressed to a unicast address at this
                   layer.";
              }
              leaf DiscardPacketsSent {
                type types:StatsCounter32;
                description
                  "The total number of APDUs that were requested for
                   transmission by a higher layer (i.e., outbound
                   APDUs at the x1 reference point) but chosen to
                   be discarded even though no errors had been
                   detected to prevent their being transmitted
                   (e.g., buffer overflow).";
              }
              leaf DiscardPacketsReceived {
                type types:StatsCounter32;
                description
                  "The total number of received APDUs that were
                   chosen to be discarded even though no errors
                   had been detected to prevent their being
                   delivered.";
              }
              leaf MulticastPacketsSent {
                type types:StatsCounter64;
                description
                  "The total number of APDUs that were requested for
                   transmission by a higher layer (i.e., outbound
                   APDUs at the x1 reference point) and which
                   were addressed to a multicast address at this
                   layer.  It includes APDUs that were discarded
                   or not sent.";
              }
              leaf MulticastPacketsReceived {
                type types:StatsCounter64;
                description
                  "The total number of received APDUs that were
                   delivered to a higher layer (i.e., inbound
                   APDUs at the x1 reference point) and which
                   were addressed to a multicast address at this
                   layer.";
              }
              leaf BroadcastPacketsSent {
                type types:StatsCounter64;
                description
                  "The total number of APDUs that were requested for
                   transmission by a higher layer (i.e., outbound
                   APDUs at the x1 reference point) and which
                   were addressed to a broadcast address at this
                   layer.  It includes APDUs that were discarded
                   or not sent.";
              }
              leaf BroadcastPacketsReceived {
                type types:StatsCounter64;
                description
                  "The total number of received APDUs that were
                   delivered to a higher layer (i.e., inbound
                   APDUs at the x1 reference point) and which
                   were addressed to a broadcast address at this
                   layer.";
              }
              leaf UnknownProtoPacketsReceived {
                type types:StatsCounter32;
                description
                  "The total number of APDUs received by the
                   management that were discarded because of an
                   unknown or unsupported protocol.";
              }
              leaf MgmtBytesSent {
                type types:StatsCounter64;
                description
                  "The total number of MPDU bytes transmitted by the
                   node through a physical medium, which
                   correspond to management LPDUs and framing
                   overhead.";
              }
              leaf MgmtBytesReceived {
                type types:StatsCounter64;
                description
                  "The total number of MPDU bytes received by the
                   node through a physical medium, which
                   correspond to management LPDUs and framing
                   overhead.";
              }
              leaf MgmtPacketsSent {
                type types:StatsCounter64;
                description
                  "The total number of LCDUs requested for
                   transmission by a management layer (i.e.,
                   outbound LCDUs generated in LLC defined in
                   {{bibref|G.9961|Clause 8.1.3}}) that were
                   transmitted by the node through a physical
                   medium.";
              }
              leaf MgmtPacketsReceived {
                type types:StatsCounter64;
                description
                  "The total number of LCDUs delivered to a
                   management layer (i.e., inbound LCDUs) that
                   were received by the node through a physical
                   medium.";
              }
              leaf BlocksSent {
                type types:StatsCounter64;
                description
                  "The total number of LPDUs that were transmitted
                   by the node through a physical medium,
                   regardless of new or retransmitted LPDUs.";
              }
              leaf BlocksReceived {
                type types:StatsCounter64;
                description
                  "The total number of LPDUs that were received by
                   the node through a physical medium, with or
                   without errors.";
              }
              leaf BlocksResent {
                type types:StatsCounter32;
                description
                  "The total number of LPDUs that were
                   retransmitted.";
              }
              leaf BlocksErrorsReceived {
                type types:StatsCounter32;
                description
                  "The total number of received LPDUs that contained
                   errors.
                
                   Note the following relationships hold:
                
                   * PacketsSent + ErrorsSent +
                   DiscardPacketsSent = UnicastPacketsSent +
                   MulticastPacketsSent + BroadcastPacketsSent.
                
                   * PacketsReceived = UnicastPacketsReceived +
                   MulticastPacketsReceived +
                   BroadcastPacketsReceived.
                
                   * Retransmission rate = BlocksResent /
                   BlocksSent.
                
                   * Block error rate = BlocksErrorReceived /
                   BlocksReceived.";
              }
            }
          }

          container Channels {
            config false;
            description
              "Per-channel G.hn performance monitoring results.
            
               Note: channels are unidirectional.";
            leaf TimeStamp {
              type yang:date-and-time;
              description
                "Time at which channel data was last collected.";
            }

            list Channel {
              key "DestinationMACAddress";
              description
                "Per-channel G.hn performance monitoring results
                 during the current sample interval.  Each table
                 entry contains the results collected from the
                 channel between a G.hn interface (as indicated
                 by {{param|##.DiagnoseMACAddress}}) and a G.hn
                 interface indicated by
                 {{param|DestinationMACAddress}})";
              leaf DestinationMACAddress {
                type types:MACAddress;
                description
                  "MAC address of the destination node of the link
                   being measured.";
              }
              leaf SNR {
                type uint32;
                description
                  "The result of an SNR test performed over the
                   channel.  It is formatted as a comma-separated
                   list of N/M unsigned integers that represents
                   the result of Signal-to-Noise-Ratio
                   measurement averaging in groups of M
                   subcarriers.  The number N depends on the
                   bandplan used by the node and corresponds to
                   the OFDM control parameter N of each medium as
                   defined in {{bibref|G.9964}}.  The number M
                   corresponds to the parameter
                   {{param|##.SNRGroupLength}}.";
              }
            }
          }
        }
      }
    }

    container HomePlug {
      description
        "HomePlug object that contains the {{object|Interface}}
         table.  The HomePlug industry standard
         {{bibref|HPAV1.1}} defines peer to peer communication
         over powerline medium.";

      list Interface {
        key "Alias";
        description
          "HomePlug interface table (a stackable interface object as
           described in {{bibref|TR-181i2|Section 4.2}}).  Each
           table entry models the PHY and MAC levels of a
           HomePlug interface {{bibref|HPAV1.1}}.";
        leaf Enable {
          type boolean;
          description
            "Enables or disables the interface.
          
             This parameter is based on ''ifAdminStatus'' from
             {{bibref|RFC2863}}.";
        }
        leaf Status {
          type enumeration {
            enum "Up";
            enum "Down";
            enum "Unknown";
            enum "Dormant";
            enum "NotPresent";
            enum "LowerLayerDown";
            enum "Error";
          }
          config false;
          description
            "The current operational state of the interface (see
             {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the interface as assigned by the
             CPE.";
        }
        leaf LastChange {
          type uint32;
          config false;
          description
            "The accumulated time in {{units}} since the interface
             entered its current operational state.";
        }
        leaf LowerLayers {
          type string;
          description
            "{{list}} {{reference|an interface object that is
             stacked immediately below this interface object}}
             See {{bibref|TR-181i2|Section 4.2.1}}.
          
             Note: Since {{object}} is a layer 1 interface, it is
             expected that {{param}} will not be used.";
        }
        leaf Upstream {
          type boolean;
          config false;
          description
            "Indicates whether the interface points towards the
             Internet ({{true}}) or towards End Devices
             ({{false}}).
          
             For example:
          
             * For an Internet Gateway Device, {{param}} will be
             {{true}} for all WAN interfaces and {{false}} for
             all LAN interfaces.
          
             * For a standalone WiFi Access Point that is
             connected via Ethernet to an Internet Gateway
             Device, {{param}} will be {{true}} for the Ethernet
             interface and {{false}} for the WiFi Radio
             interface.
          
             * For an End Device, {{param}} will be {{true}} for
             all interfaces.";
        }
        leaf MACAddress {
          type types:MACAddress;
          config false;
          description
            "The MAC Address of the interface.
          
             Note: This is not necessarily the same as the
             Ethernet header source or destination MAC address,
             which is associated with the IP interface and is
             modeled via the
             {{param|.Ethernet.Link.{i}.MACAddress}} parameter.";
        }
        leaf LogicalNetwork {
          type string {
            length "0..64";
          }
          description
            "The textual name of the HomePlug Logical Network.";
        }
        leaf Version {
          type string {
            length "0..16";
          }
          config false;
          description
            "Indicates the HomePlug version of the interface.  This
             element SHOULD be in the form of dot-delimited
             integers, where each successive integer represents a
             more minor category of variation.  For example:
          
             : \"1.0\"
          
             : \"1.1\"";
        }
        leaf FirmwareVersion {
          type string {
            length "0..64";
          }
          config false;
          description
            "The firmware version of the interface.";
        }
        leaf ForceCCo {
          type boolean;
          default "false";
          description
            "Central Coordinator (CCo) selection mode.
          
             If {{false}}, CCo selection is automatic.  If
             {{true}}, the local HomePlug interface is forced to
             be CCo and all other devices in the Logical Network
             MUST be set to automatic CCo selection.
          
             Typically {{param}} is set to automatic CCo
             selection ({{false}}).";
        }
        leaf NetworkPassword {
          type string {
            length "0..32";
          }
          description
            "The network password of the device.  This is a human
             readable ASCII string that is hashed per the
             HomePlug specification to generate the Network
             Membership Key (NMK).  Note that care needs to be
             taken when setting this parameter as it might
             prohibit communication with other adapters or
             equipment connected via the powerline network.";
        }
        leaf OtherNetworksPresent {
          type string;
          config false;
          description
            "{{list}} Indicates whether any other HomePlug networks
             are currently visible via this interface.  Examples
             of valid list items include, but are not limited to:
          
             : \"HomePlugAV\"
          
             : \"HomePlug1.0\"
          
             : \"Other\"";
        }
        leaf MaxBitRate {
          type uint32;
          config false;
          description
            "The maximum PHY bit rate supported by this interface
             (expressed in {{units}}).";
        }

        container Stats {
          config false;
          description
            "Throughput statistics for this interface.
          
             The CPE MUST reset the interface's Stats parameters
             (unless otherwise stated in individual object or
             parameter descriptions) either when the interface
             becomes operationally down due to a previous
             administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2|section 4.2.2}}.";
          leaf BytesSent {
            type uint64;
            description
              "The total number of bytes transmitted out of the
               interface, including framing characters.";
          }
          leaf BytesReceived {
            type uint64;
            description
              "The total number of bytes received on the interface,
               including framing characters.";
          }
          leaf PacketsSent {
            type uint64;
            description
              "The total number of packets transmitted out of the
               interface.";
          }
          leaf PacketsReceived {
            type uint64;
            description
              "The total number of packets received on the
               interface.";
          }
          leaf ErrorsSent {
            type uint32;
            description
              "The total number of outbound packets that could not
               be transmitted because of errors.";
          }
          leaf ErrorsReceived {
            type uint32;
            description
              "The total number of inbound packets that contained
               errors preventing them from being delivered to a
               higher-layer protocol.";
          }
          leaf UnicastPacketsSent {
            type uint64;
            description
              "The total number of packets requested for
               transmission which were not addressed to a
               multicast or broadcast address at this layer,
               including those that were discarded or not sent.";
          }
          leaf UnicastPacketsReceived {
            type uint64;
            description
              "The total number of received packets, delivered by
               this layer to a higher layer, which were not
               addressed to a multicast or broadcast address at
               this layer.";
          }
          leaf DiscardPacketsSent {
            type uint32;
            description
              "The total number of outbound packets which were
               chosen to be discarded even though no errors had
               been detected to prevent their being transmitted.
               One possible reason for discarding such a packet
               could be to free up buffer space.";
          }
          leaf DiscardPacketsReceived {
            type uint32;
            description
              "The total number of inbound packets which were chosen
               to be discarded even though no errors had been
               detected to prevent their being delivered.  One
               possible reason for discarding such a packet could
               be to free up buffer space.";
          }
          leaf MulticastPacketsSent {
            type uint64;
            description
              "The total number of packets that higher-level
               protocols requested for transmission and which
               were addressed to a multicast address at this
               layer, including those that were discarded or not
               sent.";
          }
          leaf MulticastPacketsReceived {
            type uint64;
            description
              "The total number of received packets, delivered by
               this layer to a higher layer, which were addressed
               to a multicast address at this layer.";
          }
          leaf BroadcastPacketsSent {
            type uint64;
            description
              "The total number of packets that higher-level
               protocols requested for transmission and which
               were addressed to a broadcast address at this
               layer, including those that were discarded or not
               sent.";
          }
          leaf BroadcastPacketsReceived {
            type uint64;
            description
              "The total number of received packets, delivered by
               this layer to a higher layer, which were addressed
               to a broadcast address at this layer.";
          }
          leaf UnknownProtoPacketsReceived {
            type uint32;
            description
              "The total number of packets received via the
               interface which were discarded because of an
               unknown or unsupported protocol.";
          }
          leaf MPDUTxAck {
            type uint64;
            description
              "HomePlug-specific statistic.  The Number of MAC
               Protocol Data Units (MPDUs) Transmitted and
               Acknowledged.";
          }
          leaf MPDUTxCol {
            type uint64;
            description
              "HomePlug-specific statistic.  The Number of MAC
               Protocol Data Units (MPDUs) Transmitted and
               Collided";
          }
          leaf MPDUTxFailed {
            type uint64;
            description
              "HomePlug-specific statistic.  The Number of MAC
               Protocol Data Units (MPDUs) Transmitted and Failed";
          }
          leaf MPDURxAck {
            type uint64;
            description
              "HomePlug-specific statistic.  The Number of MAC
               Protocol Data Units (MPDUs) Received and
               Acknowledged";
          }
          leaf MPDURxFailed {
            type uint64;
            description
              "HomePlug-specific statistic.  The Number of MAC
               Protocol Data Units (MPDUs) Received and Failed";
          }
        }

        list AssociatedDevice {
          key "MACAddress";
          config false;
          description
            "This table contains information about other HomePlug
             devices connected to this HomePlug interface.";
          leaf MACAddress {
            type types:MACAddress;
            description
              "MAC address of remote HomePlug device.  It is used to
               uniquely identify and easily correlate with the
               connected remote HomePlug device.";
          }
          leaf TxPhyRate {
            type uint32;
            description
              "The PHY transmit Rate (expressed in {{units}}) to
               this remote device.";
          }
          leaf RxPhyRate {
            type uint32;
            description
              "The PHY receive Rate (expressed in {{units}}) from
               this remote device.";
          }
          leaf SNRPerTone {
            type uint32;
            description
              "{{list}} List items indicate Signal to Noise Ratio
               (SNR) per tone from this remote device (expressed
               in {{units}}).";
          }
          leaf AvgAttenuation {
            type uint32;
            description
              "Average attenuation from this remote device
               (expressed in {{units}}).";
          }
          leaf EndStationMACs {
            type types:MACAddress;
            description
              "{{list}} List items represent MAC addresses of end
               stations bridged by the remote HomePlug device.
            
               For example: \"11:22:33:AA:BB:CC,
               22:33:44:DD:EE:66\"";
          }
          leaf Active {
            type boolean;
            description
              "Whether or not this device is currently present in
               the HomePlug network.
            
               The ability to list inactive nodes is OPTIONAL.
               If the CPE includes inactive nodes in this table,
               {{param}} MUST be set to {{false}} for each
               inactive node.  The length of time an inactive
               node remains listed in this table is a local
               matter to the CPE.";
          }
        }
      }
    }

    container UPA {
      description
        "Universal Powerline Association {{bibref|UPA-PLC}}.  This
         object contains the {{object|Interface}} and
         {{object|Diagnostics}} objects.";

      list Interface {
        key "Alias";
        description
          "UPA interface table (a stackable interface object as
           described in {{bibref|TR-181i2|Section 4.2}}).  Each
           table entry models the PHY and MAC levels of a UPA
           interface {{bibref|UPA-PLC}}.";
        leaf Enable {
          type boolean;
          description
            "Enables or disables the interface.
          
             This parameter is based on ''ifAdminStatus'' from
             {{bibref|RFC2863}}.";
        }
        leaf Status {
          type enumeration {
            enum "Up";
            enum "Down";
            enum "Unknown";
            enum "Dormant";
            enum "NotPresent";
            enum "LowerLayerDown";
            enum "Error";
          }
          config false;
          description
            "The current operational state of the interface (see
             {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the interface as assigned by the
             CPE.";
        }
        leaf LastChange {
          type uint32;
          config false;
          description
            "The accumulated time in {{units}} since the interface
             entered its current operational state.";
        }
        leaf LowerLayers {
          type string;
          description
            "{{list}} {{reference|an interface object that is
             stacked immediately below this interface object}}
             See {{bibref|TR-181i2|Section 4.2.1}}.
          
             Note: Since {{object}} is a layer 1 interface, it is
             expected that {{param}} will not be used.";
        }
        leaf Upstream {
          type boolean;
          config false;
          description
            "Indicates whether the interface points towards the
             Internet ({{true}}) or towards End Devices
             ({{false}}).
          
             For example:
          
             * For an Internet Gateway Device, {{param}} will be
             {{true}} for all WAN interfaces and {{false}} for
             all LAN interfaces.
          
             * For a standalone WiFi Access Point that is
             connected via Ethernet to an Internet Gateway
             Device, {{param}} will be {{true}} for the Ethernet
             interface and {{false}} for the WiFi Radio
             interface.
          
             * For an End Device, {{param}} will be {{true}} for
             all interfaces.";
        }
        leaf MACAddress {
          type types:MACAddress;
          config false;
          description
            "The MAC Address of the interface.
          
             Note: This is not necessarily the same as the
             Ethernet header source or destination MAC address,
             which is associated with the IP interface and is
             modeled via the
             {{param|.Ethernet.Link.{i}.MACAddress}} parameter.";
        }
        leaf FirmwareVersion {
          type string {
            length "0..64";
          }
          config false;
          description
            "This interface's firmware version.";
        }
        leaf MaxBitRate {
          type uint32;
          config false;
          description
            "The maximum PHY bit rate supported by this interface
             (expressed in {{units}}).";
        }
        leaf NodeType {
          type enumeration {
            enum "AP";
            enum "EP";
          }
          description
            "Type of UPA device role.  It can be Fixed Access Point
             (master) or End Point (slave) of the PLC network.
             {{enum}}";
        }
        leaf LogicalNetwork {
          type string {
            length "0..20";
          }
          description
            "The name (network ID) of the logical PLC network in
             which the local interface is a member (human
             readable string).";
        }
        leaf EncryptionMethod {
          type enumeration {
            length "0..6";
            enum "None";
            enum "DES";
            enum "3DES";
            enum "AES128";
            enum "AES256";
          }
          description
            "Encryption Method used by UPA device.  {{enum}}";
        }
        leaf EncryptionKey {
          type string {
            length "0..36";
          }
          description
            "Encryption key for secure PLC communications.
          
             This a human readable string used by the system to
             generate the encryption key to encrypt
             communications in powerline.  It takes non extended
             ASCII characters (i.e.  printable 7-bit ASCII
             character codes 32-126, which includes SPACE but
             excludes TAB, LF and CR).  For example:
             bvjPekZiYUf9kjNKJASkgJ09adfoP01Fjvgd";
        }
        leaf PowerBackoffEnabled {
          type boolean;
          description
            "Power back-off management feature status in the UPA
             device.  Boolean can be {{true}} for \"enabled\" and
             {{false}} for \"disabled\".";
        }
        leaf PowerBackoffMechanismActive {
          type boolean;
          config false;
          description
            "Show if power back-off mechanism is active at that time
             in the UPA device.  Boolean can be {{true}} for
             \"active\" and {{false}} for \"not active\".";
        }
        leaf EstApplicationThroughput {
          type uint32;
          config false;
          description
            "The estimated application throughput (expressed in
             {{units}}), received from the PLC link.  This value
             can be used to indicate link quality.";
        }
        leaf ActiveNotchEnable {
          type boolean;
          description
            "Enables or disables the {{object|ActiveNotch}} table
             for this interface.";
        }

        container Stats {
          config false;
          description
            "Throughput statistics for this interface.
          
             The CPE MUST reset the interface's Stats parameters
             (unless otherwise stated in individual object or
             parameter descriptions) either when the interface
             becomes operationally down due to a previous
             administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2|section 4.2.2}}.";
          leaf BytesSent {
            type uint64;
            description
              "The total number of bytes transmitted out of the
               interface, including framing characters.";
          }
          leaf BytesReceived {
            type uint64;
            description
              "The total number of bytes received on the interface,
               including framing characters.";
          }
          leaf PacketsSent {
            type uint64;
            description
              "The total number of packets transmitted out of the
               interface.";
          }
          leaf PacketsReceived {
            type uint64;
            description
              "The total number of packets received on the
               interface.";
          }
          leaf ErrorsSent {
            type uint32;
            description
              "The total number of outbound packets that could not
               be transmitted because of errors.";
          }
          leaf ErrorsReceived {
            type uint32;
            description
              "The total number of inbound packets that contained
               errors preventing them from being delivered to a
               higher-layer protocol.";
          }
          leaf UnicastPacketsSent {
            type uint64;
            description
              "The total number of packets requested for
               transmission which were not addressed to a
               multicast or broadcast address at this layer,
               including those that were discarded or not sent.";
          }
          leaf UnicastPacketsReceived {
            type uint64;
            description
              "The total number of received packets, delivered by
               this layer to a higher layer, which were not
               addressed to a multicast or broadcast address at
               this layer.";
          }
          leaf DiscardPacketsSent {
            type uint32;
            description
              "The total number of outbound packets which were
               chosen to be discarded even though no errors had
               been detected to prevent their being transmitted.
               One possible reason for discarding such a packet
               could be to free up buffer space.";
          }
          leaf DiscardPacketsReceived {
            type uint32;
            description
              "The total number of inbound packets which were chosen
               to be discarded even though no errors had been
               detected to prevent their being delivered.  One
               possible reason for discarding such a packet could
               be to free up buffer space.";
          }
          leaf MulticastPacketsSent {
            type uint64;
            description
              "The total number of packets that higher-level
               protocols requested for transmission and which
               were addressed to a multicast address at this
               layer, including those that were discarded or not
               sent.";
          }
          leaf MulticastPacketsReceived {
            type uint64;
            description
              "The total number of received packets, delivered by
               this layer to a higher layer, which were addressed
               to a multicast address at this layer.";
          }
          leaf BroadcastPacketsSent {
            type uint64;
            description
              "The total number of packets that higher-level
               protocols requested for transmission and which
               were addressed to a broadcast address at this
               layer, including those that were discarded or not
               sent.";
          }
          leaf BroadcastPacketsReceived {
            type uint64;
            description
              "The total number of received packets, delivered by
               this layer to a higher layer, which were addressed
               to a broadcast address at this layer.";
          }
          leaf UnknownProtoPacketsReceived {
            type uint32;
            description
              "The total number of packets received via the
               interface which were discarded because of an
               unknown or unsupported protocol.";
          }
        }

        list AssociatedDevice {
          key "MACAddress";
          config false;
          description
            "This table contains information about PLC connections
             running between this UPA interface and other UPA
             devices.";
          leaf MACAddress {
            type types:MACAddress;
            description
              "Remote UPA device MAC address.";
          }
          leaf Port {
            type uint32 {
              range "0..65535";
            }
            description
              "The PLC port number.";
          }
          leaf LogicalNetwork {
            type string {
              length "0..20";
            }
            description
              "The name of the logical PLC network (human readable
               string).
            
               In the case where the associated device belongs to
               a different powerline network than the UPA
               interface, the actual network identifier of the
               neighboring network is not shown in {{param}}.
               Rather, only a generic string, e.g.  \"Network
               1\", \"Network 2\", etc is stored here due to
               security/privacy implications.";
          }
          leaf PhyTxThroughput {
            type uint32;
            description
              "Physical transmission throughput (in {{units}}).";
          }
          leaf PhyRxThroughput {
            type uint32;
            description
              "Physical reception throughput (in {{units}}).";
          }
          leaf RealPhyRxThroughput {
            type uint32;
            description
              "Real Physical reception throughput (in {{units}}).";
          }
          leaf EstimatedPLR {
            type uint32 {
              range "0..100";
            }
            description
              "Estimated PDU Loss Rate measurement between two
               devices (i.e.  estimated {{units}} of MPDUs that
               have been received with errors).";
          }
          leaf MeanEstimatedAtt {
            type uint32;
            description
              "Mean estimated attenuation (i.e.  channel loss
               between the local interface and the remote
               device).  It is measured in {{units}}.";
          }
          leaf SmartRouteIntermediatePLCMAC {
            type types:MACAddress;
            description
              "Intermediate UPA adapter MAC address of the device
               that is acting as a relay to increase coverage in
               mesh scenarios.  This is the MAC address of a
               third UPA device, with which the UPA interface is
               doing smart repeating in order to transmit data to
               the associated {{param|MACAddress}} UPA device.
               {{param}} will be empty when {{param|DirectRoute}}
               is {{true}}.";
          }
          leaf DirectRoute {
            type boolean;
            description
              "Route status, where {{true}} indicates ''direct'' and
               {{false}} indicates ''indirect''.";
          }
          leaf Active {
            type boolean;
            description
              "Whether or not this node is currently present in the
               UPA network.
            
               The ability to list inactive nodes is OPTIONAL.
               If the CPE includes inactive nodes in this table,
               {{param}} MUST be set to {{false}} for each
               inactive node.  The length of time an inactive
               node remains listed in this table is a local
               matter to the CPE.";
          }
        }

        list ActiveNotch {
          key "Alias";
          description
            "This object contains the list of active notches of the
             UPA interface.
          
             A UPA device can have notches in its spectrum, where
             no power is transmitted in a given part of the
             spectrum.  These notches are typically located in
             amateur radio bands, to avoid interference.
          
             Note: All {{object}} entries can be enabled/disabled
             as a group using the {{param|#.ActiveNotchEnable}}
             parameter.";
          leaf Enable {
            type boolean;
            default "false";
            description
              "Enables or disables the active notch entry.";
          }
          leaf StartFreq {
            type uint32;
            description
              "The initial frequency (in {{units}}) of a notch
               enabled in the spectrum of the local interface.";
          }
          leaf StopFreq {
            type uint32;
            description
              "The final frequency (in {{units}}) of a notch enabled
               in the spectrum of the local interface.";
          }
          leaf Depth {
            type uint32;
            description
              "The depth (in {{units}}) of a notch enabled in the
               spectrum of the local interface.";
          }
        }

        list BridgeFor {
          key "MACAddress";
          config false;
          description
            "This object represents the bridge table of the UPA
             interface.  Each instance is a bridge table entry.
          
             It shows the MAC addresses of the remote UPA devices
             with their associated port number, and the MAC
             addresses of the end-devices (PCs, STBs, routers,
             etc) connected to Ethernet port of the powerline
             adapters with their associated logical port.  In
             this way the system identifies to which UPA device
             an external device is connected to.";
          leaf MACAddress {
            type types:MACAddress;
            description
              "MAC address of the device.";
          }
          leaf Port {
            type uint32 {
              range "0..65535";
            }
            description
              "Internal bridge associated port.";
          }
        }
      }

      container Diagnostics {
        description
          "The UPA Diagnostics object.";

        container InterfaceMeasurement {
          description
            "This object provides access to either a
             Signal-to-Noise-Ratio (SNR) Port Measurement test or
             a Channel Frequency Response (CFR) Port Measurement
             test.  The {{param|Type}} parameter is used to
             select which type of test to perform.
          
             CFR and SNR measurements are done between a two UPA
             devices (a local interface and a remote device
             belonging to the same network).";
          leaf DiagnosticsState {
            type enumeration {
              enum "None";
              enum "Requested";
              enum "Canceled";
              enum "Complete";
              enum "Error";
              enum "Error_InvalidPort";
            }
            description
              "{{issue|A10-DIAG|No error state in original version}}
            
               {{datatype|expand}}";
          }
          leaf Type {
            type enumeration {
              enum "SNR";
              enum "CFR";
            }
            description
              "Indicates the type of port measurement test to be
               carried out.  {{enum}}.";
          }
          leaf Interface {
            type string {
              length "0..256";
            }
            description
              "{{reference}} This is the local UPA interface from
               which the test is to be performed.";
          }
          leaf Port {
            type uint32 {
              range "0..65535";
            }
            description
              "PLC port being measured.  This identifies which PLC
               connection to measure between the local interface
               (indicated by {{param|Interface}}) and the remote
               device (implied by {{param}}).";
          }
          leaf Measurements {
            type uint32;
            config false;
            description
              "{{list}} Result of Signal-to-Noise-Ratio measurement
               (if {{param|Type}} is {{enum|SNR|Type}}) or
               Channel Frequency Response measurement (if
               {{param|Type}} is {{enum|CFR|Type}}).
            
               List items indicate measurements per carrier for a
               PLC port (expressed in {{units}}).";
          }
          leaf RxGain {
            type int32;
            config false;
            description
              "Reception gain of the adapter (expresssed in
               {{units}}).";
          }
        }
      }
    }

    container WiFi {
      description
        "The WiFi object is based on the WiFi Alliance 802.11
         specifications ({{bibref|802.11-2007}}).  It defines
         interface objects ({{object|Radio}} and
         {{object|SSID}}), and application objects
         ({{object|AccessPoint}} and {{object|EndPoint}}).";

      list Radio {
        key "Alias";
        description
          "This object models an 802.11 wireless radio on a device
           (a stackable interface object as described in
           {{bibref|TR-181i2|Section 4.2}}).
        
           If the device can establish more than one connection
           simultaneously (e.g.  a dual radio device), a separate
           {{object}} instance MUST be used for each physical
           radio of the device.  See {{bibref|TR-181i2|Appendix
           III.1}} for additional information.
        
           Note: A dual-band single-radio device (e.g.  an
           802.11a/b/g radio) can be configured to operate at 2.4
           or 5 GHz frequency bands, but only a single frequency
           band is used to transmit/receive at a given time.
           Therefore, a single {{object}} instance is used even
           for a dual-band radio.";
        leaf Enable {
          type boolean;
          description
            "Enables or disables the radio.
          
             This parameter is based on ''ifAdminStatus'' from
             {{bibref|RFC2863}}.";
        }
        leaf Status {
          type enumeration {
            enum "Up";
            enum "Down";
            enum "Unknown";
            enum "Dormant";
            enum "NotPresent";
            enum "LowerLayerDown";
            enum "Error";
          }
          config false;
          description
            "The current operational state of the radio (see
             {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the radio as assigned by the CPE.";
        }
        leaf LastChange {
          type uint32;
          config false;
          description
            "The accumulated time in {{units}} since the radio
             entered its current operational state.";
        }
        leaf LowerLayers {
          type string;
          description
            "{{list}} {{reference|an interface object that is
             stacked immediately below this interface object}}
             See {{bibref|TR-181i2|Section 4.2.1}}.
          
             Note: Since {{object}} is a layer 1 interface, it is
             expected that {{param}} will not be used.";
        }
        leaf Upstream {
          type boolean;
          config false;
          description
            "Indicates whether the interface points towards the
             Internet ({{true}}) or towards End Devices
             ({{false}}).
          
             For example:
          
             * For an Internet Gateway Device, {{param}} will be
             {{true}} for all WAN interfaces and {{false}} for
             all LAN interfaces.
          
             * For a standalone WiFi Access Point that is
             connected via Ethernet to an Internet Gateway
             Device, {{param}} will be {{true}} for the Ethernet
             interface and {{false}} for the WiFi Radio
             interface.
          
             * For an End Device, {{param}} will be {{true}} for
             all interfaces.";
        }
        leaf MaxBitRate {
          type uint32;
          config false;
          description
            "The maximum PHY bit rate supported by this interface
             (expressed in {{units}}).";
        }
        leaf SupportedFrequencyBands {
          type enumeration {
            enum "2.4GHz";
            enum "5GHz";
          }
          config false;
          description
            "{{list}} List items indicate the frequency bands at
             which the radio can operate.";
        }
        leaf OperatingFrequencyBand {
          type string;
          description
            "Indicates the frequency band at which the radio is
             operating.
          
             If the radio supports multiple bands, and {{param}}
             is changed, then all parameters whose value is not
             valid for the new frequency band (e.g.
             {{param|Channel}}) MUST be set to a valid value
             (according to some CPE vendor-specific behavior).";
        }
        leaf SupportedStandards {
          type enumeration {
            enum "a";
            enum "b";
            enum "g";
            enum "n";
            enum "ac";
          }
          config false;
          description
            "{{list}} List items indicate which IEEE 802.11
             standards this {{object}} instance can support
             simultaneously, in the frequency band specified by
             {{param|OperatingFrequencyBand}}.  {{enum}}
          
             Each value indicates support for the indicated
             standard.
          
             If {{param|OperatingFrequencyBand}} is set to
             {{enum|2.4GHz|OperatingFrequencyBand}}, only values
             {{enum|b}}, {{enum|g}}, {{enum|n}} are allowed.
          
             If {{param|OperatingFrequencyBand}} is set to
             {{enum|5GHz|OperatingFrequencyBand}}, only values
             {{enum|a}}, {{enum|n}}, {{enum|ac}} are allowed.";
        }
        leaf OperatingStandards {
          type string;
          description
            "{{list}} List items indicate which IEEE 802.11 standard
             this {{object}} instance is configured for.
          
             Each value indicates support for the indicated
             standard.
          
             If {{param|OperatingFrequencyBand}} is set to
             {{enum|2.4GHz|OperatingFrequencyBand}}, only values
             {{enum|b}}, {{enum|g}}, {{enum|n}} are allowed.
          
             If {{param|OperatingFrequencyBand}} is set to
             {{enum|5GHz|OperatingFrequencyBand}}, only values
             {{enum|a}}, {{enum|n}}, {{enum|ac}} are allowed.
          
             For example, a value of \"g,b\" (or \"b,g\" - order
             is not important) means that the 802.11g standard
             {{bibref|802.11g-2003}} is used with a
             backwards-compatible mode for 802.11b
             {{bibref|802.11b-1999}}.  A value of \"g\" means
             that only the 802.11g standard can be used.";
        }
        leaf PossibleChannels {
          type string;
          config false;
          description
            "{{list}} List items represent possible radio channels
             for the wireless standard (a, b, g, n) and the
             regulatory domain.
          
             Ranges in the form \"n-m\" are permitted.
          
             For example, for 802.11b and North America, would be
             \"1-11\".";
        }
        leaf ChannelsInUse {
          type string;
          config false;
          description
            "{{list}} List items represent channels that the radio
             determines to be currently in use (including any
             that it is using itself).
          
             Ranges in the form \"n-m\" are permitted.";
        }
        leaf Channel {
          type uint32 {
            range "1..255";
          }
          description
            "The current radio channel used by the connection.  To
             request automatic channel selection, set
             {{param|AutoChannelEnable}} to {{true}}.
          
             Whenever {{param|AutoChannelEnable}} is {{true}},
             the value of the {{param}} parameter MUST be the
             channel selected by the automatic channel selection
             procedure.
          
             Note: Valid {{param}} values depend on the
             {{param|OperatingFrequencyBand}} and
             {{param|RegulatoryDomain}} values specified.";
        }
        leaf AutoChannelSupported {
          type boolean;
          config false;
          description
            "Indicates whether automatic channel selection is
             supported by this radio.  If {{false}}, then
             {{param|AutoChannelEnable}} MUST be {{false}}.";
        }
        leaf AutoChannelEnable {
          type boolean;
          description
            "Enable or disable automatic channel selection.
          
             Set to {{false}} to disable the automatic channel
             selection procedure, in which case the currently
             selected channel remains selected.
          
             Set to {{true}} to enable the automatic channel
             selection procedure.  This procedure MUST
             automatically select the channel, and MAY also
             change it subsequently.
          
             {{param}} MUST automatically change to {{false}}
             whenever the channel is manually selected, i.e.
             whenever the {{param|Channel}} parameter is written.
          
             Whenever {{param}} is {{true}}, the value of the
             {{param|Channel}} parameter MUST be the channel
             selected by the automatic channel selection
             procedure.";
        }
        leaf AutoChannelRefreshPeriod {
          type uint32;
          description
            "The time period in {{units}} between two consecutive
             automatic channel selections.  A value of 0 means
             that the automatic channel selection is done only at
             boot time.
          
             This parameter is significant only if
             {{param|AutoChannelEnable}} is set to {{true}}.";
        }
        leaf OperatingChannelBandwidth {
          type enumeration {
            enum "20MHz";
            enum "40MHz";
            enum "80MHz";
            enum "160MHz";
            enum "Auto";
          }
          description
            "The channel bandwidth (applicable to 802.11n and
             802.11ac specifications only).";
        }
        leaf ExtensionChannel {
          type enumeration {
            enum "AboveControlChannel";
            enum "BelowControlChannel";
            enum "Auto";
          }
          description
            "The secondary extension channel position, applicable
             when operating in wide channel mode (i.e.  when
             {{param|OperatingChannelBandwidth}} is set to
             {{enum|40MHz|OperatingChannelBandwidth}} or
             {{enum|Auto|OperatingChannelBandwidth}}).";
        }
        leaf GuardInterval {
          type enumeration {
            enum "400nsec";
            enum "800nsec";
            enum "Auto";
          }
          description
            "The guard interval value between OFDM symbols
             (applicable to 802.11n and 802.11ac specifications
             only).";
        }
        leaf MCS {
          type int32 {
            range "-1..15 | 16..31";
          }
          description
            "The Modulation Coding Scheme index (applicable to
             802.11n and 802.11ac specifications only).  Values
             from 0 to 15 MUST be supported
             ({{bibref|802.11n-2009}}).  Values from 0 to 9 MUST
             be supported for {{bibref|802.11ac-2013}}.  A value
             of -1 indicates automatic selection of the MCS
             index.";
        }
        leaf TransmitPowerSupported {
          type int32 {
            range "-1..100";
          }
          config false;
          description
            "{{list}} List items represent supported transmit power
             levels as {{units}} of full power.  For example,
             \"0,25,50,75,100\".
          
             A -1 item indicates auto mode (automatic decision by
             CPE).  Auto mode allows the ''Radio'' to adjust
             transmit power accordingly.  For example, this can
             be useful for power-save modes such as EU-CoC, where
             the ''Radio'' can adjust power according to activity
             in the CPE.";
        }
        leaf TransmitPower {
          type int32 {
            range "-1..100";
          }
          description
            "Indicates the current transmit power level as a
             {{units}} of full power.  The value MUST be one of
             the values reported by the
             {{param|TransmitPowerSupported}} parameter.  A value
             of -1 indicates auto mode (automatic decision by
             CPE).";
        }
        leaf IEEE80211hSupported {
          type boolean;
          config false;
          description
            "Indicates whether IEEE 802.11h {{bibref|802.11h-2003}}
             functionality is supported by this radio.  The value
             can be {{true}} only if the 802.11a or the
             802.11n@5GHz standard is supported (i.e.
             {{param|SupportedFrequencyBands}} includes
             {{enum|5GHz|SupportedFrequencyBands}} and
             {{param|SupportedStandards}} includes
             {{enum|a|SupportedStandards}} and/or
             {{enum|n|SupportedStandards}}).";
        }
        leaf IEEE80211hEnabled {
          type boolean;
          description
            "Indicates whether IEEE 802.11h functionality is enabled
             on this radio.  The value can be {{true}} only if
             the 802.11a or the 802.11n@5GHz standard is
             supported and enabled (i.e.
             {{param|OperatingFrequencyBand}} is
             {{enum|5GHz|OperatingFrequencyBand}} and
             {{param|OperatingStandards}} includes
             {{enum|a|OperatingStandards}} and/or
             {{enum|n|OperatingStandards}}).";
        }
        leaf RegulatoryDomain {
          type string {
            length "3";
            pattern "[A-Z][A-Z][ OI]";
          }
          description
            "The 802.11d Regulatory Domain.  First two octets are
             {{bibref|ISO3166-1}} two-character country code.
             The third octet is either \" \" (all environments),
             \"O\" (outside) or \"I\" (inside).";
        }
        leaf RetryLimit {
          type uint32 {
            range "0..7";
          }
          description
            "The maximum number of retransmissions of a short packet
             i.e.  a packet that is no longer than the
             {{param|RTSThreshold}}.  This corresponds to IEEE
             802.11 parameter ''dot11ShortRetryLimit''
             {{bibref|802.11-2012}}.";
        }
        leaf CCARequest {
          type yang:hex-string {
            length "11";
          }
          description
            "A request for the clear channel assessment (CCA) report
             in the format specified in
             {{bibref|802.11-2012|Clause 8.4.2.23.3}}.";
        }
        leaf CCAReport {
          type yang:hex-string {
            length "12";
          }
          config false;
          description
            "The clear channel assessment (CCA) report in the format
             specified in {{bibref|802.11-2012|Clause
             8.4.2.24.3}}.
          
             When read, the value of this parameter MUST
             correspond to {{param|CCARequest}}.  How this is
             achieved is a local matter to the CPE.
          
             If this parameter is read before a CCARequest has
             been issued, then its value is {{empty}}.";
        }
        leaf RPIHistogramRequest {
          type yang:hex-string {
            length "11";
          }
          description
            "A request for a received power indicator (RPI)
             histogram in the format specified in
             {{bibref|802.11-2012|Clause 8.4.2.23.4}}.";
        }
        leaf RPIHistogramReport {
          type yang:hex-string {
            length "19";
          }
          config false;
          description
            "Received power indicator (RPI) histogram report in the
             format specified in {{bibref|802.11-2012|Clause
             8.4.2.24.4}}.";
        }
        leaf FragmentationThreshold {
          type uint32;
          description
            "This specifies the current maximum size, in {{units}},
             of the MPDU that can be delivered to the PHY.  This
             parameter is based on
             ''dot11FragmentationThreshold'' from
             {{bibref|802.11-2012}}.";
        }
        leaf RTSThreshold {
          type uint32;
          description
            "This indicates the number of {{units}} in an MPDU,
             below which an RTS/CTS handshake is not performed.
             This parameter is based on ''dot11RTSThreshold''
             from {{bibref|802.11-2012}}.";
        }
        leaf LongRetryLimit {
          type uint32;
          description
            "This indicates the maximum number of transmission
             attempts of a frame, the length of which is greater
             than {{param|RTSThreshold}}, that will be made
             before a failure condition is indicated.  This
             parameter is based on ''dot11LongRetryLimit'' from
             {{bibref|802.11-2012}}.";
        }
        leaf BeaconPeriod {
          type uint32;
          description
            "Time interval between transmitting beacons (expressed
             in {{units}}).  This parameter is based on
             ''dot11BeaconPeriod'' from {{bibref|802.11-2012}}.";
        }
        leaf DTIMPeriod {
          type uint32;
          description
            "This specifies the number of beacon intervals that
             elapse between transmission of Beacon frames
             containing a TIM element whose DTIM Count field is
             0.  This parameter is based on ''dot11DTIMPeriod''
             from {{bibref|802.11-2012}}.";
        }
        leaf PacketAggregationEnable {
          type boolean;
          description
            "This determines whether or not packet aggregation
             (commonly called \"frame aggregation\") is enabled.
             This applies only to 802.11n.";
        }
        leaf PreambleType {
          type enumeration {
            enum "short";
            enum "long";
            enum "auto";
          }
          description
            "The type of preamble.  Longer preambles (more overhead)
             are needed by 802.11g to coexist with legacy systems
             802.11 and 802.11b.";
        }
        leaf BasicDataTransmitRates {
          type string;
          description
            "{{list}} The set of data rates, in ''Mbps'', that have
             to be supported by all stations that desire to join
             this BSS.  The stations have to be able to receive
             and transmit at each of the data rates listed in
             {{param}}.  For example, a value of \"1,2\",
             indicates that stations support 1 Mbps and 2 Mbps.
             Most control packets use a data rate in {{param}}.";
        }
        leaf OperationalDataTransmitRates {
          type string;
          description
            "{{list}} Maximum access point data transmit rates in
             ''Mbps'' for unicast frames (a superset of
             {{param|BasicDataTransmitRates}}).  Given the value
             of {{param|BasicDataTransmitRates}} from the example
             above, {{param}} might be \"1,2,5.5,11\", indicating
             that unicast frames can additionally be transmitted
             at 5.5 Mbps and 11 Mbps.";
        }
        leaf SupportedDataTransmitRates {
          type string;
          config false;
          description
            "{{list}} Data transmit rates in ''Mbps'' for unicast
             frames at which the access point will permit a
             station to connect (a subset of
             {{param|OperationalDataTransmitRates}}).  Given the
             values of {{param|BasicDataTransmitRates}} and
             {{param|OperationalDataTransmitRates}} from the
             examples above, {{param}} might be \"1,2,5.5\",
             indicating that the AP will only permit connections
             at 1 Mbps, 2 Mbps and 5.5 Mbps, even though it could
             theoretically accept connections at 11 Mbps.";
        }

        container Stats {
          config false;
          description
            "Throughput statistics for this interface.  Packet
             counters here count 802.11 WiFi frames.  See
             {{bibref|TR-181i2a5|Appendix III}} for further
             details.  The CPE MUST reset the interface's Stats
             parameters (unless otherwise stated in individual
             object or parameter descriptions) either when the
             interface becomes operationally down due to a
             previous administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2a5|Section 4.2.2}}.";
          leaf BytesSent {
            type uint64;
            description
              "The total number of bytes transmitted out of the
               interface, including framing characters.";
          }
          leaf BytesReceived {
            type uint64;
            description
              "The total number of bytes received on the interface,
               including framing characters.";
          }
          leaf PacketsSent {
            type uint64;
            description
              "The total number of packets transmitted out of the
               interface.";
          }
          leaf PacketsReceived {
            type uint64;
            description
              "The total number of packets received on the
               interface.";
          }
          leaf ErrorsSent {
            type uint32;
            description
              "The total number of outbound packets that could not
               be transmitted because of errors.";
          }
          leaf ErrorsReceived {
            type uint32;
            description
              "The total number of inbound packets that contained
               errors preventing them from being delivered to a
               higher-layer protocol.";
          }
          leaf DiscardPacketsSent {
            type uint32;
            description
              "The total number of outbound packets which were
               chosen to be discarded even though no errors had
               been detected to prevent their being transmitted.
               One possible reason for discarding such a packet
               could be to free up buffer space.";
          }
          leaf DiscardPacketsReceived {
            type uint32;
            description
              "The total number of inbound packets which were chosen
               to be discarded even though no errors had been
               detected to prevent their being delivered.  One
               possible reason for discarding such a packet could
               be to free up buffer space.";
          }
          leaf PLCPErrorCount {
            type uint32;
            description
              "The number of packets that were received with a
               detected Physical Layer Convergence Protocol
               (PLCP) header error.";
          }
          leaf FCSErrorCount {
            type uint32;
            description
              "The number of packets that were received with a
               detected FCS error.  This parameter is based on
               dot11FCSErrorCount from {{bibref|802.11-2012|Annex
               C}}.";
          }
          leaf InvalidMACCount {
            type uint32;
            description
              "The number of packets that were received with a
               detected invalid MAC header error.";
          }
          leaf PacketsOtherReceived {
            type uint32;
            description
              "The number of packets that were received, but which
               were destined for a MAC address that is not
               associated with this interface.";
          }
          leaf Noise {
            type int32;
            description
              "An indicator of average noise strength received at
               this radio, measured in {{units}}.  This
               measurement of non-IEEE 802.11 noise power is made
               by sampling the channel when virtual carrier sense
               indicates idle and this radio is neither
               transmitting nor receiving a frame.";
          }
        }
      }

      container NeighboringWiFiDiagnostic {
        description
          "This object defines access to other WiFi SSIDs that this
           device is able to receive.";
        leaf DiagnosticsState {
          type enumeration {
            enum "None";
            enum "Requested";
            enum "Canceled";
            enum "Complete";
            enum "Error";
            enum "Completed";
          }
          description
            "{{issue|A10-DIAG|Old state \"Completed\" => New state
             \"Complete\"}}
          
             {{datatype|expand}}";
        }

        list Result {
          key "BSSID";
          config false;
          description
            "Neighboring SSID table.  This table models the other
             WiFi SSIDs that this device is able to receive.";
          leaf Radio {
            type string;
            description
              "The Radio that detected the neighboring WiFi SSID.";
          }
          leaf SSID {
            type string {
              length "0..32";
            }
            description
              "The current service set identifier in use by the
               neighboring WiFi SSID.  The value MAY be empty for
               hidden SSIDs.";
          }
          leaf BSSID {
            type types:MACAddress;
            description
              "The BSSID used for the neighboring WiFi SSID.";
          }
          leaf Mode {
            type enumeration {
              enum "AdHoc";
              enum "Infrastructure";
            }
            description
              "The mode the neighboring WiFi radio is operating in.";
          }
          leaf Channel {
            type uint32 {
              range "1..255";
            }
            description
              "The current radio channel used by the neighboring
               WiFi radio.";
          }
          leaf SignalStrength {
            type int32 {
              range "-200..0";
            }
            description
              "An indicator of radio signal strength (RSSI) of the
               neighboring WiFi radio measured in {{units}}, as
               an average of the last 100 packets received.";
          }
          leaf SecurityModeEnabled {
            type enumeration {
              enum "None";
              enum "WEP";
              enum "WPA";
              enum "WPA2";
              enum "WPA-WPA2";
              enum "WPA-Enterprise";
              enum "WPA2-Enterprise";
              enum "WPA-WPA2-Enterprise";
            }
            description
              "The type of encryption the neighboring WiFi SSID
               advertises.";
          }
          leaf EncryptionMode {
            type enumeration {
              enum "TKIP";
              enum "AES";
            }
            description
              "The type of encryption the neighboring WiFi SSID
               advertises.";
          }
          leaf OperatingFrequencyBand {
            type enumeration {
              enum "2.4GHz";
              enum "5GHz";
            }
            description
              "Indicates the frequency band at which the radio this
               SSID instance is operating.";
          }
          leaf SupportedStandards {
            type enumeration {
              enum "a";
              enum "b";
              enum "g";
              enum "n";
              enum "ac";
            }
            description
              "{{list}} List items indicate which IEEE 802.11
               standards this {{object}} instance can support
               simultaneously, in the frequency band specified by
               {{param|OperatingFrequencyBand}}.  {{enum}}
            
               Each value indicates support for the indicated
               standard.
            
               If {{param|OperatingFrequencyBand}} is set to
               {{enum|2.4GHz|OperatingFrequencyBand}}, only
               values {{enum|b}}, {{enum|g}}, {{enum|n}} are
               allowed.
            
               If {{param|OperatingFrequencyBand}} is set to
               {{enum|5GHz|OperatingFrequencyBand}}, only values
               {{enum|a}}, {{enum|n}}, {{enum|ac}} are allowed.";
          }
          leaf OperatingStandards {
            type string;
            description
              "{{list}} List items indicate which IEEE 802.11
               standard that is detected for this {{object}}.
            
               Each value indicates support for the indicated
               standard.
            
               If {{param|OperatingFrequencyBand}} is set to
               {{enum|2.4GHz|##.Radio.{i}.SupportedFrequencyBands}},
               only values {{enum|b}}, {{enum|g}}, {{enum|n}} are
               allowed.
            
               If {{param|OperatingFrequencyBand}} is set to
               {{enum|5GHz|##.Radio.{i}.SupportedFrequencyBands}},
               only values {{enum|a}}, {{enum|n}}, {{enum|ac}}
               are allowed.
            
               For example, a value of \"g,b\" (or \"b,g\" -
               order is not important) means that the 802.11g
               standard {{bibref|802.11g-2003}} is used with a
               backwards-compatible mode for 802.11b
               {{bibref|802.11b-1999}}.  A value of \"g\" means
               that only the 802.11g standard can be used.";
          }
          leaf OperatingChannelBandwidth {
            type enumeration {
              enum "20MHz";
              enum "40MHz";
              enum "80MHz";
              enum "160MHz";
              enum "Auto";
            }
            description
              "Indicates the bandwidth at which the channel is
               operating.";
          }
          leaf BeaconPeriod {
            type uint32;
            description
              "Time interval (in {{units}}) between transmitting
               beacons.";
          }
          leaf Noise {
            type int32 {
              range "-200..0";
            }
            description
              "Indicator of average noise strength (in {{units}})
               received from the neighboring WiFi radio.";
          }
          leaf BasicDataTransferRates {
            type string;
            description
              "{{list}} Basic data transmit rates (in Mbps) for the
               SSID.  For example, if {{param}} is \"1,2\", this
               indicates that the SSID is operating with basic
               rates of 1 Mbps and 2 Mbps.";
          }
          leaf SupportedDataTransferRates {
            type string;
            description
              "{{list}} Data transmit rates (in Mbps) for unicast
               frames at which the SSID will permit a station to
               connect.  For example, if {{param}} is
               \"1,2,5.5\", this indicates that the SSID will
               only permit connections at 1 Mbps, 2 Mbps and 5.5
               Mbps.";
          }
          leaf DTIMPeriod {
            type uint32;
            description
              "The number of beacon intervals that elapse between
               transmission of Beacon frames containing a TIM
               element whose DTIM count field is 0.  This value
               is transmitted in the DTIM Period field of beacon
               frames.  {{bibref|802.11-2012}}";
          }
        }
      }

      list SSID {
        key "SSID";
        description
          "WiFi SSID table (a stackable interface object as
           described in {{bibref|TR-181i2|Section 4.2}}), where
           table entries model the MAC layer.  A WiFi SSID entry
           is typically stacked on top of a {{object|#.Radio}}
           object.
        
           WiFi SSID is also a multiplexing layer, i.e.  more
           than one {{object}} can be stacked above a single
           {{object|#.Radio}}.";
        leaf Enable {
          type boolean;
          default "false";
          description
            "Enables or disables the SSID entry.
          
             This parameter is based on ''ifAdminStatus'' from
             {{bibref|RFC2863}}.";
        }
        leaf Status {
          type enumeration {
            enum "Up";
            enum "Down";
            enum "Unknown";
            enum "Dormant";
            enum "NotPresent";
            enum "LowerLayerDown";
            enum "Error";
          }
          config false;
          default "Down";
          description
            "The current operational state of the SSID entry (see
             {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the SSID entry as assigned by the
             CPE.";
        }
        leaf LastChange {
          type uint32;
          config false;
          description
            "The accumulated time in {{units}} since the SSID
             entered its current operational state.";
        }
        leaf LowerLayers {
          type string;
          default "";
          description
            "{{list}} {{reference|an interface object that is
             stacked immediately below this interface object}}
             See {{bibref|TR-181i2|Section 4.2.1}}.";
        }
        leaf BSSID {
          type types:MACAddress;
          config false;
          description
            "The Basic Service Set ID.
          
             This is the MAC address of the access point, which
             can either be local (when this instance models an
             access point SSID) or remote (when this instance
             models an end point SSID).";
        }
        leaf MACAddress {
          type types:MACAddress;
          config false;
          description
            "The MAC address of this interface.
          
             If this instance models an access point SSID,
             {{param}} is the same as {{param||BSSID}}.
          
             Note: This is not necessarily the same as the
             Ethernet header source or destination MAC address,
             which is associated with the IP interface and is
             modeled via the
             {{param|.Ethernet.Link.{i}.MACAddress}} parameter.";
        }
        leaf SSID {
          type string {
            length "0..32";
          }
          description
            "The current service set identifier in use by the
             connection.  The SSID is an identifier that is
             attached to packets sent over the wireless LAN that
             functions as an ID for joining a particular radio
             network (BSS).";
        }

        container Stats {
          config false;
          description
            "Throughput statistics for this interface.  Packet
             counters here count 802.11 WiFi frames.  See
             {{bibref|TR-181i2a5|Appendix III}} for further
             details.  The CPE MUST reset the interface's Stats
             parameters (unless otherwise stated in individual
             object or parameter descriptions) either when the
             interface becomes operationally down due to a
             previous administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2a5|Section 4.2.2}}.";
          leaf BytesSent {
            type uint64;
            description
              "The total number of bytes transmitted out of the
               interface, including framing characters.";
          }
          leaf BytesReceived {
            type uint64;
            description
              "The total number of bytes received on the interface,
               including framing characters.";
          }
          leaf PacketsSent {
            type uint64;
            description
              "The total number of packets transmitted out of the
               interface.";
          }
          leaf PacketsReceived {
            type uint64;
            description
              "The total number of packets received on the
               interface.";
          }
          leaf ErrorsSent {
            type uint32;
            description
              "The total number of outbound packets that could not
               be transmitted because of errors.  These can be
               due to the number of retransmissions exceeding the
               retry limit, or from other causes.";
          }
          leaf RetransCount {
            type uint32;
            description
              "The total number of transmitted packets which were
               retransmissions.  Two retransmissions of the same
               packet results in this counter incrementing by
               two.";
          }
          leaf FailedRetransCount {
            type uint32;
            description
              "The number of packets that were not transmitted
               successfully due to the number of retransmission
               attempts exceeding an 802.11 retry limit.  This
               parameter is based on dot11FailedCount from
               {{bibref|802.11-2012}}.";
          }
          leaf RetryCount {
            type uint32;
            description
              "The number of packets that were successfully
               transmitted after one or more retransmissions.
               This parameter is based on dot11RetryCount from
               {{bibref|802.11-2012}}.";
          }
          leaf MultipleRetryCount {
            type uint32;
            description
              "The number of packets that were successfully
               transmitted after more than one retransmission.
               This parameter is based on dot11MultipleRetryCount
               from {{bibref|802.11-2012}}.";
          }
          leaf ACKFailureCount {
            type uint32;
            description
              "The number of expected ACKs that were never received.
               This parameter is based on dot11ACKFailureCount
               from {{bibref|802.11-2012}}.";
          }
          leaf AggregatedPacketCount {
            type uint32;
            description
              "The number of aggregated packets that were
               transmitted.  This applies only to 802.11n and
               802.11ac.";
          }
          leaf ErrorsReceived {
            type uint32;
            description
              "The total number of inbound packets that contained
               errors preventing them from being delivered to a
               higher-layer protocol.";
          }
          leaf UnicastPacketsSent {
            type uint64;
            description
              "The total number of packets requested for
               transmission which were not addressed to a
               multicast or broadcast address at this layer,
               including those that were discarded or not sent.";
          }
          leaf UnicastPacketsReceived {
            type uint64;
            description
              "The total number of received packets, delivered by
               this layer to a higher layer, which were not
               addressed to a multicast or broadcast address at
               this layer.";
          }
          leaf DiscardPacketsSent {
            type uint32;
            description
              "The total number of outbound packets which were
               chosen to be discarded even though no errors had
               been detected to prevent their being transmitted.
               One possible reason for discarding such a packet
               could be to free up buffer space.";
          }
          leaf DiscardPacketsReceived {
            type uint32;
            description
              "The total number of inbound packets which were chosen
               to be discarded even though no errors had been
               detected to prevent their being delivered.  One
               possible reason for discarding such a packet could
               be to free up buffer space.";
          }
          leaf MulticastPacketsSent {
            type uint64;
            description
              "The total number of packets that higher-level
               protocols requested for transmission and which
               were addressed to a multicast address at this
               layer, including those that were discarded or not
               sent.";
          }
          leaf MulticastPacketsReceived {
            type uint64;
            description
              "The total number of received packets, delivered by
               this layer to a higher layer, which were addressed
               to a multicast address at this layer.";
          }
          leaf BroadcastPacketsSent {
            type uint64;
            description
              "The total number of packets that higher-level
               protocols requested for transmission and which
               were addressed to a broadcast address at this
               layer, including those that were discarded or not
               sent.";
          }
          leaf BroadcastPacketsReceived {
            type uint64;
            description
              "The total number of received packets, delivered by
               this layer to a higher layer, which were addressed
               to a broadcast address at this layer.";
          }
          leaf UnknownProtoPacketsReceived {
            type uint32;
            description
              "The total number of packets received via the
               interface which were discarded because of an
               unknown or unsupported protocol.";
          }
        }
      }

      list AccessPoint {
        key "SSIDReference";
        description
          "This object models an 802.11 connection from the
           perspective of a wireless access point.  Each
           {{object}} entry is associated with a particular
           {{object|#.SSID}} interface instance via the
           {{param|SSIDReference}} parameter.
        
           For enabled table entries, if {{param|SSIDReference}}
           is not a valid reference then the table entry is
           inoperable and the CPE MUST set {{param|Status}} to
           {{enum|Error_Misconfigured|Status}}.
        
           Note: The {{object}} table includes a unique key
           parameter that is a strong reference.  If a strongly
           referenced object is deleted, the CPE will set the
           referencing parameter to {{empty}}.  However, doing so
           under these circumstances might cause the updated
           {{object}} row to then violate the table's unique key
           constraint; if this occurs, the CPE MUST set
           {{param|Status}} to
           {{enum|Error_Misconfigured|Status}} and disable the
           offending {{object}} row.";
        leaf Enable {
          type boolean;
          default "false";
          description
            "Enables or disables this access point.";
        }
        leaf Status {
          type enumeration {
            enum "Disabled";
            enum "Enabled";
            enum "Error_Misconfigured";
            enum "Error";
          }
          config false;
          default "Disabled";
          description
            "Indicates the status of this access point.  {{enum}}
          
             The {{enum|Error_Misconfigured}} value indicates
             that a necessary configuration value is undefined or
             invalid.
          
             The {{enum|Error}} value MAY be used by the CPE to
             indicate a locally defined error condition.";
        }
        leaf SSIDReference {
          type string {
            length "0..256";
          }
          default "";
          description
            "{{reference}}";
        }
        leaf SSIDAdvertisementEnabled {
          type boolean;
          description
            "Indicates whether or not beacons include the SSID name.";
        }
        leaf RetryLimit {
          status deprecated;
          type uint32 {
            range "0..7";
          }
          description
            "The maximum number of retransmission for a packet.
             This corresponds to IEEE 802.11 parameter
             ''dot11ShortRetryLimit''.
          
             This parameter is DEPRECATED because it is really a
             {{object|#.Radio}} attribute.  Use
             {{param|#.Radio.{i}.RetryLimit}}.";
        }
        leaf WMMCapability {
          type boolean;
          config false;
          description
            "Indicates whether this access point supports WiFi
             Multimedia (WMM) Access Categories (AC).";
        }
        leaf UAPSDCapability {
          type boolean;
          config false;
          description
            "Indicates whether this access point supports WMM
             Unscheduled Automatic Power Save Delivery (U-APSD).
          
             Note: U-APSD support implies WMM support.";
        }
        leaf WMMEnable {
          type boolean;
          description
            "Whether WMM support is currently enabled.  When
             enabled, this is indicated in beacon frames.";
        }
        leaf UAPSDEnable {
          type boolean;
          description
            "Whether U-APSD support is currently enabled.  When
             enabled, this is indicated in beacon frames.
          
             Note: U-APSD can only be enabled if WMM is also
             enabled.";
        }
        leaf MaxAssociatedDevices {
          type uint32;
          default "0";
          description
            "The maximum number of devices that can simultaneously
             be connected to the access point.
          
             A value of 0 means that there is no specific limit.";
        }
        leaf IsolationEnable {
          type boolean;
          description
            "Enables or disables device isolation.
          
             A value of {{true}} means that the devices connected
             to the Access Point are isolated from all other
             devices within the home network (as is typically the
             case for a Wireless Hotspot).";
        }
        leaf MACAddressControlEnabled {
          type boolean;
          description
            "Indicates whether or not MAC Address Control is enabled
             on this {{object|#}}.  MAC Address Control limits
             client devices to those whose hardware addresses
             match the {{param|AllowedMACAddress}} list.";
        }
        leaf AllowedMACAddress {
          type types:MACAddress;
          description
            "Hardware addresses of client devices that are allowed
             to associate with this {{object|#}} if
             {{param|MACAddressControlEnabled}} is {{true}}.";
        }

        container Security {
          description
            "This object contains security related parameters that
             apply to a CPE acting as an Access Point
             {{bibref|802.11-2007}}.";
          leaf Reset {
            type boolean; /* command */
            description
              "When set to {{true}}, this {{object|#}} instance's
               WiFi security settings are reset to their factory
               default values.  The affected settings include
               {{param|ModeEnabled}}, {{param|WEPKey}},
               {{param|PreSharedKey}} and
               {{param|KeyPassphrase}}.
            
               If the parameter cannot be set, the CPE MUST
               reject the request as an invalid parameter value.
               Possible failure reasons include a lack of default
               values or if {{param|ModeEnabled}} is an
               Enterprise type, i.e.
               {{enum|WPA-Enterprise|ModesSupported}},
               {{enum|WPA2-Enterprise|ModesSupported}} or
               {{enum|WPA-WPA2-Enterprise|ModesSupported}}.";
          }
          leaf ModesSupported {
            type enumeration {
              enum "None";
              enum "WEP-64";
              enum "WEP-128";
              enum "WPA-Personal";
              enum "WPA2-Personal";
              enum "WPA-WPA2-Personal";
              enum "WPA-Enterprise";
              enum "WPA2-Enterprise";
              enum "WPA-WPA2-Enterprise";
            }
            config false;
            description
              "{{list}} Indicates which security modes this
               {{object|#}} instance is capable of supporting.";
          }
          leaf ModeEnabled {
            type string;
            description
              "Indicates which security mode is enabled.";
          }
          leaf WEPKey {
            type yang:hex-string {
              length "5 | 13";
            }
            description
              "A WEP key expressed as a hexadecimal string.
            
               {{param}} is used only if {{param|ModeEnabled}} is
               set to {{enum|WEP-64|ModeEnabled}} or
               {{enum|WEP-128|ModeEnabled}}.
            
               A 5 byte {{param}} corresponds to security mode
               {{enum|WEP-64|ModeEnabled}} and a 13 byte
               {{param}} corresponds to security mode
               {{enum|WEP-128|ModeEnabled}}.";
          }
          leaf PreSharedKey {
            type yang:hex-string {
              length "0..32";
            }
            description
              "A literal PreSharedKey (PSK) expressed as a
               hexadecimal string.
            
               {{param}} is only used if {{param|ModeEnabled}} is
               set to {{enum|WPA-Personal|ModeEnabled}} or
               {{enum|WPA2-Personal|ModeEnabled}} or
               {{enum|WPA-WPA2-Personal|ModeEnabled}}.
            
               If {{param|KeyPassphrase}} is written, then
               {{param}} is immediately generated.  The ACS
               SHOULD NOT set both the {{param|KeyPassphrase}}
               and the {{param}} directly (the result of doing
               this is undefined).";
          }
          leaf KeyPassphrase {
            type string {
              length "8..63";
            }
            description
              "A passphrase from which the {{param|PreSharedKey}} is
               to be generated, for
               {{enum|WPA-Personal|ModeEnabled}} or
               {{enum|WPA2-Personal|ModeEnabled}} or
               {{enum|WPA-WPA2-Personal|ModeEnabled}} security
               modes.
            
               If {{param}} is written, then
               {{param|PreSharedKey}} is immediately generated.
               The ACS SHOULD NOT set both the {{param}} and the
               {{param|PreSharedKey}} directly (the result of
               doing this is undefined).  The key is generated as
               specified by WPA, which uses PBKDF2 from PKCS #5:
               Password-based Cryptography Specification Version
               2.0 ({{bibref|RFC2898}}).";
          }
          leaf RekeyingInterval {
            type uint32;
            default "3600";
            description
              "The interval (expressed in {{units}}) in which the
               keys are re-generated.
            
               This is applicable to WPA, WPA2 and Mixed
               (WPA-WPA2) modes in Personal or Enterprise mode
               (i.e.  when {{param|ModeEnabled}} is set to a
               value other than {{enum|None|ModeEnabled}} or
               {{enum|WEP-64|ModeEnabled}} or
               {{enum|WEP-128|ModeEnabled}}.";
          }
          leaf RadiusServerIPAddr {
            type types:IPAddress;
            description
              "The IP Address of the RADIUS server used for WLAN
               security.  {{param}} is only applicable when
               {{param|ModeEnabled}} is an Enterprise type (i.e.
               {{enum|WPA-Enterprise|ModeEnabled}},
               {{enum|WPA2-Enterprise|ModeEnabled}} or
               {{enum|WPA-WPA2-Enterprise|ModeEnabled}}).";
          }
          leaf SecondaryRadiusServerIPAddr  {
            type types:IPAddress;
            description
              "The IP Address of a secondary RADIUS server used for
               WLAN security.  {{param}} is only applicable when
               {{param|ModeEnabled}} is an Enterprise type (i.e.
               {{enum|WPA-Enterprise|ModeEnabled}},
               {{enum|WPA2-Enterprise|ModeEnabled}} or
               {{enum|WPA-WPA2-Enterprise|ModeEnabled}}).
            
               The client can forward requests to the secondary
               server in the event that the primary server is
               down or unreachable, or after a number of tries to
               the primary server fail, or in a round-robin
               fashion {{bibref|RFC2865}}.";
          }
          leaf RadiusServerPort {
            type uint32;
            default "1812";
            description
              "The port number of the RADIUS server used for WLAN
               security.  {{param}} is only applicable when
               {{param|ModeEnabled}} is an Enterprise type (i.e.
               {{enum|WPA-Enterprise|ModeEnabled}},
               {{enum|WPA2-Enterprise|ModeEnabled}} or
               {{enum|WPA-WPA2-Enterprise|ModeEnabled}}).";
          }
          leaf SecondaryRadiusServerPort {
            type uint32;
            default "1812";
            description
              "The port number of the secondary RADIUS server used
               for WLAN security.  {{param}} is only applicable
               when {{param|ModeEnabled}} is an Enterprise type
               (i.e.  {{enum|WPA-Enterprise|ModeEnabled}},
               {{enum|WPA2-Enterprise|ModeEnabled}} or
               {{enum|WPA-WPA2-Enterprise|ModeEnabled}}).
            
               If this parameter is not implemented, the
               secondary RADIUS server will use the same port
               number as the primary RADIUS server.";
          }
          leaf RadiusSecret {
            type string;
            description
              "The secret used for handshaking with the RADIUS
               server {{bibref|RFC2865}}.";
          }
          leaf SecondaryRadiusSecret {
            type string;
            description
              "The secret used for handshaking with the secondary
               RADIUS server {{bibref|RFC2865}}.
            
               If this parameter is not implemented, the
               secondary RADIUS server will use the same secret
               as the primary RADIUS server.";
          }
        }

        container Accounting {
          description
            "This object contains the parameters related to RADIUS
             accounting functionality for the access point.";
          leaf Enable {
            type boolean;
            description
              "Enables or disables accounting functionality for the
               access point.";
          }
          leaf ServerIPAddr {
            type types:IPAddress;
            description
              "The IP Address of the RADIUS accounting server.";
          }
          leaf SecondaryServerIPAddr {
            type types:IPAddress;
            description
              "The IP Address of a secondary RADIUS accounting
               server.
            
               The client can forward requests to the secondary
               server in the event that the primary server is
               down or unreachable, or after a number of tries to
               the primary server fail, or in a round-robin
               fashion.  {{bibref|RFC2866}}";
          }
          leaf ServerPort {
            type uint32;
            default "1813";
            description
              "The port number of the RADIUS server used for
               accounting.  The default port is 1813 as defined
               in {{bibref|RFC2866}}.";
          }
          leaf SecondaryServerPort {
            type uint32;
            default "1813";
            description
              "The port number of the secondary RADIUS server used
               for accounting.  The default port is 1813 as
               defined in {{bibref|RFC2866}}.
            
               If this parameter is not implemented, the
               secondary RADIUS server will use the same port
               number as the primary RADIUS server.";
          }
          leaf Secret {
            type string;
            description
              "The secret used for handshaking with the RADIUS
               accounting server {{bibref|RFC2865}}.";
          }
          leaf SecondarySecret {
            type string;
            description
              "The secret used for handshaking with the secondary
               RADIUS accounting server {{bibref|RFC2865}}.
            
               If this parameter is not implemented, the
               secondary RADIUS server will use the same secret
               as the primary RADIUS server.";
          }
          leaf InterimInterval {
            type uint32 {
              range "0 | 60..max";
            }
            default "0";
            description
              "Specifies the default interim accounting interval in
               {{units}}, which is used for service accounting
               when the ''Acct-Interim-Interval'' attribute is
               not configured.  {{bibref|RFC2869|Section 2.1}}
            
               The value MUST NOT be smaller than 60.  The value
               SHOULD NOT be smaller than 600, and careful
               consideration should be given to its impact on
               network traffic {{bibref|RFC2869|Section 5.16}}.
            
               A value of 0 means no interim accounting messages
               are sent.";
          }
        }

        container WPS {
          description
            "This object contains parameters related to Wi-Fi
             Protected Setup {{bibref|WPSv1.0}} for this access
             point.";
          leaf Enable {
            type boolean;
            default "true";
            description
              "Enables or disables WPS functionality for this access
               point.";
          }
          leaf ConfigMethodsSupported {
            type enumeration {
              enum "USBFlashDrive";
              enum "Ethernet";
              enum "ExternalNFCToken";
              enum "IntegratedNFCToken";
              enum "NFCInterface";
              enum "PushButton";
              enum "PIN";
            }
            config false;
            description
              "{{list}} Indicates WPS configuration methods
               supported by the device.  {{enum}}
            
               This parameter corresponds directly to the
               \"Config Methods\" attribute of the WPS
               specification {{bibref|WPSv1.0}}.  The
               {{enum|PushButton}} and {{enum|PIN}} methods MUST
               be supported.";
          }
          leaf ConfigMethodsEnabled {
            type string;
            description
              "{{list}} Indicates WPS configuration methods enabled
               on the device.";
          }
        }

        list AssociatedDevice {
          key "MACAddress";
          config false;
          description
            "A table of the devices currently associated with the
             access point.";
          leaf MACAddress {
            type types:MACAddress;
            description
              "The MAC address of an associated device.";
          }
          leaf OperatingStandard {
            type enumeration {
              enum "a";
              enum "b";
              enum "g";
              enum "n";
              enum "ac";
            }
            description
              "The operating standard that this associated device is
               connected with.";
          }
          leaf AuthenticationState {
            type boolean;
            description
              "Whether an associated device has authenticated
               ({{true}}) or not ({{false}}).";
          }
          leaf LastDataDownlinkRate {
            type uint32 {
              range "1000..600000";
            }
            description
              "The data transmit rate in {{units}} that was most
               recently used for transmission from the access
               point to the associated device.";
          }
          leaf LastDataUplinkRate {
            type uint32 {
              range "1000..600000";
            }
            description
              "The data transmit rate in {{units}} that was most
               recently used for transmission from the associated
               device to the access point.";
          }
          leaf SignalStrength {
            type int32 {
              range "-200..0";
            }
            description
              "An indicator of radio signal strength of the uplink
               from the associated device to the access point,
               measured in {{units}}, as an average of the last
               100 packets received from the device.";
          }
          leaf Retransmissions {
            type uint32 {
              range "0..100";
            }
            description
              "The number of {{units}} that had to be
               re-transmitted, from the last 100 packets sent to
               the associated device.  Multiple re-transmissions
               of the same packet count as one.";
          }
          leaf Active {
            type boolean;
            description
              "Whether or not this node is currently present in the
               WiFi AccessPoint network.
            
               The ability to list inactive nodes is OPTIONAL.
               If the CPE includes inactive nodes in this table,
               {{param}} MUST be set to {{false}} for each
               inactive node.  The length of time an inactive
               node remains listed in this table is a local
               matter to the CPE.";
          }

          container Stats {
            description
              "These count bytes or packets sent to, or received
               from, this Associated Device, which is a WiFi
               station associated to this access point.  Packet
               counters here count 802.11 WiFi frames.
            
               The CPE MUST reset these {{object}} parameters
               (unless otherwise stated in individual object or
               parameter descriptions) either when the
               {{param|##.Status}} of the parent {{object|##}}
               object transitions from
               {{enum|Disabled|##.Status}} to
               {{enum|Enabled|##.Status}}, or when it transitions
               from {{enum|Enabled|##.Status}} to
               {{enum|Disabled|##.Status}}.";
            leaf BytesSent {
              type types:StatsCounter64;
              description
                "The total number of bytes transmitted to the
                 Associated Device, including framing characters.";
            }
            leaf BytesReceived {
              type types:StatsCounter64;
              description
                "The total number of bytes received from the
                 Associated Device, including framing characters.";
            }
            leaf PacketsSent {
              type types:StatsCounter64;
              description
                "The total number of packets transmitted to the
                 Associated Device.";
            }
            leaf PacketsReceived {
              type types:StatsCounter64;
              description
                "The total number of packets received from the
                 Associated Device.";
            }
            leaf ErrorsSent {
              type types:StatsCounter32;
              description
                "The total number of outbound packets that could not
                 be transmitted because of errors.  These might
                 be due to the number of retransmissions
                 exceeding the retry limit, or from other causes.";
            }
            leaf RetransCount {
              type types:StatsCounter32;
              description
                "The total number of transmitted packets which were
                 retransmissions.  Two retransmissions of the
                 same packet results in this counter incrementing
                 by two.";
            }
            leaf FailedRetransCount {
              type types:StatsCounter32;
              description
                "The number of packets that were not transmitted
                 successfully due to the number of retransmission
                 attempts exceeding an 802.11 retry limit.  This
                 parameter is based on ''dot11FailedCount'' from
                 {{bibref|802.11-2012}}.";
            }
            leaf RetryCount {
              type types:StatsCounter32;
              description
                "The number of packets that were successfully
                 transmitted after one or more retransmissions.
                 This parameter is based on ''dot11RetryCount''
                 from {{bibref|802.11-2012}}.";
            }
            leaf MultipleRetryCount {
              type types:StatsCounter32;
              description
                "The number of packets that were successfully
                 transmitted after more than one retransmission.
                 This parameter is based on
                 ''dot11MultipleRetryCount'' from
                 {{bibref|802.11-2012}}.";
            }
          }
        }

        list AC {
          key "AccessCategory";
          min-elements 4;
          max-elements 4;
          description
            "This object contains parameters related to WiFi QoS for
             different 802.11e access categories (priorities).
             Access categories are: BE, BK, VI, and VO.  These
             parameters can help control and monitor 802.11e
             Enhanced distributed channel access (EDCA).  The
             size of this table is fixed, with four entries which
             are identified by the {{param|AccessCategory}}
             parameter as follows:
          
             * BE (Best Effort)
          
             * BK (Background)
          
             * VI (Video)
          
             * VO (Voice)";
          leaf AccessCategory {
            type enumeration {
              enum "BE";
              enum "BK";
              enum "VI";
              enum "VO";
            }
            config false;
            description
              "This identifies the access category.";
          }
          leaf AIFSN {
            type uint32 {
              range "2..15";
            }
            description
              "Arbitration Inter Frame Spacing (Number).  This is
               the number of time slots in the arbitration
               interframe space.";
          }
          leaf ECWMin {
            type uint32 {
              range "0..15";
            }
            description
              "Exponent of Contention Window (Minimum).  This
               encodes the values of CWMin as an exponent: CWMin
               = 2^ECWMin - 1.  For example, if ECWMin is 8, then
               CWMin is 2^8 - 1, or 255, (expressed in
               {{units}}).";
          }
          leaf ECWMax {
            type uint32 {
              range "0..15";
            }
            description
              "Exponent of Contention Window (Maximum).  This
               encodes the values of CWMax as an exponent: CWMax
               = 2^ECWMax - 1.  For example, if ECWMax is 8, then
               CWMax is 2^8 - 1, or 255, (expressed in
               {{units}}).";
          }
          leaf TxOpMax {
            type uint32 {
              range "0..255";
            }
            description
              "Maximum transmit opportunity, in multiples of
               {{units}}.  A TXOP time interval of 0 means it is
               limited to a single MAC protocol data unit (MPDU).";
          }
          leaf AckPolicy {
            type boolean;
            description
              "Ack Policy, where False=\"Do Not Acknowledge\" and
               True=\"Acknowledge\"";
          }
          leaf OutQLenHistogramIntervals {
            type string;
            description
              "{{list}} Definition of the histogram intervals for
               counting the transmit queue length in packets.
               Each value indicates the maximum value of the
               interval.  For example, \"0,1,4,8,\" defines the
               five intervals: 0 packets in queue, 1 packet in
               queue, 2 to 4 packets in queue, 5 to 8 packets in
               queue, and 9 or more packets in queue.  (No value
               after the last comma means no upper bound.) If
               this parameter is set to {{empty}}, no
               {{param|Stats.OutQLenHistogram}} stats will be
               collected.";
          }
          leaf OutQLenHistogramSampleInterval {
            type uint32;
            description
              "The time between recording samples of the current
               transmit queue in {{units}}.";
          }

          container Stats {
            config false;
            description
              "This object contains statistics for different 802.11e
               access categories (priorities).
            
               Packet counters here count 802.11 WiFi frames.
            
               If there are not separate stats for each access
               category, (e.g., 802.11e is not used and there is
               only one queue), then only access category 0 = BE
               applies (e.g., the statistics for the single queue
               are in access category 0 = BE).
            
               The CPE MUST reset the Access Point's Stats
               parameters (unless otherwise stated in individual
               object or parameter descriptions) either when the
               Access Point becomes operationally down due to a
               previous administrative down (i.e.  the Access
               Point's Status parameter transitions to a Diasbled
               state) or when the Access Point becomes
               administratively up (i.e.  the Access Point's
               Enable parameter transitions from false to true).
               Administrative and operational status is discussed
               in [Section 4.2.2/TR-181i2].";
            leaf BytesSent {
              type types:StatsCounter64;
              description
                "The total number of {{units}} transmitted in this
                 access category, including framing characters.";
            }
            leaf BytesReceived {
              type types:StatsCounter64;
              description
                "The total number of {{units}} received in this
                 access category, including framing characters.";
            }
            leaf PacketsSent {
              type types:StatsCounter64;
              description
                "The total number of {{units}} transmitted in this
                 access category.";
            }
            leaf PacketsReceived {
              type types:StatsCounter64;
              description
                "The total number of {{units}} received in this
                 access category.";
            }
            leaf ErrorsSent {
              type types:StatsCounter32;
              description
                "The total number of outbound {{units}} in this
                 access category that could not be transmitted
                 because of errors.  These might be due to the
                 number of retransmissions exceeding the retry
                 limit, or from other causes.";
            }
            leaf ErrorsReceived {
              type types:StatsCounter32;
              description
                "The total number of inbound {{units}} in this
                 access category that contained errors preventing
                 them from being delivered to a higher-layer
                 protocol.";
            }
            leaf DiscardPacketsSent {
              type types:StatsCounter32;
              description
                "The total number of outbound {{units}} in this
                 access category which were chosen to be
                 discarded even though no errors had been
                 detected to prevent their being transmitted.
                 One possible reason for discarding such a packet
                 could be to free up buffer space.";
            }
            leaf DiscardPacketsReceived {
              type types:StatsCounter32;
              description
                "The total number of inbound {{units}} in this
                 access category which were chosen to be
                 discarded even though no errors had been
                 detected to prevent their being delivered.  One
                 possible reason for discarding such a packet
                 could be to free up buffer space.";
            }
            leaf RetransCount {
              type types:StatsCounter32;
              description
                "The total number of transmitted {{units}} in this
                 access category which were retransmissions.  Two
                 retransmissions of the same packet results in
                 this counter incrementing by two.";
            }
            leaf OutQLenHistogram {
              type string;
              description
                "{{list}} Histogram of the total length of the
                 transmit queue of this access category in
                 packets (1 packet, 2 packets, etc.) according to
                 the intervals defined by
                 {{param|#.OutQLenHistogramIntervals}}, with
                 samples taken each
                 {{param|#.OutQLenHistogramSampleInterval}}.
                 Example: \"12,5,1,0,2,0,0,1\".";
            }
          }
        }
      }

      list EndPoint {
        key "SSIDReference";
        description
          "This object models an 802.11 connection from the
           perspective of a wireless end point.  Each {{object}}
           entry is associated with a particular
           {{object|#.SSID}} interface instance via the
           {{param|SSIDReference}} parameter, and an associated
           active {{object|Profile}} instance via the
           {{param|ProfileReference}} parameter.  The active
           profile is responsible for specifying the actual SSID
           and security settings used by the end point.
        
           For enabled table entries, if {{param|SSIDReference}}
           or {{param|ProfileReference}} is not a valid reference
           then the table entry is inoperable and the CPE MUST
           set {{param|Status}} to
           {{enum|Error_Misconfigured|Status}}.
        
           Note: The {{object}} table includes a unique key
           parameter that is a strong reference.  If a strongly
           referenced object is deleted, the CPE will set the
           referencing parameter to {{empty}}.  However, doing so
           under these circumstances might cause the updated
           {{object}} row to then violate the table's unique key
           constraint; if this occurs, the CPE MUST set
           {{param|Status}} to
           {{enum|Error_Misconfigured|Status}} and disable the
           offending {{object}} row.";
        leaf Enable {
          type boolean;
          default "false";
          description
            "Enables or disables this end point.";
        }
        leaf Status {
          type enumeration {
            enum "Disabled";
            enum "Enabled";
            enum "Error_Misconfigured";
            enum "Error";
          }
          config false;
          default "Disabled";
          description
            "Indicates the status of this end point.  {{enum}}
          
             The {{enum|Error_Misconfigured}} value indicates
             that a necessary configuration value is undefined or
             invalid.
          
             The {{enum|Error}} value MAY be used by the CPE to
             indicate a locally defined error condition.";
        }
        leaf ProfileReference {
          type string {
            length "0..256";
          }
          default "";
          description
            "{{reference}} This is the currently active profile,
             which specifies the SSID and security settings to be
             used by the end point.";
        }
        leaf SSIDReference {
          type string {
            length "0..256";
          }
          config false;
          default "";
          description
            "{{reference}} {{param}} is determined based on the
             {{param|Profile.{i}.SSID}} within the associated
             {{param|ProfileReference}}) endpoint profile.
             {{param}} MUST be {{empty}} if
             {{param|ProfileReference}} is {{empty}} (i.e.  only
             when an active profile is assigned can the
             associated SSID interface be determined).";
        }

        container Stats {
          config false;
          description
            "Throughput statistics for this end point.";
          leaf LastDataDownlinkRate {
            type uint32 {
              range "1000..600000";
            }
            description
              "The data transmit rate in {{units}} that was most
               recently used for transmission from the access
               point to the end point device.";
          }
          leaf LastDataUplinkRate {
            type uint32 {
              range "1000..600000";
            }
            description
              "The data transmit rate in {{units}} that was most
               recently used for transmission from the end point
               to the access point device.";
          }
          leaf SignalStrength {
            type int32 {
              range "-200..0";
            }
            description
              "An indicator of radio signal strength of the downlink
               from the access point to the end point, measured
               in {{units}}, as an average of the last 100
               packets received from the device.";
          }
          leaf Retransmissions {
            type uint32 {
              range "0..100";
            }
            default "0";
            description
              "The number of {{units}} that had to be
               re-transmitted, from the last 100 packets sent to
               the access point.  Multiple re-transmissions of
               the same packet count as one.";
          }
        }

        container Security {
          config false;
          description
            "This object contains security related parameters that
             apply to a WiFi end point {{bibref|802.11-2007}}.";
          leaf ModesSupported {
            type enumeration {
              enum "None";
              enum "WEP-64";
              enum "WEP-128";
              enum "WPA-Personal";
              enum "WPA2-Personal";
              enum "WPA-WPA2-Personal";
              enum "WPA-Enterprise";
              enum "WPA2-Enterprise";
              enum "WPA-WPA2-Enterprise";
            }
            description
              "{{list}} Indicates which security modes this
               {{object|#}} instance is capable of supporting.";
          }
        }

        list Profile {
          key "SSID Location Priority";
          description
            "EndPoint Profile table.";
          leaf Enable {
            type boolean;
            default "false";
            description
              "Enables or disables this Profile.
            
               When there are multiple WiFi EndPoint Profiles,
               e.g.  each instance supports a different SSID
               and/or different security configuration, this
               parameter can be used to control which of the
               instances are currently enabled.";
          }
          leaf Status {
            type enumeration {
              enum "Active";
              enum "Available";
              enum "Error";
              enum "Disabled";
            }
            config false;
            default "Disabled";
            description
              "Indicates the status of this Profile.  {{enum}}
            
               The {{enum|Active}} value is reserved for the
               instance that is actively connected.  The
               {{enum|Available}} value represents an instance
               that is not currently active, but is also not
               disabled or in error.  The {{enum|Error}} value
               MAY be used by the CPE to indicate a locally
               defined error condition.";
          }
          leaf SSID {
            type string {
              length "0..32";
            }
            description
              "The profile identifier in use by the connection.  The
               SSID is an identifier that is attached to packets
               sent over the wireless LAN that functions as an ID
               for joining a particular radio network (BSS).";
          }
          leaf Location {
            type string;
            description
              "Location of the profile.  This value serves as a
               reminder from the user, describing the location of
               the profile.  For example: \"Home\", \"Office\",
               \"Neighbor House\", \"Airport\", etc.  An empty
               string is also valid.";
          }
          leaf Priority {
            type uint32 {
              range "min..255";
            }
            default "0";
            description
              "The profile Priority defines one of the criteria used
               by the End Point to automatically select the
               \"best\" AP when several APs with known profiles
               are simultaneously available for association.
            
               In this situation, the End Point has to select the
               AP with the higher priority in its profile.  If
               there are several APs with the same priority,
               providing different SSID or the same SSID, then
               the wireless end point has to select the APs
               according to other criteria like signal quality,
               SNR, etc.
            
               0 is the highest priority.";
          }

          container Security {
            description
              "This object contains security related parameters that
               apply to a WiFi End Point profile
               {{bibref|802.11-2007}}.";
            leaf ModeEnabled {
              type string;
              description
                "Indicates which security mode is enabled.";
            }
            leaf WEPKey {
              type yang:hex-string {
                length "5 | 13";
              }
              description
                "A WEP key expressed as a hexadecimal string.
              
                 {{param}} is used only if {{param|ModeEnabled}}
                 is set to {{enum|WEP-64|ModeEnabled}} or
                 {{enum|WEP-128|ModeEnabled}}.
              
                 A 5 byte {{param}} corresponds to security mode
                 {{enum|WEP-64|ModeEnabled}} and a 13 byte
                 {{param}} corresponds to security mode
                 {{enum|WEP-128|ModeEnabled}}.";
            }
            leaf PreSharedKey {
              type yang:hex-string {
                length "0..32";
              }
              description
                "A literal PreSharedKey (PSK) expressed as a
                 hexadecimal string.
              
                 {{param}} is only used if {{param|ModeEnabled}}
                 is set to {{enum|WPA-Personal|ModeEnabled}} or
                 {{enum|WPA2-Personal|ModeEnabled}} or
                 {{enum|WPA-WPA2-Personal|ModeEnabled}}.
              
                 If {{param|KeyPassphrase}} is written, then
                 {{param}} is immediately generated.  The ACS
                 SHOULD NOT set both the {{param|KeyPassphrase}}
                 and the {{param}} directly (the result of doing
                 this is undefined).";
            }
            leaf KeyPassphrase {
              type string {
                length "8..63";
              }
              description
                "A passphrase from which the {{param|PreSharedKey}}
                 is to be generated, for
                 {{enum|WPA-Personal|ModeEnabled}} or
                 {{enum|WPA2-Personal|ModeEnabled}} or
                 {{enum|WPA-WPA2-Personal|ModeEnabled}} security
                 modes.
              
                 If {{param}} is written, then
                 {{param|PreSharedKey}} is immediately generated.
                 The ACS SHOULD NOT set both the {{param}} and
                 the {{param|PreSharedKey}} directly (the result
                 of doing this is undefined).  The key is
                 generated as specified by WPA, which uses PBKDF2
                 from PKCS #5: Password-based Cryptography
                 Specification Version 2.0 {{bibref|RFC2898}}.";
            }
          }
        }

        container WPS {
          description
            "This object contains parameters related to Wi-Fi
             Protected Setup {{bibref|WPSv1.0}} for this end
             point.";
          leaf Enable {
            type boolean;
            default "true";
            description
              "Enables or disables WPS functionality for this end
               point.";
          }
          leaf ConfigMethodsSupported {
            type enumeration {
              enum "USBFlashDrive";
              enum "Ethernet";
              enum "ExternalNFCToken";
              enum "IntegratedNFCToken";
              enum "NFCInterface";
              enum "PushButton";
              enum "PIN";
            }
            config false;
            description
              "{{list}} Indicates the WPS configuration methods
               supported by the device.  {{enum}}
            
               This parameter corresponds directly to the
               \"Config Methods\" attribute of the WPS
               specification {{bibref|WPSv1.0}}.";
          }
          leaf ConfigMethodsEnabled {
            type string;
            description
              "{{list}} Indicates the WPS configuration methods
               enabled on the device.";
          }
        }

        list AC {
          key "AccessCategory";
          min-elements 4;
          max-elements 4;
          description
            "This object contains parameters related to WiFi QoS for
             different 802.11e access categories (priorities).
             Access categories are: BE, BK, VI, and VO.  These
             parameters can help control and monitor 802.11e
             Enhanced distributed channel access (EDCA).  The
             size of this table is fixed, with four entries which
             are identified by the {{param|AccessCategory}}
             parameter as follows:
          
             * BE (Best Effort)
          
             * BK (Background)
          
             * VI (Video)
          
             * VO (Voice)";
          leaf AccessCategory {
            type enumeration {
              enum "BE";
              enum "BK";
              enum "VI";
              enum "VO";
            }
            config false;
            description
              "This identifies the access category.";
          }
          leaf AIFSN {
            type uint32 {
              range "2..15";
            }
            description
              "Arbitration Inter Frame Spacing (Number).  This is
               the number of time slots in the arbitration
               interframe space.";
          }
          leaf ECWMin {
            type uint32 {
              range "0..15";
            }
            description
              "Exponent of Contention Window (Minimum).  This
               encodes the values of CWMin as an exponent: CWMin
               = 2^ECWMin - 1.  For example, if ECWMin is 8, then
               CWMin is 2^8 - 1, or 255, (expressed in
               {{units}}).";
          }
          leaf ECWMax {
            type uint32 {
              range "0..15";
            }
            description
              "Exponent of Contention Window (Maximum).  This
               encodes the values of CWMax as an exponent: CWMax
               = 2^ECWMax - 1.  For example, if ECWMax is 8, then
               CWMax is 2^8 - 1, or 255, (expressed in
               {{units}}).";
          }
          leaf TxOpMax {
            type uint32 {
              range "0..255";
            }
            description
              "Maximum transmit opportunity, in multiples of
               {{units}}.  A TXOP time interval of 0 means it is
               limited to a single MAC protocol data unit (MPDU).";
          }
          leaf AckPolicy {
            type boolean;
            description
              "Ack Policy, where False=\"Do Not Acknowledge\" and
               True=\"Acknowledge\"";
          }
          leaf OutQLenHistogramIntervals {
            type string;
            description
              "{{list}} Definition of the histogram intervals for
               counting the transmit queue length in packets.
               Each value indicates the maximum value of the
               interval.  For example, \"0,1,4,8,\" defines the
               five intervals: 0 packets in queue, 1 packet in
               queue, 2 to 4 packets in queue, 5 to 8 packets in
               queue, and 9 or more packets in queue.  (No value
               after the last comma means no upper bound.) If
               this parameter is set to an empty string, no
               {{param|Stats.OutQLenHistogram}} stats will be
               collected.";
          }
          leaf OutQLenHistogramSampleInterval {
            type uint32;
            description
              "The time between recording samples of the current
               transmit queue {{units}}.";
          }

          container Stats {
            config false;
            description
              "This object contains statistics for different 802.11e
               access categories (priorities).
            
               Packet counters here count 802.11 WiFi frames.
            
               If there are not separate stats for each access
               category, (e.g., 802.11e is not used and there is
               only one queue), then only access category 0 = BE
               applies (e.g., the statistics for the single queue
               are in access category 0 = BE).
            
               The CPE MUST reset the EndPoint's Stats parameters
               (unless otherwise stated in individual object or
               parameter descriptions) either when the EndPoint
               becomes operationally down due to a previous
               administrative down (i.e.  the EndPoint's Status
               parameter transitions to a Diasbled state) or when
               the EndPoint becomes administratively up (i.e.
               the EndPoint's Enable parameter transitions from
               false to true).  Administrative and operational
               status is discussed in [Section 4.2.2/TR-181i2].";
            leaf BytesSent {
              type types:StatsCounter64;
              description
                "The total number of {{units}} transmitted in this
                 access category, including framing characters.";
            }
            leaf BytesReceived {
              type types:StatsCounter64;
              description
                "The total number of {{units}} received in this
                 access category, including framing characters.";
            }
            leaf PacketsSent {
              type types:StatsCounter64;
              description
                "The total number of {{units}} transmitted in this
                 access category.";
            }
            leaf PacketsReceived {
              type types:StatsCounter64;
              description
                "The total number of {{units}} received in this
                 access category.";
            }
            leaf ErrorsSent {
              type types:StatsCounter32;
              description
                "The total number of outbound {{units}} in this
                 access category that could not be transmitted
                 because of errors.  These might be due to the
                 number of retransmissions exceeding the retry
                 limit, or from other causes.";
            }
            leaf ErrorsReceived {
              type types:StatsCounter32;
              description
                "The total number of inbound {{units}} in this
                 access category that contained errors preventing
                 them from being delivered to a higher-layer
                 protocol.";
            }
            leaf DiscardPacketsSent {
              type types:StatsCounter32;
              description
                "The total number of outbound {{units}} in this
                 access category which were chosen to be
                 discarded even though no errors had been
                 detected to prevent their being transmitted.
                 One possible reason for discarding such a packet
                 could be to free up buffer space.";
            }
            leaf DiscardPacketsReceived {
              type types:StatsCounter32;
              description
                "The total number of inbound {{units}} in this
                 access category which were chosen to be
                 discarded even though no errors had been
                 detected to prevent their being delivered.  One
                 possible reason for discarding such a packet
                 could be to free up buffer space.";
            }
            leaf RetransCount {
              type types:StatsCounter32;
              description
                "The total number of transmitted {{units}} in this
                 access category which were retransmissions.  Two
                 retransmissions of the same packet results in
                 this counter incrementing by two.";
            }
            leaf OutQLenHistogram {
              type string;
              description
                "{{list}} Histogram of the total length of the
                 transmit queue of this access category in
                 packets (1 packet, 2 packets, etc.) according to
                 the intervals defined by
                 {{param|#.OutQLenHistogramIntervals}}, with
                 samples taken each
                 {{param|#.OutQLenHistogramSampleInterval}}.
                 Example: \"12,5,1,0,2,0,0,1\"";
            }
          }
        }
      }
    }

    container ZigBee {
      description
        "Top level object for ZigBee capabilities based on the
         {{bibref|ZigBee2007}} specification.";

      list Interface {
        key "ZDOReference";
        description
          "ZigBee interface table (a stackable interface object as
           described in {{bibref|TR-181i2|Section 4.2}}).  This
           table models the ZigBee interface of a ZigBee end
           device, ZigBee router or ZigBee coordinator.";
        leaf Enable {
          type boolean;
          description
            "Enables or disables the interface.  This parameter is
             based on ''ifAdminStatus'' from {{bibref|RFC2863}}.";
        }
        leaf Status {
          type enumeration {
            enum "Up";
            enum "Down";
            enum "Unknown";
            enum "Dormant";
            enum "NotPresent";
            enum "LowerLayerDown";
            enum "Error";
          }
          config false;
          description
            "The current operational state of the interface (see
             {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the interface as assigned by the
             CPE.";
        }
        leaf LastChange {
          type uint32;
          config false;
          description
            "The accumulated time in {{units}} since the interface
             entered its current operational state.";
        }
        leaf LowerLayers {
          type string;
          description
            "{{list}} {{reference|an interface object that is
             stacked immediately below this interface object}}
             See {{bibref|TR-181i2|Section 4.2.1}}.";
        }
        leaf IEEEAddress {
          type types:IEEE_EUI64;
          config false;
          description
            "The IEEE address assigned to this interface.  A value
             of \"FF:FF:FF:FF:FF:FF:FF:FF\" indicates that this
             address is unknown.  This parameter has the same
             value as the {{param|.ZigBee.ZDO.{i}.IEEEAddress}}
             parameter of the ZDO instance {{param|ZDOReference}}
             is pointing to.";
        }
        leaf NetworkAddress {
          type types:ZigBeeNetworkAddress;
          config false;
          description
            "The ZigBee network address assigned to this interface.
             This parameter has the same value as the
             {{param|.ZigBee.ZDO.{i}.NetworkAddress}} parameter
             of the ZDO instance {{param|ZDOReference}} is
             pointing to.";
        }
        leaf ZDOReference {
          type string {
            length "0..256";
          }
          config false;
          description
            "The ZigBee Device Object assigned to this interface.";
        }

        container Stats {
          config false;
          description
            "Throughput statistics for this interface.
          
             The CPE MUST reset the interface's Stats parameters
             (unless otherwise stated in individual object or
             parameter descriptions) either when the interface
             becomes operationally down due to a previous
             administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2|section 4.2.2}}.";
          leaf BytesSent {
            type types:StatsCounter64;
            description
              "The total number of {{units}} transmitted out of the
               interface, including framing characters.";
          }
          leaf BytesReceived {
            type types:StatsCounter64;
            description
              "The total number of {{units}} received on the
               interface, including framing characters.";
          }
          leaf PacketsSent {
            type types:StatsCounter64;
            description
              "The total number of {{units}} sent transmitted out of
               the interface.";
          }
          leaf PacketsReceived {
            type types:StatsCounter64;
            description
              "The total number of {{units}} received by the
               interface.";
          }
          leaf ErrorsSent {
            type types:StatsCounter32;
            description
              "The total number of {{units}} discarded by interface
               due to any error.";
          }
          leaf ErrorsReceived {
            type types:StatsCounter32;
            description
              "The total number of {{units}} received that contained
               errors preventing them from being delivered to a
               higher-layer protocol.";
          }
          leaf UnicastPacketsSent {
            type types:StatsCounter32;
            description
              "The total number of {{units}} requested for
               transmission which were not addressed to a
               multicast or broadcast address at this layer,
               including those that were discarded or not sent.";
          }
          leaf UnicastPacketsReceived {
            type types:StatsCounter32;
            description
              "The total number of {{units}} received which were not
               addressed to a multicast or broadcast address at
               this layer.";
          }
          leaf DiscardPacketsSent {
            type types:StatsCounter32;
            description
              "The total number of {{units}} requested for
               transmission which were chosen to be discarded
               even though no errors had been detected to prevent
               the {{units}} being transmitted.";
          }
          leaf DiscardPacketsReceived {
            type types:StatsCounter32;
            description
              "The total number of {{units}} received which were
               chosen to be discarded even though no errors had
               been detected to prevent their being delivered.";
          }
          leaf MulticastPacketsSent {
            type types:StatsCounter32;
            description
              "The total number of {{units}} requested for
               transmission which were addressed to a multicast
               address at this layer, including those that were
               discarded or not sent.";
          }
          leaf MulticastPacketsReceived {
            type types:StatsCounter32;
            description
              "The total number of {{units}} received which were
               addressed to a multicast address at this layer and
               delivered by this layer to a higher layer.";
          }
          leaf BroadcastPacketsSent {
            type types:StatsCounter32;
            description
              "The total number of {{units}} requested for
               transmission which were addressed to a broadcast
               address at this layer, including those that were
               discarded or not sent.";
          }
          leaf BroadcastPacketsReceived {
            type types:StatsCounter32;
            description
              "The total number of {{units}} received which were
               addressed to a broadcast address at this layer and
               delivered by this layer to a higher layer.";
          }
          leaf UnknownPacketsReceived {
            type types:StatsCounter32;
            description
              "The total number of {{units}} received which were
               discarded because of an unknown or unsupported
               protocol.";
          }
        }

        list AssociatedDevice {
          key "IEEEAddress NetworkAddress";
          config false;
          description
            "This table provides information about other ZigBee
             devices that are directly accessible via this
             interface.
          
             {{keys}}
          
             It is possible that instances of this object have
             the same key value when the value of
             {{param|IEEEAddress}} parameter is
             \"FF:FF:FF:FF:FF:FF:FF:FF\" and the ZigBee
             Coordinators on two or more separate area networks
             assign the same value for the
             {{param|NetworkAddress}}.  This is because the
             ZigBee specification describes only intra-area
             network topologies {{bibref|ZigBee2007|Section 1.1.4
             Network Topology}}.  As such if two or more
             {{object}} instances have the same key value the
             implemenation is undefined.";
          leaf IEEEAddress {
            type types:IEEE_EUI64;
            description
              "The IEEE address assigned to this device.  A value of
               \"FF:FF:FF:FF:FF:FF:FF:FF\" indicates that this
               address is unknown.";
          }
          leaf NetworkAddress {
            type types:ZigBeeNetworkAddress;
            description
              "The ZigBee network address assigned to this device.";
          }
          leaf Active {
            type boolean;
            description
              "Whether or not this device is currently present in
               the ZigBee network as defined in
               {{bibref|ZigBee2007|section 2.4.4.1}}.
            
               The ability to list inactive devices is OPTIONAL.
               If the CPE includes inactive devices in this
               table, {{param}} MUST be set to {{false}} for each
               inactive device.  The length of time an inactive
               device remains listed in this table is a local
               matter to the CPE.";
          }
          leaf ZDOReference {
            type string {
              length "0..256";
            }
            description
              "The ZigBee Device Object assigned to this interface.";
          }
        }
      }

      list ZDO {
        key "IEEEAddress NetworkAddress";
        description
          "ZigBee Device Object (ZDO) provides management
           capabilities of the ZigBee Application Support (APS)
           and Network (NWK) layers of a ZigBee Device as defined
           in {{bibref|ZigBee2007|section 2.5}}.
        
           {{keys}}
        
           It is possible that instances of this object have the
           same key value when the value of {{param|IEEEAddress}}
           parameter is \"FF:FF:FF:FF:FF:FF:FF:FF\" and the
           ZigBee Coordinators on two or more separate area
           networks assign the same value for the
           {{param|NetworkAddress}}.  This is because the ZigBee
           specification describes only intra-area network
           topologies {{bibref|ZigBee2007|Section 1.1.4 Network
           Topology}}.  As such if two or more {{object}}
           instances have the same key value the implemenation is
           undefined";
        leaf IEEEAddress {
          type types:IEEE_EUI64;
          config false;
          description
            "The IEEE address assigned to this device.  A value of
             \"FF:FF:FF:FF:FF:FF:FF:FF\" indicates that this
             address is unknown.";
        }
        leaf NetworkAddress {
          type types:ZigBeeNetworkAddress;
          config false;
          description
            "The ZigBee network address assigned to this device.";
        }

        container NodeDescriptor {
          config false;
          description
            "The {{object}} object describes the node capabilities
             of the ZigBee device as defined in
             {{bibref|ZigBee2007|section 2.3.2.3 Node
             Descriptor}}.";
          leaf LogicalType {
            type enumeration {
              enum "ZC";
              enum "ZR";
              enum "ZED";
            }
            description
              "The type of ZigBee device that is extracted from the
               Logical Type Field as defined in
               {{bibref|ZigBee2007|Table 2.29}}.
            
               {{enum}}";
          }
          leaf ComplexDescriptorSupported {
            type boolean;
            description
              "When {{true}}, specifies that the
               {{object|#.ComplexDescriptor}} object is supported
               for this ZigBee device.";
          }
          leaf UserDescriptorSupported {
            type boolean;
            description
              "When {{true}}, specifies that the
               {{object|#.UserDescriptor}} object is supported
               for this ZigBee device.";
          }
          leaf FrequencyBand {
            type enumeration {
              enum "868-868.6";
              enum "902-928";
              enum "2400-2483.5";
            }
            description
              "Specifies the frequency bands that are supported by
               the underlying IEEE 802.15.4 radio utilized by the
               ZigBee device.
            
               {{list}} {{enum}}";
          }
          leaf MACCapability {
            type enumeration {
              enum "AlternatePANCoordinator";
              enum "FFD";
              enum "MainsPowerSource";
              enum "OnWhenIdle";
              enum "SecureCommunication";
            }
            description
              "Specifies the IEEE 802.15.4-2003 MAC sub-layer
               capabilities for this ZigBee device.
            
               {{list}} {{enum}}";
          }
          leaf ManufactureCode {
            type uint32 {
              range "min..65535";
            }
            description
              "Specifies a manufacturer code that is allocated by
               the ZigBee Alliance, relating the manufacturer to
               the device.";
          }
          leaf MaximumBufferSize {
            type uint32 {
              range "min..128";
            }
            description
              "Specifies the maximum buffer size, in {{units}}, of
               the network sub-layer data unit (NSDU) for this
               ZigBee device.";
          }
          leaf MaximumIncomingTransferSize {
            type uint32 {
              range "min..32768";
            }
            description
              "Specifies the maximum size, in {{units}}, of the
               application sub-layer data unit (ASDU) that can be
               transferred to this ZigBee device in one single
               message transfer.";
          }
          leaf MaximumOutgoingTransferSize {
            type uint32 {
              range "min..32768";
            }
            description
              "Specifies the maximum size, in {{units}}, of the
               application sub-layer data unit (ASDU) that can be
               transferred from this ZigBee device in one single
               message transfer.";
          }
          leaf ServerMask {
            type enumeration {
              enum "PrimaryTrustCenter";
              enum "PrimaryBindingTableCache";
              enum "BackupBindingTableCache";
              enum "PrimaryDiscoveryCache";
              enum "BackupDiscoveryCache";
              enum "NetworkManager";
            }
            description
              "Specifies the system server capabilities of this
               ZigBee device.
            
               {{list}} {{enum}}";
          }
          leaf DescriptorCapability {
            type enumeration {
              enum "ExtendedActiveEndpointListAvailable";
              enum "ExtendedSimpleDescriptorListAvailable";
            }
            description
              "Specifies the descriptor capabilities of this ZigBee
               device.
            
               {{list}} {{enum}}";
          }
        }

        container PowerDescriptor {
          config false;
          description
            "The {{object}} object describes the power capabilities
             of the ZigBee device as defined in
             {{bibref|ZigBee2007|section 2.3.2.4 Node Power
             Descriptor}}.";
          leaf CurrentPowerMode {
            type enumeration {
              enum "Synchronized";
              enum "Periodic";
              enum "Manual";
            }
            description
              "Specifies the current sleep/power-saving mode of the
               ZigBee device.
            
               {{enum}}";
          }
          leaf AvailablePowerSource {
            type enumeration {
              enum "Constant";
              enum "Rechargeable";
              enum "Disposable";
            }
            description
              "Specifies the power sources available on this ZigBee
               device.
            
               {{list}} {{enum}}";
          }
          leaf CurrentPowerSource {
            type enumeration {
              enum "Constant";
              enum "Rechargeable";
              enum "Disposable";
            }
            description
              "The current power source field specifies the current
               power source being utilized by the node.
            
               {{enum}}";
          }
          leaf CurrentPowerSourceLevel {
            type enumeration {
              enum "Critical";
              enum "33";
              enum "66";
              enum "100";
            }
            description
              "Specifies the level of charge of the current power
               source.
            
               {{enum}}";
          }
        }

        container UserDescriptor {
          config false;
          description
            "The {{object}} object is an optional descriptor that
             describes user defined capabilities of the ZigBee
             device as defined in {{bibref|ZigBee2007|section
             2.3.2.7 User Descriptor}}.  The {{object}} object
             contains information that allows the user to
             identify the device using a user-friendly character
             string, such as \"Bedroom TV\" or \"Stairs Light\".";
          leaf DescriptorAvailable {
            type boolean;
            description
              "When {{true}}, the User Descriptor recorded has been
               received from the target device.";
          }
          leaf Description {
            type string {
              length "0..16";
            }
            description
              "Specifies the information that allows the user to
               identify the ZigBee device using a user-friendly
               character string, such as \"Bedroom TV\" or
               \"Stairs light\".";
          }
        }

        container ComplexDescriptor {
          config false;
          description
            "The {{object}} object is an optional descriptor that
             describes extended capabilities of the ZigBee device
             as defined in {{bibref|ZigBee2007|section 2.3.2.6
             Complex Descriptor}}.";
          leaf DescriptorAvailable {
            type boolean;
            description
              "When {{true}}, the Complex Descriptor recorded has
               been received from the target device.";
          }
          leaf Language {
            type string;
            description
              "Specifies the ISO 639-1 language code as defined in
               {{bibref|ISO639-1}}.";
          }
          leaf CharacterSet {
            type string;
            description
              "Specifies the ISO 646 character set as defined in
               {{bibref|ISO646-1991}}.";
          }
          leaf ManufacturerName {
            type string;
            description
              "Specifies the name of the manufacturer of the ZigBee
               device.";
          }
          leaf ModelName {
            type string;
            description
              "Specifies the name of the manufacturer's model of the
               ZigBee device.";
          }
          leaf SerialNumber {
            type string;
            description
              "Specifies the manufacturer's serial number of the
               ZigBee device.";
          }
          leaf DeviceURL {
            type string;
            description
              "Specifies the URL through which more information
               relating to the ZigBee device can be obtained.";
          }
          leaf Icon {
            type yang:hex-string {
              length "0..65535";
            }
            description
              "The icon field contains an octet string which carries
               the data for an icon that can represent the ZigBee
               device.  The format of the icon MUST be a
               32-by-32-pixel PNG image.";
          }
          leaf IconURL {
            type string;
            description
              "Specifies the URL through which the icon for the
               ZigBee device can be obtained.";
          }
        }

        container Security {
          config false;
          description
            "The {{object}} object provides the configuration
             capabilities needed to perform the Security
             Management functionality defined in
             {{bibref|ZigBee2007|section 4 Security Management}}.";
          leaf TrustCenterAddress {
            type types:IEEE_EUI64;
            description
              "Specifies the IEEE address of a special device
               trusted by devices within a ZigBee network to
               distribute keys for the purpose of network and
               end-to-end application configuration management.";
          }
          leaf SecurityLevel {
            type enumeration {
              enum "None";
              enum "MIC-32";
              enum "MIC-64";
              enum "MIC-128";
              enum "ENC";
              enum "ENC-MIC-32";
              enum "ENC-MIC-64";
              enum "ENC-MIC-128";
            }
            description
              "Specifies how an outgoing frame is to be secured, how
               an incoming frame purportedly has been secured; it
               also indicates whether or not the payload is
               encrypted and to what extent data authenticity
               over the frame is provided, as reflected by the
               length of the message integrity code (MIC).
            
               {{enum}}";
          }
          leaf TimeOutPeriod {
            type uint32 {
              range "min..65535";
            }
            description
              "The period of time, in {{units}}, that this ZigBee
               device will wait for an expected security protocol
               frame.";
          }
        }

        container Network {
          config false;
          description
            "The {{object}} object provides the configuration
             capabilities needed to by a ZigBee Device to operate
             within a ZigBee Area Network as defined in
             {{bibref|ZigBee2007|section 2.5.2.4 Network
             Manager}}.";

          list Neighbor {
            key "Neighbor";
            description
              "The {{object}} object provides the configuration
               capabilities needed to by a ZigBee Device to
               operate within a ZigBee Area Network as defined in
               {{bibref|ZigBee2007|section 2.5.2.4 Network
               Manager}}.";
            leaf Neighbor {
              type string;
              description
                "Neighbor of this ZigBee device.  The value MUST be
                 the path name of a row in the ZigBee.ZDO table.
                 If the referenced row is deleted then this entry
                 MUST be deleted.";
            }
            leaf LQI {
              type uint32 {
                range "min..255";
              }
              description
                "The LQI field specified link quality identification
                 (LQI) for neighbor ZigBee device.";
            }
            leaf Relationship {
              type enumeration {
                enum "Parent";
                enum "Child";
                enum "PrevChild";
                enum "Sibling";
                enum "None";
              }
              description
                "The relationship between the neighbor and this
                 device.{{enum}}";
            }
            leaf PermitJoin {
              type enumeration {
                enum "Accepting";
                enum "NotAccepting";
                enum "Unknown";
              }
              description
                "An indication of whether the neighbor device is
                 accepting join requests.{{enum}}";
            }
            leaf Depth {
              type uint32;
              description
                "The tree depth of the neighbor device.  A value of
                 0x00 indicates that the device is the ZigBee
                 coordinator for the network.";
            }
          }
        }

        container NodeManager {
          config false;
          description
            "The {{object}} object describes the configuration
             capabilities related for remote management of the
             ZigBee Area Network as defined in
             {{bibref|ZigBee2007|section 2.5.2.6 Node Manager}}.";

          list RoutingTable {
            key "DestinationAddress";
            description
              "The {{object}} object describes the route table as
               defined in {{bibref|ZigBee2007|table 3.51 Routing
               Table Entry}}.";
            leaf DestinationAddress {
              type string {
                length "0..4";
                pattern "([0-9A-Fa-f]){4}";
              }
              description
                "The ZigBee network address of this route.";
            }
            leaf NextHopAddress {
              type types:ZigBeeNetworkAddress;
              description
                "Specifies the network address of the next hop
                 ZigBee device on the way to the destination
                 ZigBee device.";
            }
            leaf Status {
              type enumeration {
                enum "Active";
                enum "DiscoveryUnderway";
                enum "DiscoveryFailed";
                enum "Inactive";
                enum "ValidationUnderway";
              }
              description
                "The status of the route entry.  {{enum}}";
            }
            leaf MemoryConstrained {
              type boolean;
              description
                "A flag indicating whether the device is a memory
                 constrained concentrator.";
            }
            leaf ManyToOne {
              type boolean;
              description
                "A flag indicating that the destination is a
                 concentrator that issued a many to-one request.";
            }
            leaf RouteRecordRequired {
              type boolean;
              description
                "A flag indicating that a route record command frame
                 should be sent to the destination prior to the
                 next data packet.";
            }
          }
        }

        list Binding {
          key "Alias";
          description
            "The {{object}} object describes the configuration
             capabilities related to maintaining a ZigBee
             Device's Binding Table as defined in
             {{bibref|ZigBee2007|section 2.2.8.2 Binding}}.";
          leaf Enable {
            type boolean;
            description
              "Enables or disables the use of this binding on the
               device.";
          }
          leaf SourceEndpoint {
            type uint32 {
              range "min..240";
            }
            description
              "Specifies the source endpoint used in this binding
               entry.";
          }
          leaf SourceAddress {
            type types:IEEE_EUI64;
            description
              "Specifies the source address used in this binding
               entry.";
          }
          leaf ClusterId {
            type uint32 {
              range "min..65535";
            }
            description
              "Specifies the cluster identifier used in this binding
               entry.";
          }
          leaf DestinationAddressMode {
            type enumeration {
              enum "Group";
              enum "Endpoint";
            }
            description
              "Specifies the type of destination address used for
               this binding entry.  {{enum}}";
          }
          leaf DestinationEndpoint {
            type uint32 {
              range "min..240";
            }
            description
              "Specifies the destination endpoint for the binding
               entry.  The value of this field is valid when the
               value of the {{param|DestinationAddressMode}} is
               {{enum|Endpoint|DestinationAddressMode}}.";
          }
          leaf IEEEDestinationAddress {
            type types:IEEE_EUI64;
            description
              "Specifies the IEEE destination address for this
               binding entry.  The value of this field is valid
               when the value of the
               {{param|DestinationAddressMode}} is
               {{enum|Endpoint|DestinationAddressMode}}.";
          }
          leaf GroupDestinationAddress {
            type types:ZigBeeNetworkAddress;
            description
              "Specifies the group destination address for this
               binding entry.  The value of this field is valid
               when the value of the
               {{param|DestinationAddressMode}} is
               {{enum|Group|DestinationAddressMode}}.";
          }
        }

        list Group {
          key "GroupId";
          description
            "The {{object}} object describes the configuration
             capabilities related to maintaining a ZigBee
             Device's Group Table as defined in
             {{bibref|ZigBee2007|section 2.5.2.7 Group Manager}}.";
          leaf Enable {
            type boolean;
            description
              "Enables or disables the use of this group on the
               device.";
          }
          leaf GroupId {
            type types:ZigBeeNetworkAddress;
            description
              "The Group Identifier for this object as defined in
               {{bibref|ZigBee2007|table 2.25 Group Table Entry
               Format}}.";
          }
          leaf EndpointList {
            type string {
              length "0..256";
            }
            description
              "The list of application endpoints assigned as a
               member of this {{object}} object.";
          }
        }

        list ApplicationEndpoint {
          key "EndpointId";
          description
            "The {{object}} object describes the application
             endpoint as defined in {{bibref|ZigBee2007|section
             2.1.2 Application Framework}}.";
          leaf Enable {
            type boolean;
            description
              "Enables or disables the use of this application
               endpoint on the device.";
          }
          leaf EndpointId {
            type uint32 {
              range "min..240";
            }
            description
              "The Endpoint Identifier for this object as defined in
               {{bibref|ZigBee2007|section 2.1.2 Application
               Framework}}.
            
               An {{object}} with an {{param}} value of 0 is
               designated as the device application: This is a
               special application that is responsible for device
               operation and contains logic to manage the
               device's networking and general maintenance
               features.";
          }

          container SimpleDescriptor {
            description
              "The {{object}} object contains the attributes of the
               Simple Descriptor of an application endpoint, as
               defined in {{bibref|ZigBee2007|section 2.3.2.5
               Simple Descriptor}}.";
            leaf ProfileId {
              type uint32 {
                range "min..65535";
              }
              description
                "Specifies the application profile that is supported
                 on this endpoint.  Application profiles are
                 agreements for messages, message formats,
                 andprocessing actions that enable developers to
                 create an interoperable, distributed application
                 employing application entities that reside on
                 separate ZigBee devices.  These application
                 profiles enable applications to send commands,
                 request data, and process commands and requests
                 as defined in {{bibref|ZigBee2007|section
                 2.1.2.1 Application Profiles}}.";
            }
            leaf DeviceId {
              type uint32 {
                range "min..65535";
              }
              config false;
              description
                "Application device identifier, as defined in
                 {{bibref|ZigBee2007|section 2.3.2.5.3
                 Application Device Identifier Field}}.";
            }
            leaf DeviceVersion {
              type uint32 {
                range "min..15";
              }
              config false;
              description
                "Application device version, as defined in
                 {{bibref|ZigBee2007|section 2.3.2.5.4
                 Application Device Version Field}}.";
            }
            leaf InputClusterList {
              type uint32 {
                range "min..65535";
              }
              description
                "{{list}} Specifies the input cluster identifiers to
                 be matched by the ZigBee coordinator by remote
                 Zigbee device's output cluster list for this
                 {{object}} object.";
            }
            leaf OutputClusterList {
              type uint32 {
                range "min..65535";
              }
              description
                "{{list}} Specifies the output cluster identifiers
                 to be matched by the ZigBee coordinator by
                 remote Zigbee device's input cluster list for
                 this {{object}} object.";
            }
          }
        }
      }

      container Discovery {
        description
          "This object is used for managing the discovery of ZigBee
           devices within a ZigBee Area Network.  ZigBee Devices
           are discovered via the {{object|#.ZDO}} instance
           associated with the ZigBee Coordinator of an Area
           Network.";

        list AreaNetwork {
          key "Coordinator";
          description
            "This object specifies the ZigBee devices that are
             discovered by the {{param|Coordinator}}.
          
             As the ZigBee specification does not provide a
             discovery protocol between the CWMP proxy and the
             ZigBee coordinator, the {{object}} object is
             provisioned and not discovered.";
          leaf Enable {
            type boolean;
            description
              "Enables or disables discovery of the ZigBee devices
               in this {{object}}.";
          }
          leaf LastUpdate {
            type yang:date-and-time;
            config false;
            description
              "The date and time when this {{object}} or its member
               devices (i.e., the devices with ZDOs listed in
               {{param|ZDOList}}) were updated due to a discovery
               operation.";
          }
          leaf Status {
            type enumeration {
              enum "Indeterminate";
              enum "InProgress";
              enum "Success";
              enum "Error";
              enum "Error_Timeout";
            }
            config false;
            description
              "The status of the current discovery operation.
            
               {{enum}}";
          }
          leaf Coordinator {
            type string {
              length "0..256";
            }
            description
              "The Fully Qualified Domain Name (FQDN) or IP address
               of the ZigBee Coordinator.  The coordinator MAY be
               located within the CPE.  In this scenario the ACS
               or CPE MAY use the value of \"localhost\".";
          }
          leaf ZDOReference {
            type string {
              length "0..256";
            }
            config false;
            description
              "The ZDO object for this device that is used to
               discover the ZigBee capabilities of attached
               devices.
            
               {{reference}}";
          }
          leaf ZDOList {
            type string {
              length "0..256";
            }
            config false;
            description
              "The list of ZDO objects discovered in this Area
               Network by the ZigBee Coordinator.
            
               {{reference}}";
          }
        }
      }
    }

    container Bridging {
      description
        "Layer 2 bridging configuration.  Specifies bridges between
         different layer 2 interfaces.  Bridges can be defined to
         include layer 2 filter criteria to selectively bridge
         traffic between interfaces.
      
         This object can be used to configure both 802.1D
         {{bibref|802.1D-2004}} and 802.1Q {{bibref|802.1Q-2011}}
         bridges.
      
         Not all 802.1D and 802.1Q features are modeled, and some
         additional features not present in either 802.1D or
         802.1Q are modeled.
      
         802.1Q {{bibref|802.1Q-2011}} bridges incorporate 802.1Q
         {{bibref|802.1Q-2005}} customer and 802.1ad
         {{bibref|802.1ad-2005}} provider bridges.";
      leaf MaxBridgeEntries {
        type uint32;
        config false;
        description
          "The maximum number of entries available in the
           {{object|.Bridging.Bridge}} table.";
      }
      leaf MaxDBridgeEntries {
        type uint32;
        config false;
        description
          "The maximum number of 802.1D {{bibref|802.1D-2004}}
           entries available in the {{object|.Bridging.Bridge}}
           table.  A positive value for this parameter implies
           support for 802.1D.
        
           There is no guarantee that this many 802.1D Bridges
           can be configured.  For example, the CPE might not be
           able simultaneously to support both 802.1D and 802.1Q
           Bridges.";
      }
      leaf MaxQBridgeEntries {
        type uint32;
        config false;
        description
          "The maximum number of 802.1Q {{bibref|802.1Q-2011}}
           entries available in the {{object|.Bridging.Bridge}}
           table.  A non-zero value for this parameter implies
           support for 802.1Q.
        
           There is no guarantee that this many 802.1Q Bridges
           can be configured.  For example, the CPE might not be
           able simultaneously to support both 802.1D and 802.1Q
           Bridges.";
      }
      leaf MaxVLANEntries {
        type uint32;
        config false;
        description
          "The maximum number of 802.1Q {{bibref|802.1Q-2011}} VLANs
           supported per {{object|.Bridging.Bridge}} table entry.";
      }
      leaf MaxProviderBridgeEntries {
        type uint32;
        config false;
        description
          "The maximum number of entries available in the
           {{object|.Bridging.ProviderBridge}} table.  A non-zero
           value for this parameter implies support for 802.1Q
           Provider Bridges.";
      }
      leaf MaxFilterEntries {
        type uint32;
        config false;
        description
          "The maximum number of entries available in the
           {{object|Filter}} table.";
      }

      list Bridge {
        key "Alias";
        description
          "Bridge table.";
        leaf Enable {
          type boolean;
          default "false";
          description
            "Enables or disables this {{object}}.";
        }
        leaf Status {
          type enumeration {
            enum "Disabled";
            enum "Enabled";
            enum "Error";
          }
          config false;
          default "Disabled";
          description
            "The status of this {{object}}.  {{enum}}
          
             The {{enum|Error}} value MAY be used by the CPE to
             indicate a locally defined error condition.";
        }
        leaf Standard {
          type enumeration {
            enum "802.1D-2004";
            enum "802.1Q-2005";
            enum "802.1Q-2011";
          }
          description
            "Selects the standard supported by this Bridge table
             entry.";
        }

        list Port {
          key "Alias";
          description
            "Bridge Port table, which MUST contain an entry for each
             bridge port (a stackable interface object as
             described in {{bibref|TR-181i2|Section 4.2}}).
          
             There are two types of bridge ports: management
             (upward facing) and non-management (downward
             facing).  This is determined by configuring the
             Boolean {{param|ManagementPort}} parameter.  The CPE
             will automatically configure each management bridge
             port to appear in the interface stack above all
             non-management bridge ports that share the same
             {{object|##.Bridge}} instance.";
          leaf Enable {
            type boolean;
            default "false";
            description
              "Enables or disables the bridge port.
            
               This parameter is based on ''ifAdminStatus'' from
               {{bibref|RFC2863}}.";
          }
          leaf Status {
            type enumeration {
              enum "Up";
              enum "Down";
              enum "Unknown";
              enum "Dormant";
              enum "NotPresent";
              enum "LowerLayerDown";
              enum "Error";
            }
            config false;
            default "Down";
            description
              "The current operational state of the bridge port (see
               {{bibref|TR-181i2|Section 4.2.2}}).  {{enum}}
            
               When {{param|Enable}} is {{false}} then this
               parameter SHOULD normally be {{enum|Down}} (or
               {{enum|NotPresent}} or {{enum|Error}} if there is
               a fault condition on the interface).
            
               When {{param|Enable}} is changed to {{true}} then
               this parameter SHOULD change to {{enum|Up}} if and
               only if the interface is able to transmit and
               receive network traffic; it SHOULD change to
               {{enum|Dormant}} if and only if the interface is
               operable but is waiting for external actions
               before it can transmit and receive network traffic
               (and subsequently change to {{enum|Up}} if still
               operable when the expected actions have
               completed); it SHOULD change to
               {{enum|LowerLayerDown}} if and only if the
               interface is prevented from entering the
               {{enum|Up}} state because one or more of the
               interfaces beneath it is down; it SHOULD remain in
               the {{enum|Error}} state if there is an error or
               other fault condition detected on the interface;
               it SHOULD remain in the {{enum|NotPresent}} state
               if the interface has missing (typically hardware)
               components; it SHOULD change to {{enum|Unknown}}
               if the state of the interface can not be
               determined for some reason.
            
               This parameter is based on ''ifOperStatus'' from
               {{bibref|RFC2863}}.";
          }
          leaf Name {
            type string {
              length "0..64";
            }
            config false;
            description
              "The textual name of the bridge port as assigned by
               the CPE.";
          }
          leaf LastChange {
            type uint32;
            config false;
            description
              "The accumulated time in {{units}} since the bridge
               port entered its current operational state.";
          }
          leaf LowerLayers {
            type string;
            default "";
            description
              "{{list}} {{reference|an interface object that is
               stacked immediately below this interface object}}
               See {{bibref|TR-181i2|Section 4.2.1}}.
            
               When {{param|ManagementPort}} is set to {{true}}
               the CPE MUST set {{param}} to reference all
               non-management bridge ports that are within the
               same {{object|##.Bridge}} instance (and update
               {{param}} when subsequent non-management bridge
               ports are added or deleted on that ''Bridge'').
               The ACS SHOULD NOT set {{param}} in this case.";
          }
          leaf ManagementPort {
            type boolean;
            default "false";
            description
              "If {{true}} then the entry is a management (upward
               facing) bridge port rather than a non-management
               (downward facing) bridge port.  For a given
               {{object|##.Bridge}} instance, each management
               bridge port appears in the interface stack above
               all non-management bridge ports.  The concept of
               Management Port is discussed in
               {{bibref|802.1Q-2005|chapter 8}}.";
          }
          leaf Type {
            type enumeration {
              enum "ProviderNetworkPort";
              enum "CustomerNetworkPort";
              enum "CustomerEdgePort";
              enum "CustomerVLANPort";
              enum "VLANUnawarePort";
            }
            description
              "The type of bridge port as defined in 802.1Q
               {{bibref|802.1Q-2011|Section 17
               IEEE8021BridgePortType}}.
            
               Enumeration of:
            
               {{enum}}";
          }
          leaf DefaultUserPriority {
            type uint32 {
              range "0..7";
            }
            description
              "Bridge Port Default User Priority.";
          }
          leaf PriorityRegeneration {
            type uint32 {
              range "0..7";
            }
            default "0,1,2,3,4,5,6,7";
            description
              "{{list}} List items represent user priority
               regeneration values for each ingress user priority
               on this Bridge Port.";
          }
          leaf PortState {
            type enumeration {
              enum "Disabled";
              enum "Blocking";
              enum "Listening";
              enum "Learning";
              enum "Forwarding";
              enum "Broken";
            }
            config false;
            default "Disabled";
            description
              "Bridge Port state as defined in 802.1D
               {{bibref|802.1D-2004}} and 802.1Q
               {{bibref|802.1Q-2011}}.";
          }
          leaf PVID {
            type int32 {
              range "1..4094";
            }
            default "1";
            description
              "PVID (or Port VID) is the VLAN ID with which an
               untagged or priority tagged frame that arrives on
               this port will be associated (i.e.  default Port
               VLAN ID as defined in 802.1Q
               {{bibref|802.1Q-2011}}).
            
               For an 802.1D Bridge {{bibref|802.1D-2004}}, this
               parameter MUST be ignored.";
          }
          leaf TPID {
            type uint32;
            default "33024";
            description
              "The Tag Protocol Identifier (TPID) assigned to this
               {{object}}.  The TPID is an EtherType value used
               to identify the frame as a tagged frame.
            
               Standard {{bibref|802.1Q-2011|Table 9.1}} TPID
               values are:
            
               *S-TAG 0x88A8 = 34984
            
               *C-TAG 0x8100 = 33024
            
               Non-Standard TPID values are:
            
               *S-TAG 0x9100 = 37120";
          }
          leaf AcceptableFrameTypes {
            type enumeration {
              enum "AdmitAll";
              enum "AdmitOnlyVLANTagged";
              enum "AdmitOnlyPrioUntagged";
            }
            default "AdmitAll";
            description
              "Indicates which types of frame arriving on this port
               will be admitted to the bridge (i.e.  Bridge Port
               acceptable frame types as defined in 802.1Q
               {{bibref|802.1Q-2011}}).  {{enum}}
            
               For an 802.1D {{bibref|802.1D-2004}} Bridge, the
               value of this parameter MUST be {{enum|AdmitAll}}.";
          }
          leaf IngressFiltering {
            type boolean;
            default "false";
            description
              "Enables or disables Ingress Filtering as defined in
               802.1Q {{bibref|802.1Q-2011}}.  If enabled
               ({{true}}), causes frames arriving on this port to
               be discarded if the port is not in the VLAN ID's
               member set (which is configured via the
               {{object|#.VLANPort}} table).
            
               For an 802.1D {{bibref|802.1D-2004}} Bridge, the
               value of this parameter MUST be {{false}}.";
          }
          leaf ServiceAccessPrioritySelection {
            type boolean;
            default "false";
            description
              "This parameter controls the Service Access Priority
               selection function as described in
               {{bibref|802.1Q-2011|section 6.13}}.
            
               The parameter is applicable to deployments of
               {{object|##.Bridge}} instances that are referenced
               by
               {{param|###.Bridging.ProviderBridge.{i}.SVLANComponent}}.";
          }
          leaf ServiceAccessPriorityTranslation {
            type uint32 {
              range "0..7";
            }
            default "0,1,2,3,4,5,6,7";
            description
              "{{list}} List items represent service access priority
               translation values for each ingress priority on
               this {{object}} as described in
               {{bibref|802.1Q-2011|section 6.13}}.
            
               The parameter is applicable to deployments of
               {{object|##.Bridge}} instances that are referenced
               by
               {{param|###.Bridging.ProviderBridge.{i}.SVLANComponent}}.";
          }
          leaf PriorityTagging {
            type boolean;
            default "false";
            description
              "Enables or disables priority tagging on this Bridge
               Port.
            
               When {{true}}, egress frames leaving this
               interface will be priority tagged with the frame's
               associated priority value, which will either be
               derived directly from the ingress frame or else
               set via
               {{param|.QoS.Classification.{i}.EthernetPriorityMark}}.
            
               When {{false}}, egress frames leaving this
               interface will be untagged.
            
               The parameter does not affect reception of ingress
               frames.
            
               Only applies on bridge ports that are untagged
               member of one or more VLAN's.";
          }

          container PriorityCodePoint {
            description
              "{{object}} provides the management control for the
               processing of the Priority Code Point (PCP) field
               for the 802.1Q header as defined in
               {{bibref|802.1Q-2011|section 6.9.3 Priority Code
               Point Encoding}}.
            
               The object is applicable to deployments of
               {{object|####.Bridging.ProviderBridge}} where the
               {{object|###.Bridge}} instance is referenced by
               {{param|####.Bridging.ProviderBridge.{i}.SVLANComponent}}
               or
               {{param|####.Bridging.ProviderBridge.{i}.CVLANComponents}}
               parameters.";
            leaf PCPSelection {
              type uint32 {
                range "1..4";
              }
              default "1";
              description
                "This parameter identifies the row in the
                 {{param|PCPEncoding}} and {{param|PCPDecoding}}
                 parameter lists.  The value of 1 points to the
                 8P0D row in the corresponding parameter lists.";
            }
            leaf UseDEI {
              type boolean;
              default "false";
              description
                "This parameter controls the processing of the
                 drop_eligible field and is described in
                 {{bibref|802.1Q-2011|section 6.9.3}}.";
            }
            leaf RequireDropEncoding {
              type boolean;
              default "false";
              description
                "This parameter controls the processing of the
                 encoding or decoding of the drop_eligible
                 component in the PCP field and is described in
                 {{bibref|802.1Q-2011|section 8.6.7}}.";
            }
            leaf PCPEncoding {
              type string {
                length "31";
                pattern "([0-7],){15}[0-7]";
              }
              description
                "This parameter provides the management control for
                 the processing of the encoding of the Priority
                 Code Point (PCP) field for the 802.1Q header as
                 defined in {{bibref|802.1Q-2011|section 6.9.3
                 Priority Code Point Encoding}} and
                 {{bibref|802.1Q-2011|Table 6-3}}.
              
                 The list is an ordered list that contains
                 entries for the following 4 PCP Values:
                 \"8P0D\",\"7P1D\", \"6P2D\" \"5P3D\".  Each list
                 entry matches the following pattern:
              
                 {{pattern}}
              
                 The value of this parameter MUST use square
                 brackets to protect comma separators within
                 nested lists.  For example, this corresponds to
                 Table 6-3 (mentioned above):
              
                 :
                 [7,7,6,6,5,5,4,4,3,3,2,2,1,1,0,0],[7,7,6,6,5,4,5,4,3,3,2,2,1,1,0,0],[7,7,6,6,5,4,5,4,3,2,3,2,1,1,0,0],[7,7,6,6,5,4,5,4,3,2,3,2,1,0,1,0]";
            }
            leaf PCPDecoding {
              type string {
                length "15";
                pattern "([0-7],[0-1],){7}[0-7],[0-1]";
              }
              description
                "This parameter provides the management control for
                 the processing of the decoding of the Priority
                 Code Point (PCP) field for the 802.1Q header as
                 defined in {{bibref|802.1Q-2011|section 6.9.3
                 Priority Code Point Encoding}} and
                 {{bibref|802.1Q-2011|Table 6-4}}.
              
                 The list is an ordered list that contains
                 entries for the following 4 PCP Values:
                 \"8P0D\",\"7P1D\", \"6P2D\" \"5P3D\".  Each list
                 entry matches the following pattern:
              
                 {{pattern}}
              
                 The value of this parameter MUST use square
                 brackets to protect comma separators within
                 nested lists.  For example, this corresponds to
                 Table 6-4 (mentioned above):
              
                 :
                 [7,0,6,0,5,0,4,0,3,0,2,0,1,0,0,0],[7,0,6,0,4,0,4,1,3,0,2,0,1,0,0,0],[7,0,6,0,4,0,4,1,2,0,2,1,1,0,0,0],[7,0,6,0,4,0,4,1,2,0,2,1,0,0,0,1]";
            }
          }

          container Stats {
            config false;
            description
              "Throughput statistics for this interface.
            
               The CPE MUST reset the interface's Stats
               parameters (unless otherwise stated in individual
               object or parameter descriptions) either when the
               interface becomes operationally down due to a
               previous administrative down (i.e.  the
               interface's {{param|#.Status}} parameter
               transitions to a down state after the interface is
               disabled) or when the interface becomes
               administratively up (i.e.  the interface's
               {{param|#.Enable}} parameter transitions from
               {{false}} to {{true}}).  Administrative and
               operational interface status is discussed in
               {{bibref|TR-181i2|section 4.2.2}}.";
            leaf BytesSent {
              type uint64;
              description
                "The total number of bytes transmitted out of the
                 interface, including framing characters.";
            }
            leaf BytesReceived {
              type uint64;
              description
                "The total number of bytes received on the
                 interface, including framing characters.";
            }
            leaf PacketsSent {
              type uint64;
              description
                "The total number of packets transmitted out of the
                 interface.";
            }
            leaf PacketsReceived {
              type uint64;
              description
                "The total number of packets received on the
                 interface.";
            }
            leaf ErrorsSent {
              type uint32;
              description
                "The total number of outbound packets that could not
                 be transmitted because of errors.";
            }
            leaf ErrorsReceived {
              type uint32;
              description
                "The total number of inbound packets that contained
                 errors preventing them from being delivered to a
                 higher-layer protocol.";
            }
            leaf UnicastPacketsSent {
              type uint64;
              description
                "The total number of packets requested for
                 transmission which were not addressed to a
                 multicast or broadcast address at this layer,
                 including those that were discarded or not sent.";
            }
            leaf UnicastPacketsReceived {
              type uint64;
              description
                "The total number of received packets, delivered by
                 this layer to a higher layer, which were not
                 addressed to a multicast or broadcast address at
                 this layer.";
            }
            leaf DiscardPacketsSent {
              type uint32;
              description
                "The total number of outbound packets which were
                 chosen to be discarded even though no errors had
                 been detected to prevent their being
                 transmitted.  One possible reason for discarding
                 such a packet could be to free up buffer space.";
            }
            leaf DiscardPacketsReceived {
              type uint32;
              description
                "The total number of inbound packets which were
                 chosen to be discarded even though no errors had
                 been detected to prevent their being delivered.
                 One possible reason for discarding such a packet
                 could be to free up buffer space.";
            }
            leaf MulticastPacketsSent {
              type uint64;
              description
                "The total number of packets that higher-level
                 protocols requested for transmission and which
                 were addressed to a multicast address at this
                 layer, including those that were discarded or
                 not sent.";
            }
            leaf MulticastPacketsReceived {
              type uint64;
              description
                "The total number of received packets, delivered by
                 this layer to a higher layer, which were
                 addressed to a multicast address at this layer.";
            }
            leaf BroadcastPacketsSent {
              type uint64;
              description
                "The total number of packets that higher-level
                 protocols requested for transmission and which
                 were addressed to a broadcast address at this
                 layer, including those that were discarded or
                 not sent.";
            }
            leaf BroadcastPacketsReceived {
              type uint64;
              description
                "The total number of received packets, delivered by
                 this layer to a higher layer, which were
                 addressed to a broadcast address at this layer.";
            }
            leaf UnknownProtoPacketsReceived {
              type uint32;
              description
                "The total number of packets received via the
                 interface which were discarded because of an
                 unknown or unsupported protocol.";
            }
          }
        }

        list VLAN {
          key "VLANID";
          description
            "Bridge VLAN table.  If this table is supported, if MUST
             contain an entry for each VLAN known to the Bridge.
          
             This table only applies to an 802.1Q
             {{bibref|802.1Q-2011}} Bridge.";
          leaf Enable {
            type boolean;
            default "false";
            description
              "Enables or disables this VLAN table entry.";
          }
          leaf Name {
            type string {
              length "0..64";
            }
            default "";
            description
              "Human-readable name for this VLAN table entry.";
          }
          leaf VLANID {
            type int32 {
              range "1..4094";
            }
            description
              "VLAN ID of the entry.";
          }
        }

        list VLANPort {
          key "VLAN Port";
          description
            "Bridge VLAN egress port and untagged port membership
             table.
          
             This table only applies to an 802.1Q
             {{bibref|802.1Q-2011}} Bridge.
          
             Note: The {{object}} table includes unique key
             parameters that are strong references.  If a
             strongly referenced object is deleted, the CPE will
             set the referencing parameter to {{empty}}.
             However, doing so under these circumstances might
             cause the updated {{object}} row to then violate the
             table's unique key constraint; if this occurs, the
             CPE MUST disable the offending {{object}} row.";
          leaf Enable {
            type boolean;
            default "false";
            description
              "Enables or disables this {{object}} entry.";
          }
          leaf VLAN {
            type string {
              length "0..256";
            }
            default "";
            description
              "{{reference}} Specifies the VLAN for which port
               membership is expressed.";
          }
          leaf Port {
            type string {
              length "0..256";
            }
            default "";
            description
              "{{reference}} Specifies the bridge port that is
               member of the VLAN.";
          }
          leaf Untagged {
            type boolean;
            description
              "Enables or disables untagged port membership to the
               VLAN and determines whether egress frames for this
               VLAN are sent untagged or tagged.";
          }
        }
      }

      list Filter {
        key "Alias";
        description
          "Filter table containing classification filter entries,
           each of which expresses a set of classification
           criterion to classify ingress frames as member of a
           {{object|#.Bridge}} instance or a
           {{object|#.Bridge.{i}.VLAN}} instance.
        
           Bridge VLAN classification only applies for 802.1Q
           {{bibref|802.1Q-2011}} Bridges.
        
           For enabled table entries, if {{param|Bridge}} or
           {{param|Interface}} is {{empty}} then the table entry
           is inoperable and the CPE MUST set {{param|Status}} to
           {{enum|Error_Misconfigured|Status}}.
        
           Several of this object's parameters specify DHCP
           option values.  Some cases are version neutral (the
           parameter can apply to both DHCPv4 and DHCPv6), but in
           other cases the representation of the option is
           different for DHCPv4 and DHCPv6, so it is necessary to
           define separate DHCPv4-specific and DHCPv6-specific
           parameters.  Therefore, an instance of this object
           that uses DHCP option values as filter criteria will
           be associated with either DHCPv4 or DHCPv6, as
           indicated by the {{param|DHCPType}} parameter.";
        leaf Enable {
          type boolean;
          default "false";
          description
            "Enables or disables this Filter table entry.";
        }
        leaf Status {
          type enumeration {
            enum "Disabled";
            enum "Enabled";
            enum "Error_Misconfigured";
            enum "Error";
          }
          config false;
          default "Disabled";
          description
            "The status of this Filter table entry.  {{enum}}
          
             The {{enum|Error_Misconfigured}} value indicates
             that a necessary configuration value is undefined or
             invalid.
          
             The {{enum|Error}} value MAY be used by the CPE to
             indicate a locally defined error condition.
          
             If the Bridge Port table is supported, but none of
             its entries correspond to {{param|Interface}}, or if
             such an entry exists but is disabled, {{param}} MUST
             NOT indicate {{enum|Enabled}}.
          
             If the Bridge VLAN table is supported, but none of
             its entries correspond to {{param|VLANIDFilter}}, or
             if such an entry exists but is disabled, {{param}}
             MUST NOT indicate {{enum|Enabled}}.";
        }
        leaf Bridge {
          type string {
            length "0..256";
          }
          default "";
          description
            "{{reference|a {{object|.Bridging.Bridge}} object in
             case of a 802.1D bridge or a
             {{object|.Bridging.Bridge.{i}.VLAN}} object in case
             of a 802.1Q bridge}} Note: either way, this
             identifies the bridge (because each bridge has a
             VLAN table).
          
             Defines the Bridge or Bridge VLAN to which ingress
             frames will be classified based upon matches of the
             classification criteria.";
        }
        leaf Order {
          type uint32 {
            range "1..max";
          }
          description
            "Position of the {{object}} entry in the order of
             precedence.  A value of ''1'' indicates the first
             entry considered (highest precedence).  For each
             ingress frame on the {{param|Interface}}, the
             highest ordered entry that matches the filter
             criteria is applied.  All lower order entries are
             ignored.
          
             When this value is modified, if the value matches
             that of an existing entry, the {{param}} value for
             the existing entry and all lower {{param}} entries
             is incremented (lowered in precedence) to ensure
             uniqueness of this value.  A deletion causes
             {{param}} values to be compacted.  When a value is
             changed, incrementing occurs before compaction.
          
             The value of {{param}} on creation of a {{object}}
             table entry MUST be one greater than the largest
             current value (initially assigned the lowest
             precedence).";
        }
        leaf Interface {
          type string {
            length "0..256";
          }
          default "";
          description
            "{{reference}} This MUST relate to the same bridge as
             does {{param|Bridge}}.
          
             Defines the Bridge Port on which ingress frame
             classification will occur.";
        }
        leaf DHCPType {
          type enumeration {
            enum "DHCPv4";
            enum "DHCPv6";
          }
          default "DHCPv4";
          description
            "The DHCP protocol associated with the {{object}}
             instance.  Affects only parameters that specify DHCP
             option values as filter criteria (all such parameter
             descriptions note this fact).  {{enum}}
          
             If {{param}} is {{enum|DHCPv4}}, then {{object}}
             parameters that are DHCPv6-specific are ignored.  If
             {{param}} is {{enum|DHCPv6}}, then {{object}}
             parameters that are DHCPv4-specific are ignored.";
        }
        leaf VLANIDFilter {
          type uint32 {
            range "0..4094";
          }
          default "0";
          description
            "Classification criterion.
          
             The 802.1Q {{bibref|802.1Q-2011}} VLAN ID.
          
             For an 802.1D {{bibref|802.1D-2004}} Bridge, which
             has no concept of VLANs, the VLAN ID MUST be ''0''.";
        }
        leaf EthertypeFilterList {
          type uint32;
          default "";
          description
            "Classification criterion.
          
             {{list}} Each list item represents an Ethertype
             value.
          
             Note that neither 802.1D {{bibref|802.1D-2004}} nor
             802.1Q {{bibref|802.1Q-2011}} support classification
             based on Ethertype.";
        }
        leaf EthertypeFilterExclude {
          type boolean;
          default "true";
          description
            "If {{false}}, on ingress to the interfaces associated
             with this Filter, the Bridge is defined to admit
             only those packets that match one of the
             {{param|EthertypeFilterList}} entries (in either the
             Ethernet or SNAP Type header).  If the
             {{param|EthertypeFilterList}} is empty, no packets
             are admitted.
          
             If {{true}}, on ingress to the interfaces associated
             with this Filter, the Bridge is defined to admit all
             packets except those packets that match one of the
             {{param|EthertypeFilterList}} entries (in either the
             Ethernet or SNAP Type header).  If the
             {{param|EthertypeFilterList}} is empty, packets are
             admitted regardless of Ethertype.
          
             Note that neither 802.1D {{bibref|802.1D-2004}} nor
             802.1Q {{bibref|802.1Q-2011}} support classification
             based on Ethertype.";
        }
        leaf SourceMACAddressFilterList {
          type string;
          default "";
          description
            "Classification criterion.
          
             {{list|each representing a MAC Address}}
          
             Each list entry MAY optionally specify a bit-mask,
             where matching of a packet's MAC address is only to
             be done for bit positions set to one in the mask.
             If no mask is specified, all bits of the MAC Address
             are to be used for matching.
          
             For example, the list might be: ''01:02:03:04:05:06,
             1:22:33:00:00:00/FF:FF:FF:00:00:00,
             88:77:66:55:44:33''
          
             Note that neither 802.1D {{bibref|802.1D-2004}} nor
             802.1Q {{bibref|802.1Q-2011}} support classification
             based on source MAC address.";
        }
        leaf SourceMACAddressFilterExclude {
          type boolean;
          default "true";
          description
            "If {{false}}, on ingress to the interfaces associated
             with this Filter, the Bridge admits only those
             packets whose source MAC Address matches one of the
             {{param|SourceMACAddressFilterList}} entries.  If
             the {{param|SourceMACAddressFilterList}} is empty,
             no packets are admitted.
          
             If {{true}}, on ingress to the interfaces associated
             with this Filter, the Bridge admits all packets
             except those packets whose source MAC Address
             matches one of the
             {{param|SourceMACAddressFilterList}} entries.  If
             the {{param|SourceMACAddressFilterList}} is empty,
             packets are admitted regardless of MAC address.
          
             Note that neither 802.1D {{bibref|802.1D-2004}} nor
             802.1Q {{bibref|802.1Q-2011}} support classification
             based on source MAC address.";
        }
        leaf DestMACAddressFilterList {
          type string;
          default "";
          description
            "Classification criterion.
          
             {{list}} Each list item specifies a MAC Address.
             List items MAY optionally specify a bit-mask after
             the MAC Address, where matching of a packet's MAC
             address is only to be done for bit positions set to
             one in the mask.  If no mask is specified, all bits
             of the MAC Address are to be used for matching.
          
             For example, the list might be: ''01:02:03:04:05:06,
             1:22:33:00:00:00/FF:FF:FF:00:00:00,
             88:77:66:55:44:33''";
        }
        leaf DestMACAddressFilterExclude {
          type boolean;
          default "true";
          description
            "If {{false}}, on ingress to the interfaces associated
             with this Filter, the Bridge admits only those
             packets whose destination MAC Address matches one of
             the {{param|DestMACAddressFilterList}} entries.  If
             the {{param|DestMACAddressFilterList}} is empty, no
             packets are admitted.
          
             If {{true}}, on ingress to the interfaces associated
             with this Filter, the Bridge admits all packets
             except those packets whose destination MAC Address
             matches one of the
             {{param|DestMACAddressFilterList}} entries.  If the
             {{param|DestMACAddressFilterList}} is empty, packets
             are admitted regardless of MAC address.";
        }
        leaf SourceMACFromVendorClassIDFilter {
          type string {
            length "0..255";
          }
          default "";
          description
            "Classification criterion.
          
             A string used to identify one or more devices via
             DHCP for which MAC address filtering would
             subsequently apply.  A device is considered matching
             if its DHCPv4 Vendor Class Identifier (Option 60 as
             defined in {{bibref|RFC2132}}) in the most recent
             DHCP lease acquisition or renewal matches the
             specified value according to the match criterion in
             {{param|SourceMACFromVendorClassIDMode}}.  Case
             sensitive.
          
             This is a normal string, e.g.  \"abc\" is
             represented as \"abc\" and not \"616263\" hex.
             However, if the value includes non-printing
             characters then such characters have to be
             represented using XML escapes, e.g.  #x0a for
             line-feed.
          
             Note that neither 802.1D {{bibref|802.1D-2004}} nor
             802.1Q {{bibref|802.1Q-2011}} support classification
             based on source MAC address.
          
             Note: This parameter is DHCPv4-specific.  It only
             applies when {{param|DHCPType}} is
             {{enum|DHCPv4|DHCPType}}.";
        }
        leaf SourceMACFromVendorClassIDFilterv6 {
          type yang:hex-string {
            length "0..65535";
          }
          default "";
          description
            "Classification criterion.
          
             A hexbinary string used to identify one or more
             devices via DHCP for which MAC address filtering
             would subsequently apply.  A device is considered
             matching if the most recent DHCPv6 Vendor Class
             Identifier (Option 16 as defined in
             {{bibref|RFC3315}}) was equal to the specified
             value.  The option value is binary, so an exact
             match is REQUIRED.
          
             Note that neither 802.1D {{bibref|802.1D-2004}} nor
             802.1Q {{bibref|802.1Q-2011}} support classification
             based on source MAC address.
          
             Note: This parameter is DHCPv6-specific.  It only
             applies when {{param|DHCPType}} is
             {{enum|DHCPv6|DHCPType}}.";
        }
        leaf SourceMACFromVendorClassIDFilterExclude {
          type boolean;
          default "true";
          description
            "If {{false}}, on ingress to the interfaces associated
             with this Filter, the Bridge admits only those
             packets whose source MAC Address matches that of a
             LAN device previously identified as described in
             {{param|SourceMACFromVendorClassIDFilter}} (for
             {{enum|DHCPv4|DHCPType}}) or
             {{param|SourceMACFromVendorClassIDFilterv6}} (for
             {{enum|DHCPv6|DHCPType}}).  If this corresponding
             filter parameter is {{empty}}, no packets are
             admitted.
          
             If {{true}}, on ingress to the interfaces associated
             with this Filter, the Bridge admits all packets
             except those packets whose source MAC Address
             matches that of a LAN device previously identified
             as described in
             {{param|SourceMACFromVendorClassIDFilter}} (for
             {{enum|DHCPv4|DHCPType}}) or
             {{param|SourceMACFromVendorClassIDFilterv6}} (for
             {{enum|DHCPv6|DHCPType}}).  If this corresponding
             filter parameter is {{empty}}, packets are admitted
             regardless of MAC address.
          
             Note that neither 802.1D {{bibref|802.1D-2004}} nor
             802.1Q {{bibref|802.1Q-2011}} support classification
             based on source MAC address";
        }
        leaf SourceMACFromVendorClassIDMode {
          type enumeration {
            enum "Exact";
            enum "Prefix";
            enum "Suffix";
            enum "Substring";
          }
          default "Exact";
          description
            "{{param|SourceMACFromVendorClassIDFilter}} pattern
             match criterion.  {{enum}}
          
             For example, if
             {{param|SourceMACFromVendorClassIDFilter}} is
             \"Example\" then an Option 60 value of \"Example
             device\" will match with this parameter values of
             {{enum|Prefix}} or {{enum|Substring}}, but not with
             {{enum|Exact}} or {{enum|Suffix}}.
          
             Note that neither 802.1D {{bibref|802.1D-2004}} nor
             802.1Q {{bibref|802.1Q-2011}} support classification
             based on source MAC address.";
        }
        leaf DestMACFromVendorClassIDFilter {
          type string {
            length "0..255";
          }
          default "";
          description
            "Classification criterion.
          
             A string used to identify one or more devices via
             DHCP for which MAC address filtering would
             subsequently apply.  A device is considered matching
             if its DHCPv4 Vendor Class Identifier (Option 60 as
             defined in {{bibref|RFC2132}}) in the most recent
             DHCP lease acquisition or renewal matches the
             specified value according to the match criterion in
             {{param|DestMACFromVendorClassIDMode}}.  Case
             sensitive.
          
             This is a normal string, e.g.  \"abc\" is
             represented as \"abc\" and not say \"616263\" hex.
             However, if the value includes non-printing
             characters then such characters have to be
             represented using XML escapes, e.g.  #x0a for
             line-feed.
          
             Note: This parameter is DHCPv4-specific.  It only
             applies when {{param|DHCPType}} is
             {{enum|DHCPv4|DHCPType}}.";
        }
        leaf DestMACFromVendorClassIDFilterv6 {
          type yang:hex-string {
            length "0..65535";
          }
          default "";
          description
            "Classification criterion.
          
             A hexbinary string used to identify one or more
             devices via DHCP for which MAC address filtering
             would subsequently apply.  A device is considered
             matching if the most recent DHCPv6 Vendor Class
             Identifier (Option 16 as defined in
             {{bibref|RFC3315}}) was equal to the specified
             value.  The option value is binary, so an exact
             match is REQUIRED.
          
             Note: This parameter is DHCPv6-specific.  It only
             applies when {{param|DHCPType}} is
             {{enum|DHCPv6|DHCPType}}.";
        }
        leaf DestMACFromVendorClassIDFilterExclude {
          type boolean;
          default "true";
          description
            "If {{false}}, on ingress to the interfaces associated
             with this Filter, the Bridge admits only those
             packets whose destination MAC Address matches that
             of a LAN device previously identified as described
             in {{param|DestMACFromVendorClassIDFilter}} (for
             {{enum|DHCPv4|DHCPType}}) or
             {{param|DestMACFromVendorClassIDFilterv6}} (for
             {{enum|DHCPv6|DHCPType}}).  If this corresponding
             filter parameter is {{empty}}, no packets are
             admitted.
          
             If {{true}}, on ingress to the interfaces associated
             with this Filter, the Bridge admits all packets
             except those packets whose destination MAC Address
             matches that of a LAN device previously identified
             as described in
             {{param|DestMACFromVendorClassIDFilter}} (for
             {{enum|DHCPv4|DHCPType}}) or
             {{param|DestMACFromVendorClassIDFilterv6}} (for
             {{enum|DHCPv6|DHCPType}}).  If this corresponding
             filter parameter is {{empty}}, packets are admitted
             regardless of MAC address.";
        }
        leaf DestMACFromVendorClassIDMode {
          type enumeration {
            enum "Exact";
            enum "Prefix";
            enum "Suffix";
            enum "Substring";
          }
          default "Exact";
          description
            "{{param|DestMACFromVendorClassIDFilter}} pattern match
             criterion.  {{enum}}
          
             For example, if
             {{param|DestMACFromVendorClassIDFilter}} is
             ''Example'' then an Option 60 value of \"Example
             device\" will match with {{param}} values of
             {{enum|Prefix}} or {{enum|Substring}}, but not with
             {{enum|Exact}} or {{enum|Suffix}}.";
        }
        leaf SourceMACFromClientIDFilter {
          type yang:hex-string {
            length "0..65535";
          }
          default "";
          description
            "Classification criterion.
          
             A hexbinary string used to identify one or more
             devices via DHCP for which MAC address filtering
             would subsequently apply.  A device is considered
             matching if the most recent DHCP Client Identifier
             (via DHCP lease acquisition or renewal for DHCPv4)
             was equal to the specified value.  The DHCP Client
             Identifier is Option 61 (as defined in
             {{bibref|RFC2132}}) for {{enum|DHCPv4|DHCPType}}, or
             is Option 1 (as defined in {{bibref|RFC3315}}) for
             {{enum|DHCPv6|DHCPType}}.  The option value is
             binary, so an exact match is REQUIRED.
          
             Note that neither 802.1D {{bibref|802.1D-2004}} nor
             802.1Q {{bibref|802.1Q-2011}} support classification
             based on source MAC address.
          
             Note: DHCPv4 Option values are limited to a length
             of 255, while DHCPv6 Option values can have a
             maximum length of 65535.
          
             Note: This parameter is DHCP version neutral.  The
             specific DHCP version in use with this parameter is
             indicated by {{param|DHCPType}}.
          
             Note: DHCPv6 Option 1 (Client Identifier) is
             sometimes referred to as ''DUID''.";
        }
        leaf SourceMACFromClientIDFilterExclude {
          type boolean;
          default "true";
          description
            "If {{false}}, on ingress to the interfaces associated
             with this Filter, the Bridge admits only those
             packets whose source MAC Address matches that of a
             LAN device previously identified as described in
             {{param|SourceMACFromClientIDFilter}}.  If
             {{param|SourceMACFromClientIDFilter}} is {{empty}},
             no packets are admitted.
          
             If {{true}}, on ingress to the interfaces associated
             with this Filter, the Bridge admits all packets
             except those packets whose source MAC Address
             matches that of a LAN device previously identified
             as described in
             {{param|SourceMACFromClientIDFilter}}.  If the
             {{param|SourceMACFromClientIDFilter}} is {{empty}},
             packets are admitted regardless of MAC address.
          
             Note that neither 802.1D {{bibref|802.1D-2004}} nor
             802.1Q {{bibref|802.1Q-2011}} support classification
             based on source MAC address.";
        }
        leaf DestMACFromClientIDFilter {
          type yang:hex-string {
            length "0..65535";
          }
          default "";
          description
            "Classification criterion.
          
             A hexbinary string used to identify one or more
             devices via DHCP for which MAC address filtering
             would subsequently apply.  A device is considered
             matching if the most recent DHCP Client Identifier
             (via DHCP lease acquisition or renewal for DHCPv4)
             was equal to the specified value.  The DHCP Client
             Identifier is Option 61 (as defined in
             {{bibref|RFC2132}}) for {{enum|DHCPv4|DHCPType}}, or
             is Option 1 (as defined in {{bibref|RFC3315}}) for
             {{enum|DHCPv6|DHCPType}}.  The option value is
             binary, so an exact match is REQUIRED.
          
             Note: DHCPv4 Option values are limited to a length
             of 255, while DHCPv6 Option values can have a
             maximum length of 65535.
          
             Note: This parameter is DHCP version neutral.  The
             specific DHCP version in use with this parameter is
             indicated by {{param|DHCPType}}.
          
             Note: DHCPv6 Option 1 (Client Identifier) is
             sometimes referred to as ''DUID''.";
        }
        leaf DestMACFromClientIDFilterExclude {
          type boolean;
          default "true";
          description
            "If {{false}}, on ingress to the interfaces associated
             with this Filter, the Bridge admits only those
             packets whose destination MAC Address matches that
             of a LAN device previously identified as described
             in {{param|DestMACFromClientIDFilter}}.  If
             {{param|DestMACFromClientIDFilter}} is {{empty}}, no
             packets are admitted.
          
             If {{true}}, on ingress to the interfaces associated
             with this Filter, the Bridge admits all packets
             except those packets whose destination MAC Address
             matches that of a LAN device previously identified
             as described in {{param|DestMACFromClientIDFilter}}.
             If the {{param|DestMACFromClientIDFilter}} is
             {{empty}}, packets are admitted regardless of MAC
             address.";
        }
        leaf SourceMACFromUserClassIDFilter {
          type yang:hex-string {
            length "0..65535";
          }
          default "";
          description
            "Classification criterion.
          
             A hexbinary string used to identify one or more
             devices via DHCP for which MAC address filtering
             would subsequently apply.  A device is considered
             matching if the most recent DHCP User Class
             Identifier (via DHCP lease acquisition or renewal
             for DHCPv4) was equal to the specified value.  The
             DHCP User Class Identifier is Option 77 (as defined
             in {{bibref|RFC3004}}) for {{enum|DHCPv4|DHCPType}},
             or is Option 15 (as defined in {{bibref|RFC3315}})
             for {{enum|DHCPv6|DHCPType}}.  The option value is
             binary, so an exact match is REQUIRED.
          
             Note that neither 802.1D {{bibref|802.1D-2004}} nor
             802.1Q {{bibref|802.1Q-2011}} support classification
             based on source MAC address.
          
             Note: DHCPv4 Option values are limited to a length
             of 255, while DHCPv6 Option values can have a
             maximum length of 65535.
          
             Note: This parameter is DHCP version neutral.  The
             specific DHCP version in use with this parameter is
             indicated by {{param|DHCPType}}.";
        }
        leaf SourceMACFromUserClassIDFilterExclude {
          type boolean;
          default "true";
          description
            "If {{false}}, on ingress to the interfaces associated
             with this Filter, the Bridge admits only those
             packets whose source MAC Address matches that of a
             LAN device previously identified as described in
             {{param|SourceMACFromUserClassIDFilter}}.  If
             {{param|SourceMACFromUserClassIDFilter}} is
             {{empty}}, no packets are admitted.
          
             If {{true}}, on ingress to the interfaces associated
             with this Filter, the Bridge admits all packets
             except those packets whose source MAC Address
             matches that of a LAN device previously identified
             as described in
             {{param|SourceMACFromUserClassIDFilter}}.  If the
             {{param|SourceMACFromUserClassIDFilter}} is
             {{empty}}, packets are admitted regardless of MAC
             address.
          
             Note that neither 802.1D {{bibref|802.1D-2004}} nor
             802.1Q {{bibref|802.1Q-2011}} support classification
             based on source MAC address.";
        }
        leaf DestMACFromUserClassIDFilter {
          type yang:hex-string {
            length "0..65535";
          }
          default "";
          description
            "Classification criterion.
          
             A hexbinary string used to identify one or more
             devices via DHCP for which MAC address filtering
             would subsequently apply.  A device is considered
             matching if the most recent DHCP User Class
             Identifier (via DHCP lease acquisition or renewal
             for DHCPv4) was equal to the specified value.  The
             DHCP User Class Identifier is Option 77 (as defined
             in {{bibref|RFC3004}}) for {{enum|DHCPv4|DHCPType}},
             or is Option 15 (as defined in {{bibref|RFC3315}})
             for {{enum|DHCPv6|DHCPType}}.  The option value is
             binary, so an exact match is REQUIRED.
          
             Note: DHCPv4 Option values are limited to a length
             of 255, while DHCPv6 Option values can have a
             maximum length of 65535.
          
             Note: This parameter is DHCP version neutral.  The
             specific DHCP version in use with this parameter is
             indicated by {{param|DHCPType}}.";
        }
        leaf DestMACFromUserClassIDFilterExclude {
          type boolean;
          default "true";
          description
            "If {{false}}, on ingress to the interfaces associated
             with this Filter, the Bridge admits only those
             packets whose destination MAC Address matches that
             of a LAN device previously identified as described
             in {{param|DestMACFromUserClassIDFilter}}.  If
             {{param|DestMACFromUserClassIDFilter}} is {{empty}},
             no packets are admitted.
          
             If {{true}}, on ingress to the interfaces associated
             with this Filter, the Bridge admits all packets
             except those packets whose destination MAC Address
             matches that of a LAN device previously identified
             as described in
             {{param|DestMACFromUserClassIDFilter}}.  If the
             {{param|DestMACFromUserClassIDFilter}} is {{empty}},
             packets are admitted regardless of MAC address.";
        }
        leaf DestIP {
          type types:IPAddress;
          default "";
          description
            "Classification criterion.
          
             Destination IP address.  {{empty}} indicates this
             criterion is not used for classification.";
        }
        leaf DestMask {
          type types:IPPrefix;
          default "";
          description
            "Destination IP address mask, represented as an IP
             routing prefix using CIDR notation [RFC4632].  The
             IP address part MUST be {{empty}} (and, if
             specified, MUST be ignored).";
        }
        leaf DestIPExclude {
          type boolean;
          default "false";
          description
            "If {{false}}, the class includes only those packets
             that match the (masked) DestIP entry, if specified.
          
             If {{true}}, the class includes all packets except
             those that match the (masked) DestIP entry, if
             specified.";
        }
        leaf SourceIP {
          type types:IPAddress;
          default "";
          description
            "Classification criterion.
          
             Source IP address.  {{empty}} indicates this
             criterion is not used for classification.";
        }
        leaf SourceMask {
          type types:IPPrefix;
          default "";
          description
            "Source IP address mask, represented as an IP routing
             prefix using CIDR notation [RFC4632].  The IP
             address part MUST be an empty string (and, if
             specified, MUST be ignored).";
        }
        leaf SourceIPExclude {
          type boolean;
          default "false";
          description
            "If {{false}}, the class includes only those packets
             that match the (masked) {{param|SourceIP}} entry, if
             specified.
          
             If {{true}}, the class includes all packets except
             those that match the (masked) {{param|SourceIP}}
             entry, if specified.";
        }
        leaf Protocol {
          type int32 {
            range "-1..255";
          }
          default "-1";
          description
            "Classification criterion.
          
             Protocol number.  A value of -1 indicates this
             criterion is not used for classification.";
        }
        leaf ProtocolExclude {
          type boolean;
          default "false";
          description
            "If {{false}}, the class includes only those packets
             that match the {{param|Protocol}} entry, if
             specified.
          
             If {{true}}, the class includes all packets except
             those that match the {{param|Protocol}} entry, if
             specified.";
        }
        leaf DestPort {
          type int32 {
            range "-1..65535";
          }
          default "-1";
          description
            "Classification criterion.
          
             Destination port number.  A value of -1 indicates
             this criterion is not used for classification.";
        }
        leaf DestPortRangeMax {
          type int32 {
            range "-1..65535";
          }
          default "-1";
          description
            "Classification criterion.
          
             If specified, indicates the classification criterion
             is to include the port range from {{param|DestPort}}
             through {{param}} (inclusive).  If specified,
             {{param}} MUST be greater than or equal to
             {{param|DestPort}}.
          
             A value of -1 indicates that no port range is
             specified.";
        }
        leaf DestPortExclude {
          type boolean;
          default "false";
          description
            "If {{false}}, the class includes only those packets
             that match the {{param|DestPort}} entry (or port
             range), if specified.
          
             If {{true}}, the class includes all packets except
             those that match the {{param|DestPort}} entry (or
             port range), if specified.";
        }
        leaf SourcePort {
          type int32 {
            range "-1..65535";
          }
          default "-1";
          description
            "Classification criterion.
          
             Source port number.  A value of -1 indicates this
             criterion is not used for classification.";
        }
        leaf SourcePortRangeMax {
          type int32 {
            range "-1..65535";
          }
          default "-1";
          description
            "Classification criterion.
          
             If specified, indicates the classification criterion
             is to include the port range from
             {{param|SourcePort}} through {{param}} (inclusive).
             If specified, {{param}} MUST be greater than or
             equal to SourcePort.
          
             A value of -1 indicates that no port range is
             specified.";
        }
        leaf SourcePortExclude {
          type boolean;
          default "false";
          description
            "If {{false}}, the class includes only those packets
             that match the {{param|SourcePort}} entry (or port
             range), if specified.
          
             If {{true}}, the class includes all packets except
             those that match the {{param|SourcePort}} entry (or
             port range), if specified.";
        }
      }

      list ProviderBridge {
        key "Alias";
        description
          "Provider Bridge table.
        
           A Provider Bridge is described in
           {{bibref|802.1Q-2011|section 5.10 Provider Bridge
           conformance}} as an entity that is comprised of one
           S-VLAN component and zero or more C-VLAN components.
           S-VLAN and C-VLAN components are modelled as instances
           of {{object|#.Bridge}} objects.
        
           When {{param|Type}} is configured with value of
           {{enum|PE|Type}} VLAN tags from the S-VLAN component
           (outer of 2 VLAN tags) are stacked on top of the VLAN
           tag from the C-VLAN component (inner of 2 VLAN tags).
        
           When {{param|Type}} is configured with value of
           {{enum|S-VLAN|Type}} only VLAN tags from the S-VLAN
           component are utilized.";
        leaf Enable {
          type boolean;
          default "false";
          description
            "Enables or disables this {{object}}.";
        }
        leaf Status {
          type enumeration {
            enum "Disabled";
            enum "Enabled";
            enum "Error_Misconfigured";
            enum "Error";
          }
          config false;
          default "Disabled";
          description
            "The status of this {{object}}.  {{enum}}
          
             The {{enum|Error_Misconfigured}} value indicates
             that a necessary configuration value is undefined or
             invalid.  For example when the {{param|Type}} is
             configured with value of {{enum|PE|Type}} but
             {{param|CVLANComponents}} is {{empty}}.
          
             The {{enum|Error}} value MAY be used by the CPE to
             indicate a locally defined error condition.";
        }
        leaf Type {
          type enumeration {
            enum "S-VLAN";
            enum "PE";
          }
          description
            "Selects the standard supported by this {{object}} table
             entry.";
        }
        leaf SVLANComponent {
          type string {
            length "0..256";
          }
          default "";
          description
            "{{reference|a {{object|#.Bridge}} instance that
             specifies the S-VLAN component for the {{object}}}}";
        }
        leaf CVLANComponents {
          type string {
            length "0..256";
          }
          default "";
          description
            "{{list}} {{reference|a {{object|#.Bridge}} instance
             that specifies a C-VLAN component for the
             {{object}}}}";
        }
      }
    }

    container PPP {
      description
        "Point-to-Point Protocol {{bibref|RFC1661}}.  This object
         contains the {{object|Interface}} table.";
      leaf SupportedNCPs {
        type enumeration {
          enum "ATCP";
          enum "IPCP";
          enum "IPXCP";
          enum "NBFCP";
          enum "IPv6CP";
        }
        config false;
        description
          "The Network Control Protocols (NCPs) that are supported
           by the device.  {{enum}}
        
           Note that {{enum|IPv6CP}} is an IPv6 capability.";
      }

      list Interface {
        key "Alias";
        description
          "PPP interface table (a stackable interface object as
           described in {{bibref|TR-181i2|Section 4.2}}).";
        leaf Enable {
          type boolean;
          default "false";
          description
            "Enables or disables the interface.
          
             This parameter is based on ''ifAdminStatus'' from
             {{bibref|RFC2863}}.";
        }
        leaf Status {
          type enumeration {
            enum "Up";
            enum "Down";
            enum "Unknown";
            enum "Dormant";
            enum "NotPresent";
            enum "LowerLayerDown";
            enum "Error";
          }
          config false;
          default "Down";
          description
            "The current operational state of the interface (see
             {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the interface as assigned by the
             CPE.";
        }
        leaf LastChange {
          type uint32;
          config false;
          description
            "The accumulated time in {{units}} since the interface
             entered its current operational state.";
        }
        leaf LowerLayers {
          type string;
          default "";
          description
            "{{list}} {{reference|an interface object that is
             stacked immediately below this interface object}}
             See {{bibref|TR-181i2|Section 4.2.1}}.";
        }
        leaf Reset {
          type boolean; /* command */
          default "false";
          description
            "When set to {{true}}, the device MUST tear down the
             existing PPP connection represented by this object
             and establish a new one.
          
             The device MUST initiate the reset after completion
             of the current CWMP session.  The device MAY delay
             resetting the connection in order to avoid
             interruption of a user service such as an ongoing
             voice call.
          
             Reset on a disabled interface is a no-op (not an
             error).";
        }
        leaf ConnectionStatus {
          type enumeration {
            enum "Unconfigured";
            enum "Connecting";
            enum "Authenticating";
            enum "Connected";
            enum "PendingDisconnect";
            enum "Disconnecting";
            enum "Disconnected";
          }
          config false;
          description
            "Current status of the connection.";
        }
        leaf LastConnectionError {
          type enumeration {
            enum "ERROR_NONE";
            enum "ERROR_ISP_TIME_OUT";
            enum "ERROR_COMMAND_ABORTED";
            enum "ERROR_NOT_ENABLED_FOR_INTERNET";
            enum "ERROR_BAD_PHONE_NUMBER";
            enum "ERROR_USER_DISCONNECT";
            enum "ERROR_ISP_DISCONNECT";
            enum "ERROR_IDLE_DISCONNECT";
            enum "ERROR_FORCED_DISCONNECT";
            enum "ERROR_SERVER_OUT_OF_RESOURCES";
            enum "ERROR_RESTRICTED_LOGON_HOURS";
            enum "ERROR_ACCOUNT_DISABLED";
            enum "ERROR_ACCOUNT_EXPIRED";
            enum "ERROR_PASSWORD_EXPIRED";
            enum "ERROR_AUTHENTICATION_FAILURE";
            enum "ERROR_NO_DIALTONE";
            enum "ERROR_NO_CARRIER";
            enum "ERROR_NO_ANSWER";
            enum "ERROR_LINE_BUSY";
            enum "ERROR_UNSUPPORTED_BITSPERSECOND";
            enum "ERROR_TOO_MANY_LINE_ERRORS";
            enum "ERROR_IP_CONFIGURATION";
            enum "ERROR_UNKNOWN";
          }
          config false;
          description
            "The cause of failure for the last connection setup
             attempt.";
        }
        leaf AutoDisconnectTime {
          type uint32;
          description
            "The time in {{units}} since the establishment of the
             connection after which connection termination is
             automatically initiated by the CPE.  This occurs
             irrespective of whether the connection is being used
             or not.  A value of 0 (zero) indicates that the
             connection is not to be shut down automatically.";
        }
        leaf IdleDisconnectTime {
          type uint32;
          description
            "The time in {{units}} that if the connection remains
             idle, the CPE automatically terminates the
             connection.  A value of 0 (zero) indicates that the
             connection is not to be shut down automatically.";
        }
        leaf WarnDisconnectDelay {
          type uint32;
          description
            "Time in {{units}} the {{param|ConnectionStatus}}
             remains in the
             {{enum|PendingDisconnect|ConnectionStatus}} state
             before transitioning to disconnecting state to drop
             the connection.";
        }
        leaf Username {
          type string {
            length "0..64";
          }
          description
            "Username to be used for authentication.";
        }
        leaf Password {
          type string {
            length "0..64";
          }
          description
            "Password to be used for authentication.";
        }
        leaf EncryptionProtocol {
          type enumeration {
            enum "None";
            enum "MPPE";
          }
          config false;
          description
            "Describes the PPP encryption protocol.";
        }
        leaf CompressionProtocol {
          type enumeration {
            enum "None";
            enum "Van Jacobson";
            enum "STAC LZS";
          }
          config false;
          description
            "Describes the PPP compression protocol.";
        }
        leaf AuthenticationProtocol {
          type enumeration {
            enum "PAP";
            enum "CHAP";
            enum "MS-CHAP";
          }
          config false;
          description
            "Describes the PPP authentication protocol.";
        }
        leaf MaxMRUSize {
          type uint32 {
            range "64..65535";
          }
          default "1500";
          description
            "The maximum allowed size of frames sent from the remote
             peer.";
        }
        leaf CurrentMRUSize {
          type uint32 {
            range "64..65535";
          }
          config false;
          description
            "The current MRU in use over this connection.";
        }
        leaf ConnectionTrigger {
          type enumeration {
            enum "OnDemand";
            enum "AlwaysOn";
            enum "Manual";
          }
          description
            "Trigger used to establish the PPP connection.  {{enum}}
          
             Note that the reason for a PPP connection becoming
             disconnected to begin with might be either external
             to the CPE, such as termination by the BRAS or
             momentary disconnection of the physical interface,
             or internal to the CPE, such as use of the
             {{param|IdleDisconnectTime}} and/or
             {{param|AutoDisconnectTime}} parameters in this
             object.";
        }
        leaf LCPEcho {
          type uint32;
          config false;
          description
            "PPP LCP Echo period in {{units}}.";
        }
        leaf LCPEchoRetry {
          type uint32;
          config false;
          description
            "Number of PPP LCP Echo retries within an echo period.";
        }
        leaf IPCPEnable {
          type boolean;
          description
            "Enables or disables IPCP ({{bibref|RFC1332}}) on this
             interface.  If this parameter is present,
             {{enum|IPCP|#.SupportedNCPs}} MUST be included in
             {{param|#.SupportedNCPs}}.";
        }
        leaf IPv6CPEnable {
          type boolean;
          description
            "Enables or disables IPv6CP ({{bibref|RFC5072}}) on this
             interface.  If this parameter is present,
             {{enum|IPv6CP|#.SupportedNCPs}} MUST be included in
             {{param|#.SupportedNCPs}}.";
        }

        container PPPoA {
          config false;
          description
            "PPPoA object that functionally groups PPPoA related
             parameters.";
        }

        container PPPoE {
          description
            "PPPoE object that functionally groups PPPoE related
             parameters.";
          leaf SessionID {
            type uint32 {
              range "1..max";
            }
            config false;
            description
              "Represents the PPPoE Session ID.";
          }
          leaf ACName {
            type string {
              length "0..256";
            }
            description
              "PPPoE Access Concentrator.";
          }
          leaf ServiceName {
            type string {
              length "0..256";
            }
            description
              "PPPoE Service Name.";
          }
        }

        container IPCP {
          description
            "IP Control Protocol (IPCP) client object for this PPP
             interface {{bibref|RFC1332}}.  {{object}} only
             applies to IPv4.";
          leaf LocalIPAddress {
            type types:IPv4Address;
            config false;
            default "";
            description
              "The local IPv4 address for this connection received
               via IPCP.";
          }
          leaf RemoteIPAddress {
            type types:IPv4Address;
            config false;
            default "";
            description
              "The remote IPv4 address for this connection received
               via IPCP.";
          }
          leaf DNSServers {
            type types:IPv4Address;
            config false;
            default "";
            description
              "{{list}} Items represent DNS Server IPv4 address(es)
               received via IPCP {{bibref|RFC1877}}.";
          }
          leaf PassthroughEnable {
            type boolean;
            default "false";
            description
              "If {{false}}, the PPP Interface retrieved information
               is configured on the IP Interface stacked on top
               of this PPP Interface.
            
               If {{true}}, the PPP Interface retrieved
               information is propagated to the parameters in the
               referenced {{param|PassthroughDHCPPool}} object,
               replacing any existing configuration (including
               ''MinAddress'', ''MaxAddress'', ''SubnetMask'',
               ''IPRouters'', and ''DNSServers'').";
          }
          leaf PassthroughDHCPPool {
            type string {
              length "0..256";
            }
            default "";
            description
              "{{reference}}When {{param}} is set to {{empty}},
               {{param|PassthroughEnable}} MUST be set to
               {{false}} (i.e.  passthrough can not be enabled
               without a pool reference specified).";
          }
        }

        container IPv6CP {
          config false;
          description
            "IPv6 Control Protocol (IPv6CP) client object for this
             PPP interface {{bibref|RFC5072}}.  {{object}} only
             applies to IPv6.";
          leaf LocalInterfaceIdentifier {
            type types:IPv6Address;
            description
              "The interface identifier for the local end of the PPP
               link, negotiated using the IPv6CP
               ''Interface-Identifier'' option
               {{bibref|RFC5072|Section 4.1}}.
            
               The identifier is represented as the rightmost 64
               bits of an IPv6 address (the leftmost 64 bits MUST
               be zero and MUST be ignored by the recipient).";
          }
          leaf RemoteInterfaceIdentifier {
            type types:IPv6Address;
            description
              "The interface identifier for the remote end of the
               PPP link, negotiated using the IPv6CP
               ''Interface-Identifier'' option
               {{bibref|RFC5072|Section 4.1}}.
            
               The identifier is represented as the rightmost 64
               bits of an IPv6 address (the leftmost 64 bits MUST
               be zero and MUST be ignored by the recipient).";
          }
        }

        container Stats {
          config false;
          description
            "Throughput statistics for this interface.
          
             The CPE MUST reset the interface's Stats parameters
             (unless otherwise stated in individual object or
             parameter descriptions) either when the interface
             becomes operationally down due to a previous
             administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2|section 4.2.2}}.";
          leaf BytesSent {
            type uint64;
            description
              "The total number of bytes transmitted out of the
               interface, including framing characters.";
          }
          leaf BytesReceived {
            type uint64;
            description
              "The total number of bytes received on the interface,
               including framing characters.";
          }
          leaf PacketsSent {
            type uint64;
            description
              "The total number of packets transmitted out of the
               interface.";
          }
          leaf PacketsReceived {
            type uint64;
            description
              "The total number of packets received on the
               interface.";
          }
          leaf ErrorsSent {
            type uint32;
            description
              "The total number of outbound packets that could not
               be transmitted because of errors.";
          }
          leaf ErrorsReceived {
            type uint32;
            description
              "The total number of inbound packets that contained
               errors preventing them from being delivered to a
               higher-layer protocol.";
          }
          leaf UnicastPacketsSent {
            type uint64;
            description
              "The total number of packets requested for
               transmission which were not addressed to a
               multicast or broadcast address at this layer,
               including those that were discarded or not sent.";
          }
          leaf UnicastPacketsReceived {
            type uint64;
            description
              "The total number of received packets, delivered by
               this layer to a higher layer, which were not
               addressed to a multicast or broadcast address at
               this layer.";
          }
          leaf DiscardPacketsSent {
            type uint32;
            description
              "The total number of outbound packets which were
               chosen to be discarded even though no errors had
               been detected to prevent their being transmitted.
               One possible reason for discarding such a packet
               could be to free up buffer space.";
          }
          leaf DiscardPacketsReceived {
            type uint32;
            description
              "The total number of inbound packets which were chosen
               to be discarded even though no errors had been
               detected to prevent their being delivered.  One
               possible reason for discarding such a packet could
               be to free up buffer space.";
          }
          leaf MulticastPacketsSent {
            type uint64;
            description
              "The total number of packets that higher-level
               protocols requested for transmission and which
               were addressed to a multicast address at this
               layer, including those that were discarded or not
               sent.";
          }
          leaf MulticastPacketsReceived {
            type uint64;
            description
              "The total number of received packets, delivered by
               this layer to a higher layer, which were addressed
               to a multicast address at this layer.";
          }
          leaf BroadcastPacketsSent {
            type uint64;
            description
              "The total number of packets that higher-level
               protocols requested for transmission and which
               were addressed to a broadcast address at this
               layer, including those that were discarded or not
               sent.";
          }
          leaf BroadcastPacketsReceived {
            type uint64;
            description
              "The total number of received packets, delivered by
               this layer to a higher layer, which were addressed
               to a broadcast address at this layer.";
          }
          leaf UnknownProtoPacketsReceived {
            type uint32;
            description
              "The total number of packets received via the
               interface which were discarded because of an
               unknown or unsupported protocol.";
          }
        }
      }
    }

    container IP {
      description
        "IP object that contains the {{object|Interface}},
         {{object|ActivePort}}, and {{object|Diagnostics}}
         objects.";
      leaf IPv4Capable {
        type boolean;
        config false;
        description
          "Indicates whether the device is IPv4 capable.";
      }
      leaf IPv4Enable {
        type boolean;
        description
          "Enables or disables the IPv4 stack, and so the use of
           IPv4 on the device.  This affects only layer 3 and
           above.
        
           When {{false}}, IP interfaces that had been
           operationally up and passing IPv4 packets will now no
           longer be able to do so, and will be operationally
           down (unless also attached to an enabled IPv6 stack).";
      }
      leaf IPv4Status {
        type enumeration {
          enum "Disabled";
          enum "Enabled";
          enum "Error";
        }
        config false;
        description
          "Indicates the status of the IPv4 stack.  {{enum}}
        
           The {{enum|Error}} value MAY be used by the CPE to
           indicate a locally defined error condition.";
      }
      leaf IPv6Capable {
        type boolean;
        config false;
        description
          "Indicates whether the device is IPv6 capable.
        
           Note: If {{false}}, it is expected that IPv6-related
           parameters, enumeration values, etc will not be
           implemented by the device.";
      }
      leaf IPv6Enable {
        type boolean;
        description
          "Enables or disables the IPv6 stack, and so the use of
           IPv6 on the device.  This affects only layer 3 and
           above.
        
           When {{false}}, IP interfaces that had been
           operationally up and passing IPv6 packets will now no
           longer be able to do so, and will be operationally
           down (unless also attached to an enabled IPv4 stack).";
      }
      leaf IPv6Status {
        type enumeration {
          enum "Disabled";
          enum "Enabled";
          enum "Error";
        }
        config false;
        description
          "Indicates the status of the IPv6 stack.  {{enum}}
        
           The {{enum|Error}} value MAY be used by the CPE to
           indicate a locally defined error condition.";
      }
      leaf ULAPrefix {
        type types:IPv6Prefix;
        description
          "The ULA /48 prefix {{bibref|RFC4193|Section 3}}.";
      }

      list Interface {
        key "Alias";
        description
          "IP interface table (a stackable interface object as
           described in {{bibref|TR-181i2|Section 4.2}}).  This
           table models the layer 3 IP interface.
        
           Each IP interface can be attached to the IPv4 and/or
           IPv6 stack.  The interface's IP addresses and prefixes
           are listed in the {{object|IPv4Address}},
           {{object|IPv6Address}} and {{object|IPv6Prefix}}
           tables.
        
           Note that support for manipulating {{param|Loopback}}
           interfaces is OPTIONAL, so the implementation MAY
           choose not to create (or allow the ACS to create)
           {{object}} instances of type {{enum|Loopback|Type}}.
        
           When the ACS administratively disables the interface,
           i.e.  sets {{param|Enable}} to {{false}}, the
           interface's automatically-assigned IP addresses and
           prefixes MAY be retained.  When the ACS
           administratively enables the interface, i.e.  sets
           {{param|Enable}} to {{true}}, these IP addresses and
           prefixes MUST be refreshed.  It's up to the
           implementation to decide exactly what this means: it
           SHOULD take all reasonable steps to refresh everything
           but if it is unable, for example, to refresh a prefix
           that still has a significant lifetime, it might well
           choose to retain rather than discard it.
        
           Any {{enum|Tunneled|Type}} IP interface instances
           instantiated by the CPE MUST NOT have any statistics,
           writable parameters, IP addresses or IPv6 prefixes.
           Any read-only parameters, e.g.  {{param|Status}}, MUST
           return the same information as for the corresponding
           {{enum|Tunnel|Type}} interface.  The reason for these
           rules is that {{enum|Tunneled|Type}} IP interfaces
           exist only in order to be the targets of references
           (within the data model) and do not model any concepts
           over and above those already modeled by the
           {{enum|Tunnel|Type}} IP interfaces.
        
           Note that {{enum|Tunnel|Type}} and
           {{enum|Tunneled|Type}} IP interfaces are part of a
           legacy mechanism that is only used for
           {{object|##.IPv6rd}}, {{object|##.DSLite}} and
           {{object|##.IPsec}} tunnels and MUST NOT be used in
           any other context.  For all other tunneling mechanisms
           {{enum|Normal|Type}} IP interfaces are stacked above
           technology-specific Tunnel Interfaces, e.g.  above
           {{object|##.GRE.Tunnel.{i}.Interface}} or
           {{object|##.MAP.Domain.{i}.Interface}} objects.";
        leaf Enable {
          type boolean;
          default "false";
          description
            "Enables or disables the interface (regardless of
             {{param|IPv4Enable}} and {{param|IPv6Enable}}).
          
             This parameter is based on ''ifAdminStatus'' from
             {{bibref|RFC2863}}.";
        }
        leaf IPv4Enable {
          type boolean;
          description
            "If set to {{true}}, attaches this interface to the IPv4
             stack.  If set to {{false}}, detaches this interface
             from the IPv4 stack.
          
             Once detached from the IPv4 stack, the interface
             will now no longer be able to pass IPv4 packets, and
             will be operationally down (unless also attached to
             an enabled IPv6 stack).
          
             For an IPv4 capable device, if {{param}} is not
             present this interface SHOULD be permanently
             attached to the IPv4 stack.
          
             Note that {{param}} is independent of
             {{param|Enable}}, and that to administratively
             enable an interface for IPv4 it is necessary for
             both {{param|Enable}} and {{param}} to be {{true}}.";
        }
        leaf IPv6Enable {
          type boolean;
          description
            "If set to {{true}}, attaches this interface to the IPv6
             stack.  If set to {{false}}, detaches this interface
             from the IPv6 stack.
          
             Once detached from the IPv6 stack, the interface
             will now no longer be able to pass IPv6 packets, and
             will be operationally down (unless also attached to
             an enabled IPv4 stack).
          
             For an IPv6 capable device, if {{param}} is not
             present this interface SHOULD be permanently
             attached to the IPv6 stack.
          
             Note that {{param}} is independent of
             {{param|Enable}}, and that to administratively
             enable an interface for IPv6 it is necessary for
             both {{param|Enable}} and {{param}} to be {{true}}.";
        }
        leaf ULAEnable {
          type boolean;
          default "false";
          description
            "Controls whether or not ULAs {{bibref|RFC4193}} are
             generated and used on this interface.";
        }
        leaf Status {
          type enumeration {
            enum "Up";
            enum "Down";
            enum "Unknown";
            enum "Dormant";
            enum "NotPresent";
            enum "LowerLayerDown";
            enum "Error";
          }
          config false;
          default "Down";
          description
            "The current operational state of the interface (see
             {{bibref|TR-181i2|Section 4.2.2}}).  {{enum}}
          
             When {{param|Enable}} is {{false}} then {{param}}
             SHOULD normally be {{enum|Down}} (or
             {{enum|NotPresent}} or {{enum|Error}} if there is a
             fault condition on the interface).
          
             When {{param|Enable}} is changed to {{true}} then
             {{param}} SHOULD change to {{enum|Up}} if and only
             if the interface is able to transmit and receive
             network traffic; it SHOULD change to
             {{enum|Dormant}} if and only if the interface is
             operable but is waiting for external actions before
             it can transmit and receive network traffic (and
             subsequently change to {{enum|Up}} if still operable
             when the expected actions have completed); it SHOULD
             change to {{enum|LowerLayerDown}} if and only if the
             interface is prevented from entering the {{enum|Up}}
             state because one or more of the interfaces beneath
             it is down; it SHOULD remain in the {{enum|Error}}
             state if there is an error or other fault condition
             detected on the interface; it SHOULD remain in the
             {{enum|NotPresent}} state if the interface has
             missing (typically hardware) components; it SHOULD
             change to {{enum|Unknown}} if the state of the
             interface can not be determined for some reason.
          
             This parameter is based on ''ifOperStatus'' from
             {{bibref|RFC2863}}.";
        }
        leaf Name {
          type string {
            length "0..64";
          }
          config false;
          description
            "The textual name of the interface as assigned by the
             CPE.";
        }
        leaf LastChange {
          type uint32;
          config false;
          description
            "The accumulated time in {{units}} since the interface
             entered its current operational state.";
        }
        leaf LowerLayers {
          type string;
          default "";
          description
            "{{list}} {{reference|an interface object that is
             stacked immediately below this interface object}}
             See {{bibref|TR-181i2|Section 4.2.1}}.
          
             {{param}} MUST be {{empty}} and read-only when
             {{param|Type}} is {{enum|Loopback|Type}},
             {{enum|Tunnel|Type}}, or {{enum|Tunneled|Type}}.";
        }
        leaf Router {
          type string {
            length "0..256";
          }
          default "";
          description
            "{{reference}} The ''Router'' instance that is
             associated with this IP Interface entry.";
        }
        leaf Reset {
          type boolean; /* command */
          default "false";
          description
            "When set to {{true}}, the device MUST tear down the
             existing IP connection represented by this object
             and establish a new one.
          
             The device MUST initiate the reset after completion
             of the current CWMP session.  The device MAY delay
             resetting the connection in order to avoid
             interruption of a user service such as an ongoing
             voice call.
          
             Reset on a disabled interface is a no-op (not an
             error).";
        }
        leaf MaxMTUSize {
          type uint32 {
            range "64..65535";
          }
          description
            "The maximum transmission unit (MTU); the largest
             allowed size of an IP packet (including IP headers,
             but excluding lower layer headers such as Ethernet,
             PPP, or PPPoE headers) that is allowed to be
             transmitted by or through this device.";
        }
        leaf Type {
          type enumeration {
            enum "Normal";
            enum "Loopback";
            enum "Tunnel";
            enum "Tunneled";
          }
          config false;
          default "Normal";
          description
            "IP interface type.  {{enum}}
          
             For {{enum|Loopback}}, {{enum|Tunnel}}, and
             {{enum|Tunneled}} IP interface objects, the
             {{param|LowerLayers}} parameter MUST be {{empty}}.";
        }
        leaf Loopback {
          type boolean;
          default "false";
          description
            "When set to {{true}}, the IP interface becomes a
             loopback interface and the CPE MUST set
             {{param|Type}} to {{enum|Loopback|Type}}.  In this
             case, the CPE MUST also set {{param|LowerLayers}} to
             {{empty}} and fail subsequent attempts at setting
             {{param|LowerLayers}} until the interface is no
             longer a loopback.
          
             Support for manipulating loopback interfaces is
             OPTIONAL.";
        }
        leaf AutoIPEnable {
          type boolean;
          default "false";
          description
            "If {{true}}, enables auto-IP on the interface
             {{bibref|RFC3927}}.  This mechanism is only used
             with IPv4.
          
             When auto-IP is enabled on an interface, an
             {{object|IPv4Address}} object will dynamically be
             created and configured with auto-IP parameter
             values.  The exact conditions under which an auto-IP
             address is created (e.g.  always when enabled or
             only in absence of dynamic IP addressing) is
             implementation specific.";
        }

        list IPv4Address {
          key "IPAddress SubnetMask";
          description
            "IPv4 address table.  Entries are auto-created and
             auto-deleted as IP addresses are added and deleted
             via DHCP, auto-IP, or IPCP.  Static entries are
             created and configured by the ACS.";
          leaf Enable {
            type boolean;
            default "false";
            description
              "Enables or disables this IPv4 address.";
          }
          leaf Status {
            type enumeration {
              enum "Disabled";
              enum "Enabled";
              enum "Error_Misconfigured";
              enum "Error";
            }
            config false;
            default "Disabled";
            description
              "The status of this {{object}} table entry.  {{enum}}
            
               The {{enum|Error_Misconfigured}} value indicates
               that a necessary configuration value is undefined
               or invalid.
            
               The {{enum|Error}} value MAY be used by the CPE to
               indicate a locally defined error condition.";
          }
          leaf IPAddress {
            type types:IPv4Address;
            description
              "IPv4 address.
            
               This parameter can only be modified if the
               {{param|AddressingType}} is
               {{enum|Static|AddressingType}}.";
          }
          leaf SubnetMask {
            type types:IPv4Address;
            default "";
            description
              "Subnet mask.
            
               This parameter can only be modified if the
               {{param|AddressingType}} is
               {{enum|Static|AddressingType}}.";
          }
          leaf AddressingType {
            type enumeration {
              enum "DHCP";
              enum "IKEv2";
              enum "AutoIP";
              enum "IPCP";
              enum "Static";
            }
            config false;
            default "Static";
            description
              "Addressing method used to assign the IP address.
               {{enum}}";
          }
        }

        list IPv6Address {
          key "IPAddress";
          description
            "This table contains the IP interface's IPv6 unicast
             addresses.  There MUST be an entry for each such
             address, including anycast addresses.
          
             There are several ways in which entries can be added
             to and deleted from this table, including:
          
             * Automatically via SLAAC {{bibref|RFC4862}}, which
             covers generation of link-local addresses (for all
             types of device) and global addresses (for
             non-router devices).
          
             * Automatically via DHCPv6 {{bibref|RFC3315}}, which
             covers generation of any type of address (subject to
             the configured DHCP server policy).
          
             * Manually via a GUI or some other local management
             interface.
          
             * Manually via factory default configuration.
          
             * By the ACS.
          
             This table MUST NOT include entries for the
             Subnet-Router anycast address
             {{bibref|RFC4291|Section 2.6.1}}.  Such entries
             would be identical to others but with a zero
             interface identifier, and would add no value.
          
             A loopback interface will always have address
             ''::1'' {{bibref|RFC4291|Section 2.5.3}} and MAY
             also have link-local address ''fe80::1''.
          
             This object is based on ''ipAddressTable'' from
             {{bibref|RFC4293}}.";
          leaf Enable {
            type boolean;
            default "false";
            description
              "Enables or disables this {{object}} entry.";
          }
          leaf Status {
            type enumeration {
              enum "Disabled";
              enum "Enabled";
              enum "Error_Misconfigured";
              enum "Error";
            }
            config false;
            default "Disabled";
            description
              "The status of this {{object}} table entry.  {{enum}}
            
               The {{enum|Error_Misconfigured}} value indicates
               that a necessary configuration value is undefined
               or invalid.
            
               The {{enum|Error}} value MAY be used by the CPE to
               indicate a locally defined error condition.";
          }
          leaf IPAddressStatus {
            type enumeration {
              enum "Preferred";
              enum "Deprecated";
              enum "Invalid";
              enum "Inaccessible";
              enum "Unknown";
              enum "Tentative";
              enum "Duplicate";
              enum "Optimistic";
            }
            config false;
            default "Invalid";
            description
              "The status of {{param|IPAddress}}, indicating whether
               it can be used for communication.  See also
               {{param|PreferredLifetime}} and
               {{param|ValidLifetime}}.  {{enum}}
            
               This parameter is based on ''ipAddressStatus'' and
               ''ipAddressStatusTC'' from {{bibref|RFC4293}}.";
          }
          leaf IPAddress {
            type types:IPv6Address;
            default "";
            description
              "IPv6 address.
            
               This parameter can only be modified if the
               {{param|Origin}} is {{enum|Static|Origin}}.
            
               This parameter is based on ''ipAddressAddr'' from
               {{bibref|RFC4293}}.";
          }
          leaf Origin {
            type enumeration {
              enum "AutoConfigured";
              enum "DHCPv6";
              enum "IKEv2";
              enum "MAP";
              enum "WellKnown";
              enum "Static";
            }
            config false;
            default "Static";
            description
              "Mechanism via which the IP address was assigned.
               {{enum}}
            
               This parameter is based on ''ipOrigin'' from
               {{bibref|RFC4293}}.";
          }
          leaf Prefix {
            type string;
            default "";
            description
              "IPv6 address prefix.
            
               Some addresses, e.g.  addresses assigned via the
               DHCPv6 IA_NA option, are not associated with a
               prefix, and some
               {{enum|WellKnown|#.IPv6Prefix.{i}.Origin}}
               prefixes might not be modeled.  In both of these
               cases {{param}} will be {{null}}.
            
               This parameter can only be modified if the
               {{param|Origin}} is {{enum|Static|Origin}}.
            
               This parameter is based on ''ipAddressPrefix''
               from {{bibref|RFC4293}}.";
          }
          leaf PreferredLifetime {
            type yang:date-and-time;
            default "9999-12-31T23:59:59Z";
            description
              "The time at which this address will cease to be
               preferred (i.e.  will become deprecated), or
               {{null}} if not known.  For an infinite lifetime,
               the parameter value MUST be 9999-12-31T23:59:59Z.
            
               This parameter can only be modified if the
               {{param|Origin}} is {{enum|Static|Origin}}.";
          }
          leaf ValidLifetime {
            type yang:date-and-time;
            default "9999-12-31T23:59:59Z";
            description
              "The time at which this address will cease to be valid
               (i.e.  will become invalid), or {{null}} if
               unknown.  For an infinite lifetime, the parameter
               value MUST be 9999-12-31T23:59:59Z.
            
               This parameter can only be modified if the
               {{param|Origin}} is {{enum|Static|Origin}}.";
          }
          leaf Anycast {
            type boolean;
            default "false";
            description
              "Indicates whether this is an anycast address
               {{bibref|RFC4291|Section 2.6}}.  Anycast addresses
               are syntactically identical to unicast addresses
               and so need to be configured explicitly.
            
               This parameter can only be modified if the
               {{param|Origin}} is {{enum|Static|Origin}}.
            
               This parameter is based on ''ipAddressType'' from
               {{bibref|RFC4293}}.";
          }
        }

        list IPv6Prefix {
          key "Prefix";
          description
            "This table contains the interface's IPv6 prefixes.
             There MUST be an entry for each such prefix, not
             only for prefixes learned from router
             advertisements.
          
             There are several ways in which entries can be added
             to and deleted from this table, including:
          
             * Automatically via {{bibref|RFC4861}} Router
             Advertisements.  See also
             {{object|.RouterAdvertisement}}.
          
             * Automatically via DHCPv6 {{bibref|RFC3315}} prefix
             delegation {{bibref|RFC3633}}.  See also
             {{object|.DHCPv6.Client}}.
          
             * Automatically via internal CPE logic, e.g.
             creation of child prefixes derived from a parent
             prefix.
          
             * Manually via a GUI or some other local management
             interface.
          
             * Manually via factory default configuration.
          
             * By the ACS.
          
             The CPE MAY choose not to create {{object}} entries
             for {{enum|WellKnown|Origin}} prefixes or for the
             ULA /48 prefix {{bibref|RFC4193}}.  If an {{object}}
             entry exists for the ULA /48 prefix, it MUST be on a
             downstream interface (i.e.  an interface for which
             the physical layer interface object has ''Upstream''
             = {{false}}).
          
             This object is based on ''ipAddressPrefixTable''
             from {{bibref|RFC4293}}.";
          leaf Enable {
            type boolean;
            default "false";
            description
              "Enables or disables this {{object}} entry.";
          }
          leaf Status {
            type enumeration {
              enum "Disabled";
              enum "Enabled";
              enum "Error";
            }
            config false;
            default "Disabled";
            description
              "The status of this {{object}} table entry.  {{enum}}
            
               The {{enum|Error}} value MAY be used by the CPE to
               indicate a locally defined error condition.";
          }
          leaf PrefixStatus {
            type enumeration {
              enum "Preferred";
              enum "Deprecated";
              enum "Invalid";
              enum "Inaccessible";
              enum "Unknown";
            }
            config false;
            default "Invalid";
            description
              "The status of {{param|Prefix}}, indicating whether it
               can be used for communication.  See also
               {{param|PreferredLifetime}} and
               {{param|ValidLifetime}}.  {{enum}}
            
               This parameter is based on ''ipAddressStatus'' and
               ''ipAddressStatusTC'' from {{bibref|RFC4293}}.";
          }
          leaf Prefix {
            type types:IPv6Prefix;
            default "";
            description
              "IPv6 address prefix.
            
               This parameter can only be modified if the
               {{param|Origin}} is {{enum|Static|Origin}}.
            
               This parameter is based on
               ''ipAddressPrefixPrefix'' from {{bibref|RFC4293}}.";
          }
          leaf Origin {
            type enumeration {
              enum "AutoConfigured";
              enum "PrefixDelegation";
              enum "RouterAdvertisement";
              enum "WellKnown";
              enum "Static";
              enum "Child";
            }
            config false;
            default "Static";
            description
              "Mechanism via which the prefix was assigned or most
               recently updated.  {{enum}}
            
               Note that:
            
               * {{enum|PrefixDelegation}} and
               {{enum|RouterAdvertisement}} prefixes can exist
               only on upstream interfaces (i.e.  interfaces for
               which the physical layer interface object has
               ''Upstream'' = {{true}}),
            
               * {{enum|AutoConfigured}} and {{enum|WellKnown}}
               prefixes can exist on any interface, and
            
               * {{enum|Static}} and {{enum|Child}} prefixes can
               exist only on downstream interfaces (i.e.
               interfaces for which the physical layer interface
               object has ''Upstream'' = {{false}}).
            
               Also note that a {{enum|Child}} prefix's
               {{param|ParentPrefix}} will always be an
               {{enum|AutoConfigured}},
               {{enum|PrefixDelegation}}, or
               {{enum|RouterAdvertisement}} prefix.
            
               This parameter is based on ''ipAddressOrigin''
               from {{bibref|RFC4293}}.";
          }
          leaf StaticType {
            type enumeration {
              enum "Static";
              enum "Inapplicable";
              enum "PrefixDelegation";
              enum "Child";
            }
            default "Static";
            description
              "Static prefix sub-type.  For a {{enum|Static|Origin}}
               prefix, this can be set to
               {{enum|PrefixDelegation}} or {{enum|Child}},
               thereby creating an unconfigured prefix of the
               specified type that will be populated in
               preference to creating a new instance.  This
               allows the ACS to pre-create \"prefix slots\" with
               known path names that can be referenced from
               elsewhere in the data model before they have been
               populated.  {{enum}}
            
               This mechanism works as follows:
            
               * When this parameter is set to
               {{enum|PrefixDelegation}} or {{enum|Child}}, the
               instance becomes a \"prefix slot\" of the
               specified type.
            
               * Such an instance can be administratively enabled
               ({{param|Enable}} = {{true}}) but will remain
               operationally disabled ({{param|Status}} =
               {{enum|Disabled|Status}}) until it has been
               populated.
            
               * When a new prefix of of type T is needed, the
               CPE will look for a matching unpopulated instance,
               i.e.  an instance with
               ({{param|Origin}},{{param}},{{param|Prefix}}) =
               ({{enum|Static|Origin}},T,\"\").  If the CPE finds
               at least one such instance it will choose one and
               populate it.  If already administratively enabled
               it will immediately become operationally enabled.
               If the CPE finds no such instances, it will create
               and populate a new instance with
               ({{param|Origin}},{{param}}) = (T,T).  If the CPE
               finds more than one such instance, the algorithm
               via which it chooses which instance to populate is
               implementation-specific.
            
               * When a prefix that was populated via this
               mechanism becomes invalid, the CPE will reset
               {{param|Prefix}} to {{empty}}.  This does not
               affect the value of the {{param|Enable}}
               parameter.
            
               The prefix {{param}} can only be modified if
               {{param|Origin}} is {{enum|Static|Origin}}.";
          }
          leaf ParentPrefix {
            type string;
            default "";
            description
              "Indicates the parent prefix from which this prefix
               was derived.  The parent prefix is relevant only
               for {{enum|Child|Origin}} prefixes and for
               {{enum|Static|Origin}} {{enum|Child|StaticType}}
               prefixes (both of which will always be on
               downstream interfaces), i.e.  for
               {{param|Origin}}={{enum|Child|Origin}} and for
               ({{param|Origin}},{{param|StaticType}}) =
               ({{enum|Static|Origin}},{{enum|Child|StaticType}})
               prefixes.
            
               This parameter can only be modified if
               {{param|Origin}} is {{enum|Static|Origin}} (which
               makes sense only for a prefix whose
               {{param|StaticType}} is already or will be changed
               to {{enum|Child|StaticType}}).";
          }
          leaf ChildPrefixBits {
            type types:IPv6Prefix;
            default "";
            description
              "A prefix that specifies the length of
               {{enum|Static|Origin}} {{enum|Child|StaticType}}
               prefixes and how they are derived from their
               {{param|ParentPrefix}}.  It will be used if and
               only if it is not {{empty}} and is longer than the
               parent prefix (if it is not used, derivation of
               such prefixes is implementation-specific).  Any
               bits to the right of the parent prefix are set to
               the bits in this prefix.
            
               For example, for a parent prefix of fedc::/56, if
               this parameter had the value
               123:4567:89ab:cdef::/64, the child /64 would be
               fedc:0:0:ef::/64.  For a parent prefix of
               fedc::/60, the child /64 would be fedc:0:0:f::/64.
            
               This parameter can only be modified if
               {{param|Origin}} is {{enum|Static|Origin}}.";
          }
          leaf OnLink {
            type boolean;
            default "false";
            description
              "On-link flag {{bibref|RFC4861|Section 4.6.2}} as
               received (in the RA) for RouterAdvertisement.
               Indicates whether this prefix can be used for
               on-link determination.
            
               This parameter can only be modified if
               {{param|Origin}} is {{enum|Static|Origin}}.
            
               This parameter is based on
               ''ipAddressPrefixOnLinkFlag'' from
               {{bibref|RFC4293}}.";
          }
          leaf Autonomous {
            type boolean;
            default "false";
            description
              "Autonomous address configuration flag
               {{bibref|RFC4861|Section 4.6.2}} as received (in
               the RA) for RouterAdvertisement.  Indicates
               whether this prefix can be used for generating
               global addresses as specified by SLAAC
               {{bibref|RFC4862}}.
            
               This parameter can only be modified if
               {{param|Origin}} is {{enum|Static|Origin}}.
            
               This parameter is based on
               ''ipAddressPrefixAutonomousFlag'' from
               {{bibref|RFC4293}}.";
          }
          leaf PreferredLifetime {
            type yang:date-and-time;
            default "9999-12-31T23:59:59Z";
            description
              "This parameter is based on
               ''ipAddressPrefixAdvPreferredLifetime'' from
               {{bibref|RFC4293}}.  The time at which this prefix
               will cease to be preferred (i.e.  will become
               deprecated), or {{null}} if not known.  For an
               infinite lifetime, the parameter value MUST be
               9999-12-31T23:59:59Z.
            
               This parameter can only be modified if
               {{param|Origin}} is {{enum|Static|Origin}}.";
          }
          leaf ValidLifetime {
            type yang:date-and-time;
            default "9999-12-31T23:59:59Z";
            description
              "This parameter is based on
               ''ipAddressPrefixAdvValidLifetime'' from
               {{bibref|RFC4293}}.  The time at which this prefix
               will cease to be valid (i.e.  will become
               invalid), or {{null}} if not known.  For an
               infinite lifetime, the parameter value MUST be
               9999-12-31T23:59:59Z.
            
               This parameter can only be modified if
               {{param|Origin}} is {{enum|Static|Origin}}.";
          }
        }

        container Stats {
          config false;
          description
            "Throughput statistics for this interface.
          
             The CPE MUST reset the interface's Stats parameters
             (unless otherwise stated in individual object or
             parameter descriptions) either when the interface
             becomes operationally down due to a previous
             administrative down (i.e.  the interface's
             {{param|#.Status}} parameter transitions to a down
             state after the interface is disabled) or when the
             interface becomes administratively up (i.e.  the
             interface's {{param|#.Enable}} parameter transitions
             from {{false}} to {{true}}).  Administrative and
             operational interface status is discussed in
             {{bibref|TR-181i2|section 4.2.2}}.";
          leaf BytesSent {
            type uint64;
            description
              "The total number of bytes transmitted out of the
               interface, including framing characters.";
          }
          leaf BytesReceived {
            type uint64;
            description
              "The total number of bytes received on the interface,
               including framing characters.";
          }
          leaf PacketsSent {
            type uint64;
            description
              "The total number of packets transmitted out of the
               interface.";
          }
          leaf PacketsReceived {
            type uint64;
            description
              "The total number of packets received on the
               interface.";
          }
          leaf ErrorsSent {
            type uint32;
            description
              "The total number of outbound packets that could not
               be transmitted because of errors.";
          }
          leaf ErrorsReceived {
            type uint32;
            description
              "The total number of inbound packets that contained
               errors preventing them from being delivered to a
               higher-layer protocol.";
          }
          leaf UnicastPacketsSent {
            type uint64;
            description
              "The total number of packets requested for
               transmission which were not addressed to a
               multicast or broadcast address at this layer,
               including those that were discarded or not sent.";
          }
          leaf UnicastPacketsReceived {
            type uint64;
            description
              "The total number of received packets, delivered by
               this layer to a higher layer, which were not
               addressed to a multicast or broadcast address at
               this layer.";
          }
          leaf DiscardPacketsSent {
            type uint32;
            description
              "The total number of outbound packets which were
               chosen to be discarded even though no errors had
               been detected to prevent their being transmitted.
               One possible reason for discarding such a packet
               could be to free up buffer space.";
          }
          leaf DiscardPacketsReceived {
            type uint32;
            description
              "The total number of inbound packets which were chosen
               to be discarded even though no errors had been
               detected to prevent their being delivered.  One
               possible reason for discarding such a packet could
               be to free up buffer space.";
          }
          leaf MulticastPacketsSent {
            type uint64;
            description
              "The total number of packets that higher-level
               protocols requested for transmission and which
               were addressed to a multicast address at this
               layer, including those that were discarded or not
               sent.";
          }
          leaf MulticastPacketsReceived {
            type uint64;
            description
              "The total number of received packets, delivered by
               this layer to a higher layer, which were addressed
               to a multicast address at this layer.";
          }
          leaf BroadcastPacketsSent {
            type uint64;
            description
              "The total number of packets that higher-level
               protocols requested for transmission and which
               were addressed to a broadcast address at this
               layer, including those that were discarded or not
               sent.
            
               Note that IPv6 does not define broadcast
               addresses, so IPv6 packets will never cause this
               counter to increment.";
          }
          leaf BroadcastPacketsReceived {
            type uint64;
            description
              "The total number of received packets, delivered by
               this layer to a higher layer, which were addressed
               to a broadcast address at this layer.
            
               Note that IPv6 does not define broadcast
               addresses, so IPv6 packets will never cause this
               counter to increment.";
          }
          leaf UnknownProtoPacketsReceived {
            type uint32;
            description
              "The total number of packets received via the
               interface which were discarded because of an
               unknown or unsupported protocol.";
          }
        }
      }

      list ActivePort {
        key "LocalIPAddress LocalPort RemoteIPAddress RemotePort";
        config false;
        description
          "This table lists the ports on which TCP connections are
           listening or established.";
        leaf LocalIPAddress {
          type types:IPAddress;
          description
            "Connection local IP address.";
        }
        leaf LocalPort {
          type uint32 {
            range "0..65535";
          }
          description
            "Connection local port.";
        }
        leaf RemoteIPAddress {
          type types:IPAddress;
          description
            "The remote IP address of the source of inbound packets.
          
             This will be {{null}} for listening connections
             (only connections in {{enum|ESTABLISHED|Status}}
             state have remote addresses).";
        }
        leaf RemotePort {
          type uint32 {
            range "0..65535";
          }
          description
            "The remote port of the source of inbound packets.
          
             This will be {{null}} for listening connections
             (only connections in {{enum|ESTABLISHED|Status}}
             state have remote addresses).";
        }
        leaf Status {
          type enumeration {
            enum "LISTEN";
            enum "ESTABLISHED";
          }
          description
            "Current operational status of the connection.  {{enum}}";
        }
      }

      container Diagnostics {
        description
          "The IP Diagnostics object.";
        leaf IPv4PingSupported {
          type boolean;
          config false;
          description
            "Indicates that Ping over IPv4 is supported.";
        }
        leaf IPv6PingSupported {
          type boolean;
          config false;
          description
            "Indicates that Ping over IPv6 is supported.";
        }
        leaf IPv4TraceRouteSupported {
          type boolean;
          config false;
          description
            "Indicates that TraceRoute over IPv4 is supported.";
        }
        leaf IPv6TraceRouteSupported {
          type boolean;
          config false;
          description
            "Indicates that TraceRoute over IPv6 is supported.";
        }
        leaf IPv4DownloadDiagnosticsSupported {
          type boolean;
          config false;
          description
            "Indicates that Download Diagnostics over IPv4 is
             supported.";
        }
        leaf IPv6DownloadDiagnosticsSupported {
          type boolean;
          config false;
          description
            "Indicates that Download Diagnostics over IPv6 is
             supported.";
        }
        leaf IPv4UploadDiagnosticsSupported {
          type boolean;
          config false;
          description
            "Indicates that Upload Diagnostics over IPv4 is
             supported.";
        }
        leaf IPv6UploadDiagnosticsSupported {
          type boolean;
          config false;
          description
            "Indicates that Upload Diagnostics over IPv6 is
             supported.";
        }
        leaf IPv4UDPEchoDiagnosticsSupported {
          type boolean;
          config false;
          description
            "Indicates that UDPEcho Diagnostics over IPv4 is
             supported.";
        }
        leaf IPv6UDPEchoDiagnosticsSupported {
          type boolean;
          config false;
          description
            "Indicates that UDPEcho Diagnostics over IPv6 is
             supported.";
        }
        leaf IPv4ServerSelectionDiagnosticsSupported {
          type boolean;
          config false;
          description
            "Indicates that ServerSelection Diagnostics over IPv4 is
             supported.";
        }
        leaf IPv6ServerSelectionDiagnosticsSupported {
          type boolean;
          config false;
          description
            "Indicates that ServerSelection Diagnostics over IPv6 is
             supported.";
        }

        container IPPing {
          description
            "This object provides access to an IP-layer ping test.";
          leaf DiagnosticsState {
            type enumeration {
              enum "None";
              enum "Requested";
              enum "Canceled";
              enum "Complete";
              enum "Error";
              enum "Error_CannotResolveHostName";
              enum "Error_NoRouteToHost";
              enum "Error_Internal";
              enum "Error_Other";
            }
            description
              "{{issue|A10-DIAG|No error state in original version}}
            
               {{datatype|expand}}";
          }
          leaf Interface {
            type string {
              length "0..256";
            }
            description
              "{{reference}} The IP-layer interface over which the
               test is to be performed.  Example:
               Device.IP.Interface.1
            
               If {{empty}} is specified, the CPE MUST use the
               interface as directed by its routing policy
               (''Forwarding'' table entries) to determine the
               appropriate interface.";
          }
          leaf ProtocolVersion {
            type enumeration {
              enum "Any";
              enum "IPv4";
              enum "IPv6";
            }
            description
              "Indicates the IP protocol to be used.";
          }
          leaf Host {
            type string {
              length "0..256";
            }
            description
              "Host name or address of the host to ping.
            
               In the case where {{param}} is specified by name,
               and the name resolves to more than one address, it
               is up to the device implementation to choose which
               address to use.";
          }
          leaf NumberOfRepetitions {
            type uint32 {
              range "1..max";
            }
            description
              "Number of repetitions of the ping test to perform
               before reporting the results.";
          }
          leaf Timeout {
            type uint32 {
              range "1..max";
            }
            description
              "Timeout in {{units}} for the ping test.";
          }
          leaf DataBlockSize {
            type uint32 {
              range "1..65535";
            }
            description
              "Size of the data block in bytes to be sent for each
               ping.";
          }
          leaf DSCP {
            type uint32 {
              range "0..63";
            }
            description
              "DiffServ codepoint to be used for the test packets.
               By default the CPE SHOULD set this value to zero.";
          }
          leaf IPAddressUsed {
            type types:IPAddress;
            config false;
            description
              "Indicates which IP address was used to send the Ping
               request.  The parameter is only valid if the
               {{param|DiagnosticsState}} is
               {{enum|Complete|DiagnosticsState}}.";
          }
          leaf SuccessCount {
            type uint32;
            config false;
            description
              "Result parameter indicating the number of successful
               pings (those in which a successful response was
               received prior to the timeout) in the most recent
               ping test.";
          }
          leaf FailureCount {
            type uint32;
            config false;
            description
              "Result parameter indicating the number of failed
               pings in the most recent ping test.";
          }
          leaf AverageResponseTime {
            type uint32;
            config false;
            description
              "Result parameter indicating the average response time
               in {{units}} over all repetitions with successful
               responses of the most recent ping test.  If there
               were no successful responses, this value MUST be
               zero.";
          }
          leaf MinimumResponseTime {
            type uint32;
            config false;
            description
              "Result parameter indicating the minimum response time
               in {{units}} over all repetitions with successful
               responses of the most recent ping test.  If there
               were no successful responses, this value MUST be
               zero.";
          }
          leaf MaximumResponseTime {
            type uint32;
            config false;
            description
              "Result parameter indicating the maximum response time
               in {{units}} over all repetitions with successful
               responses of the most recent ping test.  If there
               were no successful responses, this value MUST be
               zero.";
          }
          leaf AverageResponseTimeDetailed {
            type uint32;
            config false;
            description
              "Result parameter indicating the average response time
               in {{units}} over all repetitions with successful
               responses of the most recent ping test.  If there
               were no successful responses, this value MUST be
               zero.";
          }
          leaf MinimumResponseTimeDetailed {
            type uint32;
            config false;
            description
              "Result parameter indicating the minimum response time
               in {{units}} over all repetitions with successful
               responses of the most recent ping test.  If there
               were no successful responses, this value MUST be
               zero.";
          }
          leaf MaximumResponseTimeDetailed {
            type uint32;
            config false;
            description
              "Result parameter indicating the maximum response time
               in {{units}} over all repetitions with successful
               responses of the most recent ping test.  If there
               were no successful responses, this value MUST be
               zero.";
          }
        }

        container TraceRoute {
          description
            "This object is defines access to an IP-layer
             trace-route test for the specified IP interface.";
          leaf DiagnosticsState {
            type enumeration {
              enum "None";
              enum "Requested";
              enum "Canceled";
              enum "Complete";
              enum "Error";
              enum "Error_CannotResolveHostName";
              enum "Error_NoRouteToHost";
              enum "Error_MaxHopCountExceeded";
              enum "Error_Internal";
              enum "Error_Other";
            }
            description
              "{{issue|A10-DIAG|No error state in original version}}
            
               {{datatype|expand}}";
          }
          leaf Interface {
            type string {
              length "0..256";
            }
            description
              "{{reference}} The IP-layer interface over which the
               test is to be performed.  Example:
               Device.IP.Interface.1
            
               If {{empty}} is specified, the CPE MUST use the
               interface as directed by its routing policy
               (''Forwarding'' table entries) to determine the
               appropriate interface.";
          }
          leaf ProtocolVersion {
            type enumeration {
              enum "Any";
              enum "IPv4";
              enum "IPv6";
            }
            description
              "Indicates the IP protocol to be used.";
          }
          leaf Host {
            type string {
              length "0..256";
            }
            description
              "Host name or address of the host to find a route to.
            
               In the case where {{param}} is specified by name,
               and the name resolves to more than one address, it
               is up to the device implementation to choose which
               address to use.";
          }
          leaf NumberOfTries {
            type uint32 {
              range "1..3";
            }
            description
              "Number of tries per hop.  Set prior to running
               Diagnostic.  By default, the CPE SHOULD set this
               value to 3.";
          }
          leaf Timeout {
            type uint32 {
              range "1..max";
            }
            description
              "Timeout in {{units}} for each hop of the trace route
               test.  By default the CPE SHOULD set this value to
               5000.";
          }
          leaf DataBlockSize {
            type uint32 {
              range "1..65535";
            }
            description
              "Size of the data block in bytes to be sent for each
               trace route.  By default, the CPE SHOULD set this
               value to 38.";
          }
          leaf DSCP {
            type uint32 {
              range "0..63";
            }
            description
              "DiffServ codepoint to be used for the test packets.
               By default the CPE SHOULD set this value to 0.";
          }
          leaf MaxHopCount {
            type uint32 {
              range "1..64";
            }
            description
              "The maximum number of hop used in outgoing probe
               packets (max TTL).  By default the CPE SHOULD set
               this value to 30.";
          }
          leaf IPAddressUsed {
            type types:IPAddress;
            config false;
            description
              "Indicates which IP address was used for TraceRoute.
               The parameter is only valid if the
               {{param|DiagnosticsState}} is
               {{enum|Complete|DiagnosticsState}}.";
          }
          leaf ResponseTime {
            type uint32;
            config false;
            description
              "Result parameter indicating the response time in
               {{units}} the most recent trace route test.  If a
               route could not be determined, this value MUST be
               zero.";
          }

          list RouteHops {
            config false;
            description
              "Contains the array of hop results returned.  If a
               route could not be determined, this array will be
               empty";
            leaf Host {
              type string {
                length "0..256";
              }
              description
                "Result parameter indicating the Host Name if DNS is
                 able to resolve or IP Address of a hop along the
                 discovered route.";
            }
            leaf HostAddress {
              type string;
              description
                "If this parameter is not {{empty}} it will contain
                 the last IP address of the host returned for
                 this hop and the {{param|Host}} will contain the
                 Host Name returned from the reverse DNS query.";
            }
            leaf ErrorCode {
              type uint32;
              description
                "Contains the error code returned for this hop.
                 This code is directly from the ICMP CODE field.";
            }
            leaf RTTimes {
              type uint32;
              description
                "{{list}} Each list item contains one or more round
                 trip times in {{units}} (one for each
                 repetition) for this hop.
              
                 A list item of 0 indicates that the
                 corresponding response was not received.  Round
                 trip times of less than 1 {{units}} MUST be
                 rounded up to 1.
              
                 The number of list entries is determined by the
                 {{param|#.RouteHopsNumberOfEntries}} parameter.";
            }
          }
        }

        container DownloadDiagnostics {
          description
            "This object defines the diagnostics configuration for a
             HTTP and FTP DownloadDiagnostics Test.
          
             Files received in the DownloadDiagnostics do not
             require file storage on the CPE device.";
          leaf DiagnosticsState {
            type enumeration {
              enum "None";
              enum "Requested";
              enum "Completed";
              enum "Error_CannotResolveHostName";
              enum "Error_NoRouteToHost";
              enum "Error_InitConnectionFailed";
              enum "Error_NoResponse";
              enum "Error_TransferFailed";
              enum "Error_PasswordRequestFailed";
              enum "Error_LoginFailed";
              enum "Error_NoTransferMode";
              enum "Error_NoPASV";
              enum "Error_IncorrectSize";
              enum "Error_Timeout";
              enum "Error_Internal";
              enum "Error_Other";
            }
            description
              "Indicate the availability of diagnostic data.
               {{enum}}
            
               If the ACS sets the value of this parameter to
               {{enum|Requested}}, the CPE MUST initiate the
               corresponding diagnostic test.  When writing, the
               only allowed value is {{enum|Requested}}.  To
               ensure the use of the proper test parameters (the
               writable parameters in this object), the test
               parameters MUST be set either prior to or at the
               same time as (in the same SetParameterValues)
               setting the {{param}} to {{enum|Requested}}.
            
               When requested, the CPE SHOULD wait until after
               completion of the communication session with the
               ACS before starting the diagnostic.
            
               When the test is completed, the value of this
               parameter MUST be either {{enum|Completed}} (if
               the test completed successfully), or one of the
               ''Error'' values listed above.
            
               If the value of this parameter is anything other
               than {{enum|Completed}}, the values of the results
               parameters for this test are indeterminate.
            
               When the diagnostic initiated by the ACS is
               completed (successfully or not), the CPE MUST
               establish a new connection to the ACS to allow the
               ACS to view the results, indicating the Event code
               ''8 DIAGNOSTICS COMPLETE'' in the Inform message.
            
               After the diagnostic is complete, the value of all
               result parameters (all read-only parameters in
               this object) MUST be retained by the CPE until
               either this diagnostic is run again, or the CPE
               reboots.  After a reboot, if the CPE has not
               retained the result parameters from the most
               recent test, it MUST set the value of this
               parameter to {{enum|None}} and remove all object
               instances from {{object|PerConnectionResult}} and
               {{object|IncrementalResult}}.
            
               Modifying any of the writable parameters in this
               object except for this one MUST result in the
               value of this parameter being set to {{enum|None}}
               and remove all object instances from
               {{object|PerConnectionResult}} and
               {{object|IncrementalResult}}.
            
               While the test is in progress, modifying any of
               the writable parameters in this object except for
               this one MUST result in the test being terminated
               and the value of this parameter being set to
               {{enum|None}} and remove all object instances from
               {{object|PerConnectionResult}} and
               {{object|IncrementalResult}}.
            
               While the test is in progress, setting this
               parameter to {{enum|Requested}} (and possibly
               modifying other writable parameters in this
               object) MUST result in the test being terminated
               and then restarted using the current values of the
               test parameters.";
          }
          leaf Interface {
            type string {
              length "0..256";
            }
            description
              "{{reference}} The IP-layer interface over which the
               test is to be performed.  Example:
               Device.IP.Interface.1
            
               If {{empty}} is specified, the CPE MUST use the
               interface as directed by its routing policy
               (''Forwarding'' table entries) to determine the
               appropriate interface.";
          }
          leaf DownloadURL {
            type string {
              length "0..256";
            }
            description
              "The URL, as defined in {{bibref|RFC3986}}, for the
               CPE to perform the download on.  This parameter
               MUST be in the form of a valid HTTP
               {{bibref|RFC2616}} or FTP {{bibref|RFC959}} URL.
            
               * When using FTP transport, FTP binary transfer
               MUST be used.
            
               * When using HTTP transport, persistent
               connections MUST be used and pipelining MUST NOT
               be used.
            
               * When using HTTP transport the HTTP
               Authentication MUST NOT be used.
            
               Note: For time based tests
               ({{param|TimeBasedTestDuration}} > 0) the ACS MAY
               add a hint to duration of the test to the URL.
               See {{bibref|TR-143a1|Section 4.3}} for more
               details.";
          }
          leaf DownloadTransports {
            type enumeration {
              enum "HTTP";
              enum "FTP";
            }
            config false;
            description
              "Supported ''DownloadDiagnostics'' transport protocols
               for a CPE device.";
          }
          leaf DownloadDiagnosticMaxConnections {
            type uint32 {
              range "1..max";
            }
            config false;
            description
              "Indicates the maximum number of connections that are
               supported by Download Diagnostics.";
          }
          leaf DownloadDiagnosticsMaxIncrementalResult {
            type uint32 {
              range "1..max";
            }
            config false;
            description
              "The maximum number of rows in
               {{object|IncrementalResult}} that the CPE will
               store.";
          }
          leaf DSCP {
            type uint32 {
              range "0..63";
            }
            description
              "The DiffServ code point for marking packets
               transmitted in the test.
            
               The default value SHOULD be zero.";
          }
          leaf EthernetPriority {
            type uint32 {
              range "0..7";
            }
            description
              "Ethernet priority code for marking packets
               transmitted in the test (if applicable).
            
               The default value SHOULD be zero.";
          }
          leaf TimeBasedTestDuration {
            type uint32 {
              range "0..999";
            }
            description
              "Controls time based testing {{bibref|TR-143a1|Section
               4.3}}.  When {{param}} > 0, {{param}} is the
               duration in {{units}} of a time based test.  If
               {{param}} is 0, the test is not based on time, but
               on the size of the file to be downloaded.  The
               default value SHOULD be 0.";
          }
          leaf TimeBasedTestMeasurementInterval {
            type uint32 {
              range "0..999";
            }
            description
              "The measurement interval duration in {{units}} for
               objects in {{object|IncrementalResult}} for a time
               based FTP/HTTP download test (when
               {{param|TimeBasedTestDuration}} > 0).  The default
               value SHOULD be 0, which implies
               {{object|IncrementalResult}} collection is
               disabled.
            
               For example if {{param|TimeBasedTestDuration}} is
               90 seconds and {{param}} is 10 {{units}}, there
               will be 9 results in {{object|IncrementalResult}},
               each with a 10 {{units}} duration.";
          }
          leaf TimeBasedTestMeasurementOffset {
            type uint32 {
              range "0..255";
            }
            description
              "This {{param}} works in conjunction with
               {{param|TimeBasedTestMeasurementInterval}} to
               allow the interval measurement to start a number
               of {{units}} after {{param|BOMTime}}.  The test
               measurement interval in
               {{object|IncrementalResult}} starts at time
               {{param|BOMTime}} + {{param}} to allow for slow
               start window removal of file transfers.
            
               This {{param}} is in {{units}}.  The default value
               SHOULD be 0.";
          }
          leaf ProtocolVersion {
            type enumeration {
              enum "Any";
              enum "IPv4";
              enum "IPv6";
            }
            description
              "Indicates the IP protocol version to be used.  The
               default value SHOULD be {{enum|Any}}.";
          }
          leaf NumberOfConnections {
            type uint32 {
              range "1..max";
            }
            description
              "The number of connections to be used in the test.
               The default value SHOULD be 1.  {{param}} MUST NOT
               be set to a value greater than
               {{param|DownloadDiagnosticMaxConnections}}.";
          }
          leaf IPAddressUsed {
            type types:IPAddress;
            config false;
            description
              "Indicates which IP address was used to send the
               request.";
          }
          leaf ROMTime {
            type yang:date-and-time;
            config false;
            description
              "Request time in UTC, which MUST be specified to
               microsecond precision.
            
               For example: 2008-04-09T15:01:05.123456Z
            
               * For HTTP this is the time at which the client
               sends the GET command.
            
               * For FTP this is the time at which the client
               sends the RTRV command.
            
               If multiple connections are used, then {{param}}
               is set to the earliest {{param}} across all
               connections.";
          }
          leaf BOMTime {
            type yang:date-and-time;
            config false;
            description
              "Begin of transmission time in UTC, which MUST be
               specified to microsecond precision
            
               For example: 2008-04-09T15:01:05.123456Z
            
               * For HTTP this is the time at which the first
               data packet is received.
            
               * For FTP this is the time at which the client
               receives the first data packet on the data
               connection.
            
               If multiple connections are used, then {{param}}
               is set to the earliest {{param}} across all
               connections.";
          }
          leaf EOMTime {
            type yang:date-and-time;
            config false;
            description
              "End of transmission in UTC, which MUST be specified
               to microsecond precision.
            
               For example: 2008-04-09T15:01:05.123456Z
            
               * For HTTP this is the time at which the last data
               packet is received.
            
               * For FTP this is the time at which the client
               receives the last packet on the data connection.
            
               If multiple connections are used, then {{param}}
               is set to the latest {{param}} across all
               connections.";
          }
          leaf TestBytesReceived {
            type uint32;
            config false;
            description
              "The number of {{units}} received during the FTP/HTTP
               transaction including FTP/HTTP headers, between
               {{param|BOMTime}} and {{param|EOMTime}} across all
               connections.";
          }
          leaf TotalBytesReceived {
            type uint32;
            config false;
            description
              "The total number of {{units}} (at the IP layer)
               received on the Interface between
               {{param|BOMTime}} and {{param|EOMTime}}.  This MAY
               be calculated by sampling Stats.bytesReceived on
               the {{param|Interface}} object at
               {{param|BOMTime}} and at {{param|EOMTime}} and
               subtracting.";
          }
          leaf TotalBytesSent {
            type uint32;
            config false;
            description
              "The total number of {{units}} (at the IP layer) sent
               on the Interface between {{param|BOMTime}} and
               {{param|EOMTime}}.  This MAY be calculated by
               sampling Stats.bytesSent on the
               {{param|Interface}} object at {{param|BOMTime}}
               and at {{param|EOMTime}} and subtracting.";
          }
          leaf TestBytesReceivedUnderFullLoading {
            type uint32;
            config false;
            description
              "The number of {{units}} of the test file received
               between the latest
               {{param|PerConnectionResult.{i}.BOMTime}} and the
               earliest {{param|PerConnectionResult.{i}.EOMTime}}
               across all connections.";
          }
          leaf TotalBytesReceivedUnderFullLoading {
            type uint32;
            config false;
            description
              "The total number of {{units}} (at the IP layer)
               received in between the latest
               {{param|PerConnectionResult.{i}.BOMTime}} and the
               earliest
               {{param|PerConnectionResult.{i}.EOMTime}}.  This
               MAY be calculated by sampling Stats.bytesReceived
               on the {{param|Interface}} object at the latest
               {{param|PerConnectionResult.{i}.BOMTime}} and at
               the earliest
               {{param|PerConnectionResult.{i}.EOMTime}} and
               subtracting.";
          }
          leaf TotalBytesSentUnderFullLoading {
            type uint32;
            config false;
            description
              "The total number of {{units}} (at the IP layer) sent
               between the latest
               {{param|PerConnectionResult.{i}.BOMTime}} and the
               earliest
               {{param|PerConnectionResult.{i}.EOMTime}}.  This
               MAY be calculated by sampling Stats.bytesSent on
               the {{param|Interface}} object at the latest
               {{param|PerConnectionResult.{i}.BOMTime}} and at
               the earliest
               {{param|PerConnectionResult.{i}.EOMTime}} and
               subtracting.";
          }
          leaf PeriodOfFullLoading {
            type uint32;
            config false;
            description
              "The period of time in {{units}} between the latest
               {{param|PerConnectionResult.{i}.BOMTime}} and the
               earliest {{param|PerConnectionResult.{i}.EOMTime}}
               of the test.";
          }
          leaf TCPOpenRequestTime {
            type yang:date-and-time;
            config false;
            description
              "Request time in UTC, which MUST be specified to
               microsecond precision.
            
               For example: 2008-04-09T15:01:05.123456Z
            
               * For HTTP this is the time at which the TCP
               socket open (SYN) was sent for the HTTP
               connection.
            
               * For FTP this is the time at which the TCP socket
               open (SYN) was sent for the data connection.
            
               Note: Interval of 1 microsecond SHOULD be
               supported.
            
               If multiple connections are used, then {{param}}
               is set to the latest {{param}} across all
               connections.";
          }
          leaf TCPOpenResponseTime {
            type yang:date-and-time;
            config false;
            description
              "Response time in UTC, which MUST be specified to
               microsecond precision.
            
               For example: 2008-04-09T15:01:05.123456Z
            
               * For HTTP this is the time at which the TCP ACK
               to the socket opening the HTTP connection was
               received.
            
               * For FTP this is the time at which the TCP ACK to
               the socket opening the data connection was
               received.
            
               Note: Interval of 1 microsecond SHOULD be
               supported.
            
               If multiple connections are used, then {{param}}
               is set to the latest {{param}} across all
               connections.";
          }
          leaf EnablePerConnectionResults {
            type boolean;
            description
              "The results must be returned in the
               {{object|PerConnectionResult}} table for every
               connection when set to {{true}}.  The default
               value SHOULD be {{false}}.";
          }

          list PerConnectionResult {
            config false;
            description
              "Results for individual connections.  This table is
               only populated when
               {{param|#.EnablePerConnectionResults}} is
               {{true}}.  A new object is created for each
               connection specified in
               {{param|#.NumberOfConnections}}.  Instance numbers
               MUST start at 1 and sequentially increment as new
               instances are created.  All instances are removed
               when {{param|#.DiagnosticsState}} is set to
               {{enum|Requested|#.DiagnosticsState}} or
               {{enum|None|#.DiagnosticsState}}.";
            leaf ROMTime {
              type yang:date-and-time;
              description
                "Request time in UTC, which MUST be specified to
                 microsecond precision.
              
                 For example: 2008-04-09T15:01:05.123456Z
              
                 * For HTTP this is the time at which the client
                 sends the GET command.
              
                 * For FTP this is the time at which the client
                 sends the RTRV command.";
            }
            leaf BOMTime {
              type yang:date-and-time;
              description
                "Begin of transmission time in UTC, which MUST be
                 specified to microsecond precision
              
                 For example: 2008-04-09T15:01:05.123456Z
              
                 * For HTTP this is the time at which the first
                 data packet is received.
              
                 * For FTP this is the time at which the client
                 receives the first data packet on the data
                 connection.";
            }
            leaf EOMTime {
              type yang:date-and-time;
              description
                "End of transmission in UTC, which MUST be specified
                 to microsecond precision.
              
                 For example: 2008-04-09T15:01:05.123456Z
              
                 * For HTTP this is the time at which the last
                 data packet is received.
              
                 * For FTP this is the time at which the client
                 receives the last packet on the data connection.";
            }
            leaf TestBytesReceived {
              type uint32;
              description
                "The number of {{units}} of the test file received
                 during the FTP/HTTP transaction including
                 FTP/HTTP headers, between {{param|BOMTime}} and
                 {{param|EOMTime}}.";
            }
            leaf TotalBytesReceived {
              type uint32;
              description
                "The total number of {{units}} (at the IP layer)
                 received on the Interface between
                 {{param|BOMTime}} and {{param|EOMTime}}.  This
                 MAY be calculated by sampling
                 Stats.bytesReceived on the {{param|#.Interface}}
                 object at {{param|BOMTime}} and at
                 {{param|EOMTime}} and subtracting.";
            }
            leaf TotalBytesSent {
              type uint32;
              description
                "The total number of {{units}} (at the IP layer)
                 sent on the Interface between {{param|BOMTime}}
                 and {{param|EOMTime}}.  This MAY be calculated
                 by sampling Stats.bytesSent on the
                 {{param|#.Interface}} object at
                 {{param|BOMTime}} and at {{param|EOMTime}} and
                 subtracting.";
            }
            leaf TCPOpenRequestTime {
              type yang:date-and-time;
              description
                "Request time in UTC, which MUST be specified to
                 microsecond precision.
              
                 For example: 2008-04-09T15:01:05.123456Z
              
                 * For HTTP this is the time at which the TCP
                 socket open (SYN) was sent for the HTTP
                 connection.
              
                 * For FTP this is the time at which the TCP
                 socket open (SYN) was sent for the data
                 connection.";
            }
            leaf TCPOpenResponseTime {
              type yang:date-and-time;
              description
                "Response time in UTC, which MUST be specified to
                 microsecond precision.
              
                 For example: 2008-04-09T15:01:05.123456Z
              
                 * For HTTP this is the time at which the TCP ACK
                 to the socket opening the HTTP connection was
                 received.
              
                 * For FTP this is the time at which the TCP ACK
                 to the socket opening the data connection was
                 received.";
            }
          }

          list IncrementalResult {
            config false;
            description
              "Results for time segmented tests (tests where
               {{param|#.TimeBasedTestDuration}} > 0 and
               {{param|#.TimeBasedTestMeasurementInterval}} > 0).
               This data is totaled across all connections in the
               test.  A new object is created every
               {{param|#.TimeBasedTestMeasurementInterval}} after
               that interval has completed.  Instance numbers
               MUST start at 1 and sequentially increment as new
               instances are created.  All instances are removed
               when {{param|#.DiagnosticsState}} is set to
               {{enum|Requested|#.DiagnosticsState}} or
               {{enum|None|#.DiagnosticsState}}.";
            leaf TestBytesReceived {
              type uint32;
              description
                "Change in the value of
                 {{param|#.TestBytesReceivedUnderFullLoading}}
                 between {{param|StartTime}} and
                 {{param|EndTime}}.";
            }
            leaf TotalBytesReceived {
              type uint32;
              description
                "The total number of {{units}} (at the IP layer)
                 received on the Interface between
                 {{param|StartTime}} and {{param|EndTime}}.  This
                 MAY be calculated by sampling
                 Stats.bytesReceived on the {{param|#.Interface}}
                 object at {{param|StartTime}} and at
                 {{param|EndTime}} and subtracting.";
            }
            leaf TotalBytesSent {
              type uint32;
              description
                "The total number of {{units}} (at the IP layer)
                 sent on the Interface between
                 {{param|StartTime}} and {{param|EndTime}}.  This
                 MAY be calculated by sampling Stats.bytesSent on
                 the {{param|#.Interface}} object at
                 {{param|StartTime}} and at {{param|EndTime}} and
                 subtracting.";
            }
            leaf StartTime {
              type yang:date-and-time;
              description
                "The start time of this interval which MUST be
                 specified to microsecond precision.
              
                 For example: 2008-04-09T15:01:05.123456Z";
            }
            leaf EndTime {
              type yang:date-and-time;
              description
                "The end time of this interval which MUST be
                 specified to microsecond precision.
              
                 For example: 2008-04-09T15:01:05.123456Z";
            }
          }
        }

        container UploadDiagnostics {
          description
            "This object defines the diagnostics configuration for a
             HTTP or FTP UploadDiagnostics test.
          
             Files sent by the UploadDiagnostics do not require
             file storage on the CPE device, and MAY be an
             arbitrary stream of bytes.";
          leaf DiagnosticsState {
            type enumeration {
              enum "None";
              enum "Requested";
              enum "Completed";
              enum "Error_CannotResolveHostName";
              enum "Error_NoRouteToHost";
              enum "Error_InitConnectionFailed";
              enum "Error_NoResponse";
              enum "Error_PasswordRequestFailed";
              enum "Error_LoginFailed";
              enum "Error_NoTransferMode";
              enum "Error_NoPASV";
              enum "Error_NoCWD";
              enum "Error_NoSTOR";
              enum "Error_NoTransferComplete";
              enum "Error_Timeout";
              enum "Error_Internal";
              enum "Error_Other";
            }
            description
              "Indicate the availability of diagnostic data.
               {{enum}}
            
               If the ACS sets the value of this parameter to
               {{enum|Requested}}, the CPE MUST initiate the
               corresponding diagnostic test.  When writing, the
               only allowed value is {{enum|Requested}}.  To
               ensure the use of the proper test parameters (the
               writable parameters in this object), the test
               parameters MUST be set either prior to or at the
               same time as (in the same SetParameterValues)
               setting the {{param}} to {{enum|Requested}}.
            
               When requested, the CPE SHOULD wait until after
               completion of the communication session with the
               ACS before starting the diagnostic.
            
               When the test is completed, the value of this
               parameter MUST be either {{enum|Completed}} (if
               the test completed successfully), or one of the
               ''Error'' values listed above.
            
               If the value of this parameter is anything other
               than {{enum|Completed}}, the values of the results
               parameters for this test are indeterminate.
            
               When the diagnostic initiated by the ACS is
               completed (successfully or not), the CPE MUST
               establish a new connection to the ACS to allow the
               ACS to view the results, indicating the Event code
               ''8 DIAGNOSTICS COMPLETE'' in the Inform message.
            
               After the diagnostic is complete, the value of all
               result parameters (all read-only parameters in
               this object) MUST be retained by the CPE until
               either this diagnostic is run again, or the CPE
               reboots.  After a reboot, if the CPE has not
               retained the result parameters from the most
               recent test, it MUST set the value of this
               parameter to {{enum|None}} and remove all object
               instances from {{object||PerConnectionResult}} and
               {{object|IncrementalResult}}.
            
               Modifying any of the writable parameters in this
               object except for this one MUST result in the
               value of this parameter being set to {{enum|None}}
               and remove all object instances from
               {{object|PerConnectionResult}} and
               {{object|IncrementalResult}}.
            
               While the test is in progress, modifying any of
               the writable parameters in this object except for
               this one MUST result in the test being terminated
               and the value of this parameter being set to
               {{enum|None}} and remove all object instances from
               {{object|PerConnectionResult}} and
               {{object|IncrementalResult}}.
            
               While the test is in progress, setting this
               parameter to {{enum|Requested}} (and possibly
               modifying other writable parameters in this
               object) MUST result in the test being terminated
               and then restarted using the current values of the
               test parameters.";
          }
          leaf Interface {
            type string {
              length "0..256";
            }
            description
              "{{reference}} The IP-layer interface over which the
               test is to be performed.  Example:
               Device.IP.Interface.1
            
               If {{empty}} is specified, the CPE MUST use the
               interface as directed by its routing policy
               (''Forwarding'' table entries) to determine the
               appropriate interface.";
          }
          leaf UploadURL {
            type string {
              length "0..256";
            }
            description
              "The URL, as defined in {{bibref|RFC3986}}, for the
               CPE to Upload to.  This parameter MUST be in the
               form of a valid HTTP {{bibref|RFC2616}} or FTP
               {{bibref|RFC959}} URL.
            
               * When using FTP transport, FTP binary transfer
               MUST be used.
            
               * When using HTTP transport, persistent
               connections MUST be used and pipelining MUST NOT
               be used.
            
               * When using HTTP transport the HTTP
               Authentication MUST NOT be used.";
          }
          leaf UploadTransports {
            type enumeration {
              enum "HTTP";
              enum "FTP";
            }
            config false;
            description
              "Supported ''UploadDiagnostics'' transport protocols
               for a CPE device.";
          }
          leaf UploadDiagnosticsMaxConnections {
            type uint32 {
              range "1..max";
            }
            config false;
            description
              "Indicates the maximum number of connections that are
               supported by Upload Diagnostics.";
          }
          leaf UploadDiagnosticsMaxIncrementalResult {
            type uint32 {
              range "1..max";
            }
            config false;
            description
              "The maximum number of rows in
               {{object|IncrementalResult}} that the CPE will
               store.";
          }
          leaf DSCP {
            type uint32 {
              range "0..63";
            }
            description
              "DiffServ code point for marking packets transmitted
               in the test.
            
               The default value SHOULD be zero.";
          }
          leaf EthernetPriority {
            type uint32 {
              range "0..7";
            }
            description
              "Ethernet priority code for marking packets
               transmitted in the test (if applicable).
            
               The default value SHOULD be zero.";
          }
          leaf TestFileLength {
            type uint32;
            description
              "The size of the file (in bytes) to be uploaded to the
               server.
            
               The CPE MUST insure the appropriate number of
               bytes are sent.";
          }
          leaf TimeBasedTestDuration {
            type uint32 {
              range "0..999";
            }
            description
              "Controls time based testing {{bibref|TR-143a1|Section
               4.3}}.  When {{param}} > 0, {{param}} is the
               duration in {{units}} of a time based test.  If
               {{param}} is 0, the test is not based on time, but
               on the size of the file to be uploaded.  The
               default value SHOULD be 0.";
          }
          leaf TimeBasedTestMeasurementInterval {
            type uint32 {
              range "0..999";
            }
            description
              "The measurement interval duration in {{units}} for
               objects in {{object|IncrementalResult}} for a time
               based FTP/HTTP upload test (when
               {{param|TimeBasedTestDuration}} > 0).  The default
               value SHOULD be 0, which implies
               {{object|IncrementalResult}} collection is
               disabled.
            
               For example if {{param|TimeBasedTestDuration}} is
               90 seconds and {{param}} is 10 {{units}}, there
               will be 9 results in {{object|IncrementalResult}},
               each with a 10 {{units}} duration.";
          }
          leaf TimeBasedTestMeasurementOffset {
            type uint32 {
              range "0..255";
            }
            description
              "This {{param}} works in conjunction with
               {{param|TimeBasedTestMeasurementInterval}} and
               allows the interval measurement to start a number
               of {{units}} after {{param|BOMTime}}.  The test
               measurement interval in
               {{object|IncrementalResult}} starts at time
               {{param|BOMTime}} + {{param}} to allow for slow
               start window removal of file transfers.
            
               This {{param}} is in {{units}}.  The default value
               SHOULD be 0.";
          }
          leaf ProtocolVersion {
            type enumeration {
              enum "Any";
              enum "IPv4";
              enum "IPv6";
            }
            description
              "Indicates the IP protocol version to be used.  The
               default value SHOULD be {{enum|Any}}.";
          }
          leaf NumberOfConnections {
            type uint32 {
              range "1..max";
            }
            description
              "The number of connections to be used in the test.
               The default value SHOULD be 1.  {{param}} MUST NOT
               be set to a value greater than
               {{param|UploadDiagnosticsMaxConnections}}.";
          }
          leaf IPAddressUsed {
            type types:IPAddress;
            config false;
            description
              "Indicates which IP address was used to send the
               request.";
          }
          leaf ROMTime {
            type yang:date-and-time;
            config false;
            description
              "Request time in UTC, which MUST be specified to
               microsecond precision.
            
               For example: 2008-04-09T15:01:05.123456Z
            
               * For HTTP this is the time at which the client
               sends the GET command.
            
               * For FTP this is the time at which the client
               sends the RTRV command.
            
               If multiple connections are used, then {{param}}
               is set to the earliest {{param}} across all
               connections.";
          }
          leaf BOMTime {
            type yang:date-and-time;
            config false;
            description
              "Begin of transmission time in UTC, which MUST be
               specified to microsecond precision
            
               For example: 2008-04-09T15:01:05.123456Z
            
               * For HTTP this is the time at which the first
               data packet is received.
            
               * For FTP this is the time at which the client
               receives the first data packet on the data
               connection.
            
               If multiple connections are used, then {{param}}
               is set to the earliest {{param}} across all
               connections.";
          }
          leaf EOMTime {
            type yang:date-and-time;
            config false;
            description
              "End of transmission in UTC, which MUST be specified
               to microsecond precision.
            
               For example: 2008-04-09T15:01:05.123456Z
            
               * For HTTP this is the time at which the last data
               packet is received.
            
               * For FTP this is the time at which the client
               receives the last packet on the data connection.
            
               If multiple connections are used, then {{param}}
               is set to the latest {{param}} across all
               connections.";
          }
          leaf TestBytesSent {
            type uint32;
            config false;
            description
              "The number of {{units}} of the test file sent during
               the FTP/HTTP transaction including FTP/HTTP
               headers, between {{param|BOMTime}} and
               {{param|EOMTime}} acrosss all connections.";
          }
          leaf TotalBytesReceived {
            type uint32;
            config false;
            description
              "The total number of {{units}} (at the IP layer)
               received on the Interface between
               {{param|BOMTime}} and {{param|EOMTime}}.  This MAY
               be calculated by sampling Stats.bytesReceived on
               the {{param|Interface}} object at
               {{param|BOMTime}} and at {{param|EOMTime}} and
               subtracting.";
          }
          leaf TotalBytesSent {
            type uint32;
            config false;
            description
              "The total number of {{units}} (at the IP layer) sent
               on the Interface between {{param|BOMTime}} and
               {{param|EOMTime}}.  This MAY be calculated by
               sampling Stats.bytesSent on the
               {{param|Interface}} object at {{param|BOMTime}}
               and at {{param|EOMTime}} and subtracting.";
          }
          leaf TestBytesSentUnderFullLoading {
            type uint32;
            config false;
            description
              "The number of {{units}} of the test file sent between
               the latest
               {{param|PerConnectionResult.{i}.BOMTime}} and the
               earliest {{param|PerConnectionResult.{i}.EOMTime}}
               across all connections.";
          }
          leaf TotalBytesReceivedUnderFullLoading {
            type uint32;
            config false;
            description
              "The total number of {{units}} (at the IP layer)
               received between the latest
               {{param|PerConnectionResult.{i}.BOMTime}} and the
               earliest {{param|PerConnectionResult.{i}.EOMTime}}
               across all connections in the test.  This MAY be
               calculated by sampling Stats.bytesReceived on the
               {{param|Interface}} object at the latest
               {{param|PerConnectionResult.{i}.BOMTime}} and at
               the earliest
               {{param|PerConnectionResult.{i}.EOMTime}} and
               subtracting.";
          }
          leaf TotalBytesSentUnderFullLoading {
            type uint32;
            config false;
            description
              "The total number of {{units}} (at the IP layer) sent
               between the latest
               {{param|PerConnectionResult.{i}.BOMTime}} and the
               earliest {{param|PerConnectionResult.{i}.EOMTime}}
               across all connections in the test.  This MAY be
               calculated by sampling Stats.bytesSent on the
               {{param|Interface}} object at the latest
               {{param|PerConnectionResult.{i}.BOMTime}} and at
               the earliest
               {{param|PerConnectionResult.{i}.EOMTime}} and
               subtracting.";
          }
          leaf PeriodOfFullLoading {
            type uint32;
            config false;
            description
              "The period of time in {{units}} between the latest
               {{param|PerConnectionResult.{i}.BOMTime}} and the
               earliest {{param|PerConnectionResult.{i}.EOMTime}}
               of the test.";
          }
          leaf TCPOpenRequestTime {
            type yang:date-and-time;
            config false;
            description
              "Request time in UTC, which MUST be specified to
               microsecond precision.
            
               For example: 2008-04-09T15:01:05.123456Z
            
               * For HTTP this is the time at which the TCP
               socket open (SYN) was sent for the HTTP
               connection.
            
               * For FTP this is the time at which the TCP socket
               open (SYN) was sent for the data connection.
            
               Note: Interval of 1 microsecond SHOULD be
               supported.
            
               If multiple connections are used, then {{param}}
               is set to the latest {{param}} across all
               connections.";
          }
          leaf TCPOpenResponseTime {
            type yang:date-and-time;
            config false;
            description
              "Response time in UTC, which MUST be specified to
               microsecond precision.
            
               For example: 2008-04-09T15:01:05.123456Z
            
               * For HTTP this is the time at which the TCP ACK
               to the socket opening the HTTP connection was
               received.
            
               * For FTP this is the time at which the TCP ACK to
               the socket opening the data connection was
               received.
            
               Note: Interval of 1 microsecond SHOULD be
               supported.
            
               If multiple connections are used, then {{param}}
               is set to the latest {{param}} across all
               connections.";
          }
          leaf EnablePerConnectionResults {
            type boolean;
            description
              "The results must be returned in the
               {{object|PerConnectionResult}} table for every
               connection when set to {{true}}.  The default
               value SHOULD be {{false}}.";
          }

          list PerConnectionResult {
            config false;
            description
              "Results for individual connections.  This table is
               only populated when
               {{param|#.EnablePerConnectionResults}} is
               {{true}}.  A new object is created for each
               connection specified in
               {{param|#.NumberOfConnections}}.  Instance numbers
               MUST start at 1 and sequentially increment as new
               instances are created.  All instances are removed
               when {{param|#.DiagnosticsState}} is set to
               {{enum|Requested|#.DiagnosticsState}} or
               {{enum|None|#.DiagnosticsState}}.";
            leaf ROMTime {
              type yang:date-and-time;
              description
                "Request time in UTC, which MUST be specified to
                 microsecond precision.
              
                 For example: 2008-04-09T15:01:05.123456Z
              
                 * For HTTP this is the time at which the client
                 sends the GET command.
              
                 * For FTP this is the time at which the client
                 sends the RTRV command.";
            }
            leaf BOMTime {
              type yang:date-and-time;
              description
                "Begin of transmission time in UTC, which MUST be
                 specified to microsecond precision
              
                 For example: 2008-04-09T15:01:05.123456Z
              
                 * For HTTP this is the time at which the first
                 data packet is received.
              
                 * For FTP this is the time at which the client
                 receives the first data packet on the data
                 connection.";
            }
            leaf EOMTime {
              type yang:date-and-time;
              description
                "End of transmission in UTC, which MUST be specified
                 to microsecond precision.
              
                 For example: 2008-04-09T15:01:05.123456Z
              
                 * For HTTP this is the time at which the last
                 data packet is received.
              
                 * For FTP this is the time at which the client
                 receives the last packet on the data connection.";
            }
            leaf TestBytesSent {
              type uint32;
              description
                "The number of {{units}} of the test file sent
                 during the FTP/HTTP transaction including
                 FTP/HTTP headers, between {{param|BOMTime}} and
                 {{param|EOMTime}}.";
            }
            leaf TotalBytesReceived {
              type uint32;
              description
                "The total number of {{units}} (at the IP layer)
                 received on the Interface between
                 {{param|BOMTime}} and {{param|EOMTime}}.  This
                 MAY be calculated by sampling
                 Stats.bytesReceived on the {{param|#.Interface}}
                 object at {{param|BOMTime}} and at
                 {{param|EOMTime}} and subtracting.";
            }
            leaf TotalBytesSent {
              type uint32;
              description
                "The total number of {{units}} (at the IP layer)
                 sent on the Interface between {{param|BOMTime}}
                 and {{param|EOMTime}}.  This MAY be calculated
                 by sampling Stats.bytesSent on the
                 {{param|#.Interface}} object at
                 {{param|BOMTime}} and at {{param|EOMTime}} and
                 subtracting.";
            }
            leaf TCPOpenRequestTime {
              type yang:date-and-time;
              description
                "Request time in UTC, which MUST be specified to
                 microsecond precision.
              
                 For example: 2008-04-09T15:01:05.123456Z
              
                 * For HTTP this is the time at which the TCP
                 socket open (SYN) was sent for the HTTP
                 connection.
              
                 * For FTP this is the time at which the TCP
                 socket open (SYN) was sent for the data
                 connection.";
            }
            leaf TCPOpenResponseTime {
              type yang:date-and-time;
              description
                "Response time in UTC, which MUST be specified to
                 microsecond precision.
              
                 For example: 2008-04-09T15:01:05.123456Z
              
                 * For HTTP this is the time at which the TCP ACK
                 to the socket opening the HTTP connection was
                 received.
              
                 * For FTP this is the time at which the TCP ACK
                 to the socket opening the data connection was
                 received.";
            }
          }

          list IncrementalResult {
            config false;
            description
              "Results for time segmented tests (tests where
               {{param|#.TimeBasedTestDuration}} > 0 and
               {{param|#.TimeBasedTestMeasurementInterval}} > 0).
               This data is totaled across all connections in the
               test.  A new object is created every
               {{param|#.TimeBasedTestMeasurementInterval}} after
               that interval has completed.  Instance numbers
               MUST start at 1 and sequentially increment as new
               instances are created.  All instances are removed
               when {{param|#.DiagnosticsState}} is set to
               {{enum|Requested|#.DiagnosticsState}} or
               {{enum|None|#.DiagnosticsState}}.";
            leaf TestBytesSent {
              type uint32;
              description
                "Change in the value of {{param|#.TestBytesSent}}
                 between {{param|StartTime}} and
                 {{param|EndTime}}.";
            }
            leaf TotalBytesReceived {
              type uint32;
              description
                "The total number of {{units}} (at the IP layer)
                 received on the Interface between
                 {{param|StartTime}} and {{param|EndTime}}.  This
                 MAY be calculated by sampling
                 Stats.bytesReceived on the {{param|#.Interface}}
                 object at {{param|StartTime}} and at
                 {{param|EndTime}} and subtracting.";
            }
            leaf TotalBytesSent {
              type uint32;
              description
                "The total number of {{units}} (at the IP layer)
                 sent on the Interface between
                 {{param|StartTime}} and {{param|EndTime}}.  This
                 MAY be calculated by sampling Stats.bytesSent on
                 the {{param|#.Interface}} object at
                 {{param|StartTime}} and at {{param|EndTime}} and
                 subtracting.";
            }
            leaf StartTime {
              type yang:date-and-time;
              description
                "The start time of this interval which MUST be
                 specified to microsecond precision.
              
                 For example: 2008-04-09T15:01:05.123456Z";
            }
            leaf EndTime {
              type yang:date-and-time;
              description
                "The end time of this interval which MUST be
                 specified to microsecond precision.
              
                 For example: 2008-04-09T15:01:05.123456Z";
            }
          }
        }

        container UDPEchoConfig {
          description
            "This object allows the CPE to be configured to perform
             the UDP Echo Service defined in {{bibref|RFC862}}
             and UDP Echo Plus Service defined in
             {{bibref|TR-143|Appendix A.1}}.";
          leaf Enable {
            type boolean;
            description
              "MUST be enabled to receive UDP echo.  When enabled
               from a disabled state all related timestamps,
               statistics and UDP Echo Plus counters are cleared.";
          }
          leaf Interface {
            type string {
              length "0..256";
            }
            description
              "{{reference|IP-layer interface over which the CPE
               MUST listen and receive UDP echo requests on}}
            
               The value of this parameter MUST be either a valid
               interface or {{empty}}.  An attempt to set this
               parameter to a different value MUST be rejected as
               an invalid parameter value.
            
               If {{empty}} is specified, the CPE MUST listen and
               receive UDP echo requests on all interfaces.
            
               Note: Interfaces behind a NAT MAY require port
               forwarding rules configured in the Gateway to
               enable receiving the UDP packets.";
          }
          leaf SourceIPAddress {
            type types:IPAddress;
            description
              "The Source IP address of the UDP echo packet.  The
               CPE MUST only respond to a UDP echo from this
               source IP address.";
          }
          leaf UDPPort {
            type uint32;
            description
              "The UDP port on which the UDP server MUST listen and
               respond to UDP echo requests.";
          }
          leaf EchoPlusEnabled {
            type boolean;
            description
              "If {{true}} the CPE will perform necessary packet
               processing for UDP Echo Plus packets.";
          }
          leaf EchoPlusSupported {
            type boolean;
            config false;
            description
              "{{true}} if UDP Echo Plus is supported.";
          }
          leaf PacketsReceived {
            type uint32;
            config false;
            description
              "Incremented upon each valid UDP echo packet received.";
          }
          leaf PacketsResponded {
            type uint32;
            config false;
            description
              "Incremented for each UDP echo response sent.";
          }
          leaf BytesReceived {
            type uint32;
            config false;
            description
              "The number of UDP received bytes including payload
               and UDP header after the UDPEchoConfig is enabled.";
          }
          leaf BytesResponded {
            type uint32;
            config false;
            description
              "The number of UDP responded bytes, including payload
               and UDP header sent after the UDPEchoConfig is
               enabled.";
          }
          leaf TimeFirstPacketReceived {
            type yang:date-and-time;
            config false;
            description
              "Time in UTC, which MUST be specified to microsecond
               precision.
            
               For example: 2008-04-09T15:01:05.123456,
            
               The time that the server receives the first UDP
               echo packet after the UDPEchoConfig is enabled.";
          }
          leaf TimeLastPacketReceived {
            type yang:date-and-time;
            config false;
            description
              "Time in UTC, which MUST be specified to microsecond
               precision.
            
               For example: 2008-04-09T15:01:05.123456
            
               The time that the server receives the most recent
               UDP echo packet.";
          }
        }

        container UDPEchoDiagnostics {
          description
            "This object defines the diagnostics configuration for a
             UDP Echo test {{bibref|TR-143a1|Appendix A.1}}
             defined in {{bibref|RFC862}} or a UDP Echo Plus test
             defined in {{bibref|TR-143a1|Appendix A.1}}.";
          leaf DiagnosticsState {
            type enumeration {
              enum "None";
              enum "Requested";
              enum "Completed";
              enum "Error_CannotResolveHostName";
              enum "Error_Internal";
              enum "Error_Other";
            }
            description
              "Indicate the availability of diagnostic data.
               {{enum}}
            
               If the ACS sets the value of this parameter to
               {{enum|Requested}}, the CPE MUST initiate the
               corresponding diagnostic test.  When writing, the
               only allowed value is {{enum|Requested}}.  To
               ensure the use of the proper test parameters (the
               writable parameters in this object), the test
               parameters MUST be set either prior to or at the
               same time as (in the same SetParameterValues)
               setting the {{param}} to {{enum|Requested}}.
            
               When requested, the CPE SHOULD wait until after
               completion of the communication session with the
               ACS before starting the diagnostic.  When the test
               is completed, the value of this parameter MUST be
               either {{enum|Completed}} (if the test completed
               successfully), or one of the ''Error'' values
               listed above.
            
               If the value of this parameter is anything other
               than {{enum|Completed}}, the values of the results
               parameters for this test are indeterminate.
            
               When the diagnostic initiated by the ACS is
               completed (successfully or not), the CPE MUST
               establish a new connection to the ACS to allow the
               ACS to view the results, indicating the Event code
               ''8 DIAGNOSTICS COMPLETE'' in the Inform message.
            
               After the diagnostic is complete, the value of all
               result parameters (all read-only parameters in
               this object) MUST be retained by the CPE until
               either this diagnostic is run again, or the CPE
               reboots.  After a reboot, if the CPE has not
               retained the result parameters from the most
               recent test, it MUST set the value of this
               parameter to {{enum|None}} and remove all object
               instances from {{object|IndividualPacketResult}}.
            
               Modifying any of the writable parameters in this
               object except for this one MUST result in the
               value of this parameter being set to {{enum|None}}
               and remove all object instances from
               {{object|IndividualPacketResult}}.
            
               While the test is in progress, modifying any of
               the writable parameters in this object except for
               this one MUST result in the test being terminated
               and the value of this parameter being set to
               {{enum|None}} and remove all object instances from
               {{object|IndividualPacketResult}}.
            
               While the test is in progress, setting this
               parameter to {{enum|Requested}} (and possibly
               modifying other writable parameters in this
               object) MUST result in the test being terminated
               and then restarted using the current values of the
               test parameters.";
          }
          leaf Interface {
            type string {
              length "0..256";
            }
            description
              "{{reference|the IP-layer interface over which the
               test is to be performed|ignore}} Example:
               Device.IP.Interface.1
            
               If {{empty}} is specified, the CPE MUST use the
               interface as directed by its routing policy
               (''Forwarding'' table entries) to determine the
               appropriate interface.";
          }
          leaf Host {
            type string {
              length "0..256";
            }
            description
              "Host name or address of the host to perform tests to.";
          }
          leaf Port {
            type uint32 {
              range "1..65535";
            }
            description
              "Port on the host to perform tests to.";
          }
          leaf NumberOfRepetitions {
            type uint32 {
              range "1..max";
            }
            description
              "Number of repetitions of the test to perform before
               reporting the results.  The default value SHOULD
               be 1.";
          }
          leaf Timeout {
            type uint32 {
              range "1..max";
            }
            description
              "Timeout in {{units}} for the test.  That is, the
               amount of time to wait for the return of a packet
               that was sent to the {{param|Host}}.";
          }
          leaf DataBlockSize {
            type uint32 {
              range "1..65535";
            }
            description
              "Size of the data block in {{units}} to be sent for
               each packet.  The default value SHOULD be 24.";
          }
          leaf DSCP {
            type uint32 {
              range "0..63";
            }
            description
              "DiffServ codepoint to be used for the test packets.
               The default value SHOULD be zero.";
          }
          leaf InterTransmissionTime {
            type uint32 {
              range "1..65535";
            }
            description
              "The time in {{units}} between the
               {{param|NumberOfRepetitions}} of packets sent
               during a given test.  The default value SHOULD be
               1000.";
          }
          leaf ProtocolVersion {
            type enumeration {
              enum "Any";
              enum "IPv4";
              enum "IPv6";
            }
            description
              "Indicates the IP protocol version to be used.  The
               default value SHOULD be {{enum|Any}}.";
          }
          leaf IPAddressUsed {
            type types:IPAddress;
            config false;
            description
              "Indicates which IP address was used to send the
               request.";
          }
          leaf SuccessCount {
            type uint32;
            config false;
            description
              "Result parameter indicating the number of successful
               packets (those in which a successful response was
               received prior to the timeout) in the most recent
               test.";
          }
          leaf FailureCount {
            type uint32;
            config false;
            description
              "Result parameter indicating the number of failed
               packets (those in which a successful response was
               not received prior to the timeout) in the most
               recent test.";
          }
          leaf AverageResponseTime {
            type uint32;
            config false;
            description
              "Result parameter indicating the average response time
               in {{units}} over all repetitions with successful
               responses of the most recent test.  If there were
               no successful responses, this value MUST be zero.";
          }
          leaf MinimumResponseTime {
            type uint32;
            config false;
            description
              "Result parameter indicating the minimum response time
               in {{units}} over all repetitions with successful
               responses of the most recent test.  If there were
               no successful responses, this value MUST be zero.";
          }
          leaf MaximumResponseTime {
            type uint32;
            config false;
            description
              "Result parameter indicating the maximum response time
               in {{units}} over all repetitions with successful
               responses of the most recent test.  If there were
               no successful responses, this value MUST be zero.";
          }
          leaf EnableIndividualPacketResults {
            type boolean;
            description
              "The results must be returned in the
               {{object|IndividualPacketResult}} table for every
               repetition of the test when set to {{true}}.  The
               default value SHOULD be {{false}}.";
          }
          leaf UDPEchoDiagnosticsMaxResults {
            type uint32 {
              range "1..max";
            }
            config false;
            description
              "The maximum number of rows in
               {{object|IndividualPacketResult}} that the CPE
               will store.  If a test would create more rows than
               {{param}} only the first {{param}} rows are
               present in {{object|IndividualPacketResult}}.";
          }

          list IndividualPacketResult {
            config false;
            description
              "This object provides the results from individual
               UDPEchoPlus test packets collected during a test
               if {{param|#.EnableIndividualPacketResults}} is
               set to true.  When {{param|#.DiagnosticsState}} is
               set to {{enum|Completed|#.DiagnosticsState}} it
               should contain {{param|#.NumberOfRepetitions}}
               objects.  Instance numbers MUST start at 1 and
               sequentially increment as new instances are
               created.  The instance number should match the
               TestIterationNumber field of the request and
               response packet.  All instances are removed when
               {{param|#.DiagnosticsState}} is set to
               {{enum|Requested|#.DiagnosticsState}} or
               {{enum|None|#.DiagnosticsState}}.";
            leaf PacketSuccess {
              type boolean;
              description
                "Indicates that the response to this UDP Echo Plus
                 packet sent was received by the client.  When
                 this value is {{true}}, then all the remaining
                 parameters in this instance are valid.
                 Otherwise only the values originally set by the
                 CPE client (e.g.  {{param|PacketSendTime}} and
                 {{param|TestGenSN}}) MAY be set to valid values.";
            }
            leaf PacketSendTime {
              type yang:date-and-time;
              description
                "Time the client sent this UDP Echo Plus packet in
                 UTC, which MUST be specified to microsecond
                 precision.
              
                 For example: 2008-04-09T15:01:05.123456Z";
            }
            leaf PacketReceiveTime {
              type yang:date-and-time;
              description
                "Time the client receives the response packet in
                 UTC, which MUST be specified to microsecond
                 precision.
              
                 For example: 2008-04-09T15:01:05.123456Z
              
                 If this response is never received, {{param}}
                 SHOULD be set to the Unknown Time value as
                 specified in {{bibref|TR-106a7|Section 3.2.2}}.";
            }
            leaf TestGenSN {
              type uint32;
              description
                "The TestGenSN field in the UDPEcho Plus packet
                 {{bibref|TR-143a1|Section A.1.4}} sent by the
                 CPE client.";
            }
            leaf TestRespSN {
              type uint32;
              description
                "The TestRespSN field in the response packet
                 {{bibref|TR-143a1|Section A.1.4}} from the UDP
                 Echo Plus server (i.e.  {{param|#.Host}}) for
                 this Echo Plus packet sent by the CPE client.
                 If {{param|PacketSuccess}} is {{false}},
                 {{param}} SHOULD be 0.";
            }
            leaf TestRespRcvTimeStamp {
              type uint32;
              description
                "The TestRespRcvTimeStamp field in the response
                 packet {{bibref|TR-143a1|Section A.1.4}} from
                 the UDP Echo Plus server (i.e.
                 {{param|#.Host}}) to record the reception time
                 of this UDP Echo Plus packet sent from the CPE
                 client.  If {{param|PacketSuccess}} is
                 {{false}}, {{param}} SHOULD be 0.";
            }
            leaf TestRespReplyTimeStamp {
              type uint32;
              description
                "The TestRespReplyTimeStamp field in the response
                 packet {{bibref|TR-143a1|Section A.1.4}} from
                 the UDP Echo Plus server (i.e.
                 {{param|#.Host}}) to record the server reply
                 time of this UDP Echo Plus packet sent from the
                 CPE client.
              
                 That is, the time that the server returned the
                 UDP Echo Plus packet.  If
                 {{param|PacketSuccess}} is {{false}}, {{param}}
                 SHOULD be 0.";
            }
            leaf TestRespReplyFailureCount {
              type uint32;
              description
                "The count value that was set by the UDP Echo Plus
                 server (i.e.  {{param|#.Host}}) to record the
                 number of dropped echo response packets by the
                 server.  This count is incremented if a valid
                 echo request packet is received at a UDP
                 EchoPlus server but for some reason cannot be
                 responded to (e.g.  due to local buffer
                 overflow, CPU utilization, etc...).  If
                 {{param|PacketSuccess}} is {{false}}, {{param}}
                 SHOULD be 0.";
            }
          }
        }

        container ServerSelectionDiagnostics {
          description
            "This object provides access to a diagnostics test that
             performs either an ICMP Ping or UDP Echo ping
             against multiple hosts determining which one has the
             smallest average response time.  There MUST be a
             ping response to the transmitted ping, or timeout,
             before the next ping is sent out.";
          leaf DiagnosticsState {
            type enumeration {
              enum "None";
              enum "Requested";
              enum "Completed";
              enum "Error_CannotResolveHostName";
              enum "Error_Internal";
              enum "Error_Other";
            }
            description
              "Indicates availability of diagnostic data.  {{enum}}
            
               If the ACS sets the value of this parameter to
               {{enum|Requested}}, the CPE MUST initiate the
               corresponding diagnostic test.  When writing, the
               only allowed value is {{enum|Requested}}.  To
               ensure the use of the proper test parameters (the
               writable parameters in this object), the test
               parameters MUST be set either prior to or at the
               same time as (in the same SetParameterValues)
               setting the {{param}} to {{enum|Requested}}.
            
               When requested, the CPE SHOULD wait until after
               completion of the communication session with the
               ACS before starting the diagnostic.
            
               When the test is completed, the value of this
               parameter MUST be either {{enum|Completed}} (if
               the test completed successfully), or one of the
               ''Error'' values listed above.
            
               If the value of this parameter is anything other
               than {{enum|Completed}}, the values of the results
               parameters for this test are indeterminate.
            
               When the diagnostic initiated by the ACS is
               completed (successfully or not), the CPE MUST
               establish a new connection to the ACS to allow the
               ACS to view the results, indicating the Event code
               ''8 DIAGNOSTICS COMPLETE'' in the Inform message.
            
               After the diagnostic is complete, the value of all
               result parameters (all read-only parameters in
               this object) MUST be retained by the CPE until
               either this diagnostic is run again, or the CPE
               reboots.  After a reboot, if the CPE has not
               retained the result parameters from the most
               recent test, it MUST set the value of this
               parameter to {{enum|None}}.
            
               Modifying any of the writable parameters in this
               object except for this one MUST result in the
               value of this parameter being set to
               {{enum|None}}.
            
               While the test is in progress, modifying any of
               the writable parameters in this object except for
               this one MUST result in the test being terminated
               and the value of this parameter being set to
               {{enum|None}}.
            
               While the test is in progress, setting this
               parameter to {{enum|Requested}} (and possibly
               modifying other writable parameters in this
               object) MUST result in the test being terminated
               and then restarted using the current values of the
               test parameters.";
          }
          leaf Interface {
            type string {
              length "0..256";
            }
            description
              "{{reference|the IP-layer interface over which the
               test is to be performed|ignore}} Example:
               Device.IP.Interface.1
            
               If {{empty}} is specified, the CPE MUST use the
               interface as directed by its routing policy
               (''Forwarding'' table entries) to determine the
               appropriate interface.";
          }
          leaf ProtocolVersion {
            type enumeration {
              enum "Any";
              enum "IPv4";
              enum "IPv6";
            }
            default "Any";
            description
              "Indicates the IP protocol version to be used.";
          }
          leaf Protocol {
            type enumeration {
              enum "ICMP";
              enum "UDP Echo";
            }
            description
              "The protocol over which the test is to be performed.";
          }
          leaf HostList {
            type string {
              length "0..256";
            }
            description
              "Each entry is a Host name or address of a host to
               ping.";
          }
          leaf NumberOfRepetitions {
            type uint32 {
              range "1..max";
            }
            description
              "Number of repetitions of the ping test to perform for
               each {{param|HostList}} entry before reporting the
               results.";
          }
          leaf Timeout {
            type uint32 {
              range "1..max";
            }
            description
              "Timeout in {{units}} for each iteration of the ping
               test where the total number of iterations is the
               value of {{param|NumberOfRepetitions}} times the
               number of entities in the {{param|HostList}}
               Parameter.";
          }
          leaf FastestHost {
            type string;
            config false;
            description
              "Result parameter indicating the Host (one of the
               items within the {{param|HostList}} Parameter)
               with the smallest average response time.";
          }
          leaf MinimumResponseTime {
            type uint32;
            config false;
            description
              "Result parameter indicating the minimum response time
               in {{units}} over all repetitions with successful
               responses of the most recent ping test for the
               Host identified in {{param|FastestHost}}.  Success
               is defined by the underlying protocol used.  If
               there were no successful responses across all
               Hosts, this value MUST be zero.";
          }
          leaf AverageResponseTime {
            type uint32;
            config false;
            description
              "Result parameter indicating the average response time
               in {{units}} over all repetitions with successful
               responses of the most recent ping test for the
               Host identified in {{param|FastestHost}}.  Success
               is defined by the underlying protocol used.  If
               there were no successful responses across all
               Hosts, this value MUST be zero.";
          }
          leaf MaximumResponseTime {
            type uint32;
            config false;
            description
              "Result parameter indicating the maximum response time
               in {{units}} over all repetitions with successful
               responses of the most recent ping test for the
               Host identified in {{param|FastestHost}}.  Success
               is defined by the underlying protocol used.  If
               there were no successful responses across all
               Hosts, this value MUST be zero.";
          }
          leaf IPAddressUsed {
            type types:IPAddress;
            config false;
            description
              "Indicates which IP address was used to send the
               request to the host identified in
               {{param|FastestHost}}.";
          }
        }
      }
    }

    container LLDP {
      config false;
      description
        "This object contains Link Layer Discovery Protocol (LLDP)
         {{bibref|802.1AB-2009}} related objects and parameters.";

      container Discovery {
        description
          "This object is used for managing the discovery of LLDP
           devices.
        
           The CPE MAY, but need not, retain some or all of the
           information in this object across reboot.";

        list Device {
          key "ChassisIDSubtype ChassisID";
          description
            "This table contains information about discovered LLDP
             devices.";
          leaf Interface {
            type string;
            description
              "{{reference|the interface via which the LLDP device
               was discovered}}";
          }
          leaf ChassisIDSubtype {
            type uint32 {
              range "min..255";
            }
            description
              "The chassis identifier subtype, which is included in
               the value of the ''LLDPDU's'' Chassis ID TLV (TLV
               Type = 1).  The following subtype values are
               defined:
            
               * ''0'' (Reserved)
            
               * ''1'' (Chassis component)
            
               * ''2'' (Interface alias)
            
               * ''3'' (Port component)
            
               * ''4'' (MAC address)
            
               * ''5'' (Network address)
            
               * ''6'' (Interface name)
            
               * ''7'' (Locally assigned)
            
               * ''8-255'' (Reserved)
            
               Note: It is assumed that this integer might be
               used for HTIP (Home-network Topology Identifying
               Protocol) {{bibref|JJ-300.00}} and
               {{bibref|G.9973}}.  In this case, the Chassis ID
               is set to the representative MAC address (chassis
               ID subtype = 4) for ''HTIP-Ethernet Bridge''.";
          }
          leaf ChassisID {
            type string {
              length "1..255";
            }
            description
              "The chassis identifier, which is included in the
               value of the ''LLDPDU's'' Chassis ID TLV (TLV Type
               = 1).
            
               Note: It is assumed that this string might be used
               for HTIP (Home-network Topology Identifying
               Protocol) {{bibref|JJ-300.00}} and
               {{bibref|G.9973}}.  In this case, the Chassis ID
               is set to the representative MAC address.  If
               ''LLDPDU''s are sent and received from two or more
               LLDP agents of the same ''HTIP-Ethernet Bridge'',
               this value is same in all ''LLDPDU''s.";
          }
          leaf Host {
            type string {
              length "0..256";
            }
            description
              "{{list}}Indicates the full path names of all Host
               table entries, whether active or inactive, that
               correspond to this device.
            
               When the entries are added to or removed from the
               Host tables, the value of this parameter MUST be
               updated accordingly.";
          }

          list Port {
            key "PortIDSubtype PortID";
            description
              "This table contains information about ports on
               discovered LLDP devices.";
            leaf PortIDSubtype {
              type uint32 {
                range "min..255";
              }
              description
                "The port identifier subtype, which is included in
                 the value of the ''LLDPDU's'' Port ID TLV (TLV
                 Type = 2).  The following subtype values are
                 defined:
              
                 * ''0'' (Reserved)
              
                 * ''1'' (Interface alias)
              
                 * ''2'' (Port component)
              
                 * ''3'' (MAC address)
              
                 * ''4'' (Network address)
              
                 * ''5'' (Interface name)
              
                 * ''6'' (Agent circuit ID)
              
                 * ''7'' (Locally assigned)
              
                 * ''8-255'' (Reserved)";
            }
            leaf PortID {
              type string {
                length "1..255";
              }
              description
                "The port identifier, which is included in the value
                 of the ''LLDPDU's'' Port ID TLV (TLV Type = 2).";
            }
            leaf TTL {
              type uint32 {
                range "min..65535";
              }
              description
                "The ''LLDPDU'' lifetime (in {{units}}), which is
                 the value of the latest TimeToLive TLV (TLV Type
                 = 3).
              
                 If this value is 0, it means that the LLDP agent
                 or the MAC service function of the port is
                 stopped.";
            }
            leaf PortDescription {
              type string {
                length "0..255";
              }
              description
                "The port description, which is the value of the
                 latest Port Description TLV (TLV Type = 4), or
                 {{empty}} if no Port Description TLV has been
                 received.
              
                 Note: It is assumed that this string might be
                 used for HTIP (Home-network Topology Identifying
                 Protocol) {{bibref|JJ-300.00}} and
                 {{bibref|G.9973}}.  In this case, the parameter
                 value is likely to be one of the names defined
                 in {{bibref|JJ-300.00|Appendix A (''List of
                 Interface Standard Names'')}}.";
            }
            leaf MACAddressList {
              type types:MACAddress;
              description
                "The device's MAC addresses, which are included in
                 the value of the ''LLDPDU's'' Organizationally
                 Specific TLV (TLV Type = 127), or {{empty}} if
                 no list of MAC addresses has been received.
              
                 The parameter is relevant when there is a LLDP
                 device which has a MAC copy function and has two
                 or more MAC addresses.
              
                 Note: It is assumed that it might be used for
                 HTIP (Home-network Topology Identifying
                 Protocol) {{bibref|JJ-300.00}} and
                 {{bibref|G.9973}}.  In this case, the
                 {{bibref|OUI}} in the third octet is E0271A
                 (''TTC-OUI'') and the organizationally defined
                 subtype in the sixth octet is 3 (''MAC Address
                 List'').";
            }
            leaf LastUpdate {
              type yang:date-and-time;
              description
                "The date and time at which the last LLDPDU was
                 received for this ({{object|#}},{{object}}).";
            }

            container LinkInformation {
              description
                "The port's link information, which is included in
                 the value of the ''LLDPDU's'' Organizationally
                 Specific TLV (TLV Type = 127).
              
                 Note: It is assumed that this object might be
                 used for HTIP (Home-network Topology Identifying
                 Protocol) {{bibref|JJ-300.00}} and
                 {{bibref|G.9973}}.  In this case, the
                 {{bibref|OUI}} in the third octet is E0271A
                 (''TTC-OUI'') and the organizationally defined
                 subtype in the sixth octet is 2 (''Link
                 Information'').";
              leaf InterfaceType {
                type uint32;
                description
                  "The port's interface type, or 0 if no interface
                   type has been received.
                
                   Note: It is assumed that it might be used for
                   HTIP (Home-network Topology Identifying
                   Protocol) {{bibref|JJ-300.00}} and
                   {{bibref|G.9973}}.  In this case, it's an IANA
                   interface type {{bibref|IANAifType}}.
                
                   For example, IANAifType defines the following
                   interface types for wired line (UTP cable),
                   wireless line, power line, and coaxial cable:
                
                   * ''6'' (Wired line)
                
                   * ''71'' (Wireless)
                
                   * ''174'' (PLC)
                
                   * ''236'' (Coaxial cable)";
              }
              leaf MACForwardingTable {
                type types:MACAddress;
                description
                  "The port's MAC forwarding table, or the value is
                   {{empty}} if no forwarding table was supplied.";
              }
            }
          }

          container DeviceInformation {
            description
              "The device information, which is included in the
               value of the ''LLDPDU's'' Organizationally
               Specific TLV (TLV Type = 127).
            
               Note: It is assumed that this object might be used
               for HTIP (Home-network Topology Identifying
               Protocol) {{bibref|JJ-300.00}} and
               {{bibref|G.9973}}.  In this case, this table
               contains the Organizationally Specific TLV (TLV
               Type = 127) of ''LLDPDU'', in which the
               {{bibref|OUI}} in the third octet is E0271A
               (''TTC-OUI'') and the organizationally defined
               subtype in the sixth octet is 1 (''Device
               Information'').";
            leaf DeviceCategory {
              type string;
              description
                "Each list item indicates a device category
                 (e.g.\"AV_TV\" and \"AV_Recorder\"), or the
                 value is {{empty}} if no device categories were
                 provided.
              
                 Note: It is assumed that this list might be used
                 for HTIP (Home-network Topology Identifying
                 Protocol) {{bibref|JJ-300.00}} and
                 {{bibref|G.9973}}.  Standard HTIP device
                 categories are defined in {{bibref|JJ-300.01}}.
                 In this case, the maximum length of the list is
                 127 and of each item is 31, and any non-HTIP
                 device categories SHOULD NOT conflict with
                 standard HTIP device categories.";
            }
            leaf ManufacturerOUI {
              type string {
                length "0..6";
                pattern "";
                pattern "[0-9A-F]{6}";
              }
              description
                "The manufacturer OUI, which is included in the
                 value of the ''LLDPDU's'' Organizationally
                 Specific TLV (TLV Type = 127), or {{empty}} if
                 no manufacturer OUI was provided.
              
                 {{pattern}}";
            }
            leaf ModelName {
              type string {
                length "0..31";
              }
              description
                "The model name, which is included in the value of
                 the ''LLDPDU's'' Organizationally Specific TLV
                 (TLV Type = 127), or {{empty}} if no model name
                 was provided.
              
                 Note: It is assumed that this string might be
                 used for HTIP (Home-network Topology Identifying
                 Protocol) {{bibref|JJ-300.00}} and
                 {{bibref|G.9973}}.";
            }
            leaf ModelNumber {
              type string {
                length "0..31";
              }
              description
                "The model number, which is included in the value of
                 the ''LLDPDU's'' Organizationally Specific TLV
                 (TLV Type = 127), or {{empty}} if no model
                 number was provided.
              
                 Note: It is assumed that this string might be
                 used for HTIP (Home-network Topology Identifying
                 Protocol) {{bibref|JJ-300.00}} and
                 {{bibref|G.9973}}.";
            }

            list VendorSpecific {
              key "OrganizationCode InformationType";
              description
                "The vendor-specific device information, which is
                 included in the value of the ''LLDPDU's''
                 Organizationally Specific TLV (TLV Type = 127).
              
                 {{keys}}
              
                 Note: It is assumed that this object might be
                 used for HTIP (Home-network Topology Identifying
                 Protocol) {{bibref|JJ-300.00}} and
                 {{bibref|G.9973}}.  In this case, this table
                 contains the Organizationally Specific TLV (TLV
                 Type = 127) of ''LLDPDU'', in which the
                 {{bibref|OUI}} in the third octet is E0271A
                 (''TTC-OUI''), the organizationally defined
                 subtype in the sixth octet is 1 (''Device
                 Information''), and the device information ID in
                 the seventh octet is 255 (''Vendor-specific
                 extension field'').";
              leaf OrganizationCode {
                type string {
                  length "6";
                  pattern "[0-9A-F]{6}";
                }
                description
                  "The vendor-specific organization code, which is
                   included in the value of the ''LLDPDU's''
                   Organizationally Specific TLV (TLV Type =
                   127).";
              }
              leaf InformationType {
                type uint32 {
                  range "min..255";
                }
                description
                  "The vendor-specific device information type,
                   which is included in the value of the
                   ''LLDPDU's'' Organizationally Specific TLV
                   (TLV Type = 127).";
              }
              leaf Information {
                type string {
                  length "0..248";
                }
                description
                  "The vendor-specific device information, which is
                   included in the value of the ''LLDPDU's''
                   Organizationally Specific TLV (TLV Type =
                   127).";
              }
            }
          }
        }
      }
    }

    container IPsec {
      description
        "IPsec {{bibref|RFC4301}} object that supports the
         configuration of Encapsulating Security Payload (ESP)
         {{bibref|RFC4303}} and Authentication Header (AH)
         {{bibref|RFC4302}} in tunnel mode
         {{bibref|RFC4301|Section 3.2}}.
      
         Use of IKEv2 {{bibref|RFC5996}} is assumed.  The IPsec
         object does not currently support static configuration
         of tunnels and child Security Associations (SAs).
      
         See the IPsec Theory of Operation
         {{bibref|TR-181i2a5|Appendix IX}} for a description of
         the working of this IPsec data model.";
      leaf Enable {
        type boolean;
        description
          "Enables or disables IPsec.";
      }
      leaf Status {
        type enumeration {
          enum "Disabled";
          enum "Enabled";
          enum "Error";
        }
        config false;
        description
          "IPsec status.  {{enum}}
        
           The {{enum|Error}} value MAY be used by the CPE to
           indicate a locally defined error condition.";
      }
      leaf AHSupported {
        type boolean;
        config false;
        description
          "Indicates whether or not Authentication Header (AH)
           {{bibref|RFC4302}} is supported.";
      }
      leaf IKEv2SupportedEncryptionAlgorithms {
        type enumeration {
          enum "DES";
          enum "3DES";
          enum "RC5";
          enum "IDEA";
          enum "CAST";
          enum "BLOWFISH";
          enum "3IDEA";
          enum "AES-CBC";
          enum "AES-CTR";
          enum "AES-CCM-8";
          enum "AES-CCM-12";
          enum "AES-CCM-16";
          enum "AES-GCM-8";
          enum "AES-GCM-12";
          enum "AES-GCM-16";
          enum "CAMELLIA-CBC";
        }
        config false;
        description
          "Supported IKEv2 encryption algorithms
           {{bibref|IKEv2-params|Transform Type 1}}.  {{enum}}
        
           Note that these are the names from the above
           reference, transformed as follows:
        
           * Leading ''ENCR_'' (when present) discarded because
           they are all encryption algorithms so it's not needed.
        
           * Underscores changed to hyphens to preserve names
           used in existing data models (and because of
           inconsistent conventions).
        
           * Phrases collapsed where unambiguous, e.g.  \"with
           a(n) NN octet ICV\" -> \"-NN\".
        
           As additional algorithms are added to the above
           reference, this data model will be extended according
           to the above conventions.";
      }
      leaf ESPSupportedEncryptionAlgorithms {
        type enumeration {
          enum "NULL";
          enum "DES-IV64";
          enum "DES";
          enum "3DES";
          enum "RC5";
          enum "IDEA";
          enum "CAST";
          enum "BLOWFISH";
          enum "3IDEA";
          enum "DES-IV32";
          enum "AES-CBC";
          enum "AES-CTR";
          enum "AES-CCM-8";
          enum "AES-CCM-12";
          enum "AES-CCM-16";
          enum "AES-GCM-8";
          enum "AES-GCM-12";
          enum "AES-GCM-16";
          enum "NULL-AUTH-AES-GMAC";
          enum "CAMELLIA-CBC";
          enum "CAMELLIA-CTR";
          enum "CAMELLIA-CCM-8";
          enum "CAMELLIA-CCM-12";
          enum "CAMELLIA-CCM-16";
        }
        config false;
        description
          "Supported ESP encryption algorithms
           {{bibref|IKEv2-params|Transform Type 1}}
           {{bibref|RFC4835|Section 3.1.1}}.  {{enum}}
        
           Note that these are the names from the above
           reference, transformed as follows:
        
           * Leading ''ENCR_'' (when present) discarded because
           they are all encryption algorithms so it's not needed.
        
           * Underscores changed to hyphens to preserve names
           used in existing data models (and because of
           inconsistent conventions).
        
           * Phrases collapsed where unambiguous, e.g.  \"with
           a(n) NN octet ICV\" -> \"-NN\".
        
           * Some algorithms with apparently rather specialised
           application are omitted, e.g.
           ''ENCR_NULL_AUTH_AES_GMAC''.
        
           As additional algorithms are added to the above
           reference, this data model will be extended according
           to the above conventions.";
      }
      leaf IKEv2SupportedPseudoRandomFunctions {
        type enumeration {
          enum "HMAC-MD5";
          enum "HMAC-SHA1";
          enum "HMAC-TIGER";
          enum "AES-128-XCBC";
          enum "HMAC-SHA2-256";
          enum "HMAC-SHA2-384";
          enum "HMAC-SHA2-512";
          enum "AES-128-CMAC";
        }
        config false;
        description
          "Supported IKEv2 pseudo-random functions
           {{bibref|IKEv2-params|Transform Type 2}}.  {{enum}}
        
           Note that these are the names from the above
           reference, transformed as follows:
        
           * Leading ''PRF_'' (when present) discarded because
           they all pseudo-random functions so it's not needed.
        
           * Underscores changed to hyphens to preserve names
           used in existing data models.
        
           * Hyphen inserted after ''AES'' (or other acronym)
           when immediately followed by a key length.
        
           As additional functions are added to the above
           reference, this data model will be extended according
           to the above conventions.";
      }
      leaf SupportedIntegrityAlgorithms {
        type enumeration {
          enum "NONE";
          enum "HMAC-MD5-96";
          enum "HMAC-SHA1-96";
          enum "DES-MAC";
          enum "KPDK-MD5";
          enum "AES-XCBC-96";
          enum "HMAC-MD5-128";
          enum "HMAC-SHA1-160";
          enum "AES-CMAC-96";
          enum "AES-128-GMAC";
          enum "AES-192-GMAC";
          enum "AES-256-GMAC";
          enum "HMAC-SHA2-256-128";
          enum "HMAC-SHA2-256-192";
          enum "HMAC-SHA2-256-256";
        }
        config false;
        description
          "Supported integrity algorithms
           {{bibref|IKEv2-params|Transform Type 3}}.  {{enum}}
        
           Note that these are the names from the above
           reference, transformed as follows:
        
           * Leading ''AUTH_'' (when present) discarded because
           they all authentication (integrity) algorithms so it's
           not needed.
        
           * Underscores changed to hyphens to preserve names
           used in existing data models.
        
           As additional algorithms are added to the above
           reference, this data model will be extended according
           to the above conventions.";
      }
      leaf SupportedDiffieHellmanGroupTransforms {
        type enumeration {
          enum "NONE";
          enum "MODP-768";
          enum "MODP-1024";
          enum "MODP-1536";
          enum "MODP-2048";
          enum "MODP-3072";
          enum "MODP-4096";
          enum "MODP-6144";
          enum "MODP-8192";
          enum "ECP-256";
          enum "ECP-384";
          enum "ECP-521";
          enum "MODP-1024-PRIME-160";
          enum "MODP-2048-PRIME-224";
          enum "MODP-2048-PRIME-256";
          enum "ECP-192";
          enum "ECP-224";
        }
        config false;
        description
          "Supported Diffie-Hellman group transforms
           {{bibref|IKEv2-params|Transform Type 4}}.  {{enum}}
        
           Note that these are the names from the above
           reference, transformed as follows:
        
           * Name (other than ''NONE'') always starts with the
           type of group, currently ''MODP'' or ''ECP'' (implies
           ECP random).
        
           * This is followed by ''-NN'', where ''NN'' is the
           group length in bits.
        
           * this is followed by ''-PRIME-NN'' for groups with
           prime order subgroups, where ''NN'' is the subgroup
           length in bits.
        
           As additional algorithms are added to the above
           reference, this data model will be extended according
           to the above conventions.";
      }
      leaf MaxFilterEntries {
        type uint32;
        config false;
        description
          "The maximum number of entries in the {{object|Filter}}
           table.
        
           A value of 0 means no specific limit.";
      }
      leaf MaxProfileEntries {
        type uint32;
        config false;
        description
          "The maximum number of entries in the {{object|Profile}}
           table.
        
           A value of 0 means no specific limit.";
      }

      container Stats {
        config false;
        description
          "Global IPsec statistics.  These statistics include all
           IPsec traffic, i.e.  all IKEv2 negotiation, IKEv2 SAs
           and child SAs.
        
           The CPE MUST reset global IPsec Stats parameters
           (unless otherwise stated in individual object or
           parameter descriptions) either when IPsec is disabled
           ({{param|.IPsec.Enable}} is set to {{false}}) or when
           IPsec is enabled ({{param|.IPsec.Enable}} is set to
           {{true}}).";
        leaf NegotiationFailures {
          type types:StatsCounter32;
          description
            "The total number of times an IPsec negotiation failure
             has occurred.";
        }
        leaf BytesSent {
          type types:StatsCounter64;
          description
            "The total number of {{units}} sent by IPsec.";
        }
        leaf BytesReceived {
          type types:StatsCounter64;
          description
            "The total number of {{units}} received by IPsec.";
        }
        leaf PacketsSent {
          type types:StatsCounter64;
          description
            "The total number of {{units}} sent by IPsec.";
        }
        leaf PacketsReceived {
          type types:StatsCounter64;
          description
            "The total number of {{units}} received by IPsec.";
        }
        leaf ErrorsSent {
          type types:StatsCounter32;
          description
            "The total number of {{units}} discarded by IPsec due to
             any error.  This can include packets dropped due to
             a lack of transmit buffers.";
        }
        leaf UnknownSPIErrors {
          type types:StatsCounter32;
          description
            "The total number of {{units}} discarded by IPsec due to
             an unknown SPI (Security Parameter Index).";
        }
        leaf DecryptionErrors {
          type types:StatsCounter32;
          description
            "The total number of {{units}} discarded by IPsec due to
             ESP decryption errors.";
        }
        leaf IntegrityErrors {
          type types:StatsCounter32;
          description
            "The total number of {{units}} discarded by IPsec due to
             integrity errors.";
        }
        leaf ReplayErrors {
          type types:StatsCounter32;
          description
            "The total number of {{units}} discarded by IPsec due to
             replay errors.";
        }
        leaf PolicyErrors {
          type types:StatsCounter32;
          description
            "The total number of {{units}} discarded by IPsec due to
             policy errors.";
        }
        leaf OtherReceiveErrors {
          type types:StatsCounter32;
          description
            "The total number of {{units}} discarded by IPsec due to
             errors other than unknown SPI, decryption,
             integrity, replay or policy errors.  This can
             include packets dropped due to a lack of receive
             buffers.";
        }
      }

      list Filter {
        key "Alias";
        description
          "Filter table that represents the IPsec Security Policy
           Database (SPD) {{bibref|RFC4301|Section 4.4.1}}
           selection criteria.  Each (ordered) entry defines a
           set of selection criteria and references a
           {{object|#.Profile}} table entry that specifies how
           matching packets will be processed.
        
           SPD filtering is performed for all packets that might
           need to cross the IPsec boundary
           {{bibref|RFC4301|Section 3.1}}.  Given that IPsec
           operates at the IP level, this means that SPD
           filtering conceptually occurs after bridging and
           before routing.
        
           For enabled table entries, if {{param|Interface}} is
           not a valid reference and {{param|AllInterfaces}} is
           {{false}}, then the table entry is inoperable and the
           CPE MUST set {{param|Status}} to
           {{enum|Error_Misconfigured|Status}}.";
        leaf Enable {
          type boolean;
          default "false";
          description
            "Enables or disables this IPsec Filter table entry.";
        }
        leaf Status {
          type enumeration {
            enum "Disabled";
            enum "Enabled";
            enum "Error_Misconfigured";
            enum "Error";
          }
          config false;
          default "Disabled";
          description
            "The status of this IPsec Filter table entry.  {{enum}}
          
             The {{enum|Error_Misconfigured}} value indicates
             that a necessary configuration value is undefined or
             invalid.
          
             The {{enum|Error}} value MAY be used by the CPE to
             indicate a locally defined error condition.";
        }
        leaf Order {
          type uint32 {
            range "1..max";
          }
          description
            "Position of the {{object}} entry in the order of
             precedence.  A value of ''1'' indicates the first
             entry considered (highest precedence).  For each
             packet, the highest ordered entry that matches the
             filter criteria is applied.  All lower order entries
             are ignored.
          
             When this value is modified, if the value matches
             that of an existing entry, the {{param}} value for
             the existing entry and all lower {{param}} entries
             is incremented (lowered in precedence) to ensure
             uniqueness of this value.  A deletion causes
             {{param}} values to be compacted.  When a value is
             changed, incrementing occurs before compaction.
          
             The value of {{param}} on creation of a {{object}}
             table entry MUST be one greater than the largest
             current value (initially assigned the lowest
             precedence).";
        }
        leaf Interface {
          type string {
            length "0..256";
          }
          default "";
          description
            "SPD selection criterion.  {{reference}}
          
             This specifies the ingress interface associated with
             the entry.  It MAY be a layer 1, 2 or 3 interface.
             However, the types of interfaces for which filters
             can be instantiated is a local matter to the CPE.";
        }
        leaf AllInterfaces {
          type boolean;
          default "false";
          description
            "SPD selection criterion.
          
             This specifies that all ingress interfaces are
             associated with the entry.  If {{true}}, the value
             of {{param|Interface}} is ignored since all ingress
             interfaces are indicated.";
        }
        leaf DestIP {
          type types:IPAddress;
          default "";
          description
            "SPD selection criterion.
          
             Destination IP address.  {{empty}} indicates this
             criterion is not used, i.e.  is ''ANY''.";
        }
        leaf DestMask {
          type types:IPAddress;
          default "";
          description
            "SPD selection criterion.
          
             Destination IP address mask.  If not {{empty}}, only
             the indicated network portion of the
             {{param|DestIP}} address is to be used for
             selection.  {{empty}} indicates that the full
             {{param|DestIP}} address is to be used for
             selection.";
        }
        leaf DestIPExclude {
          type boolean;
          default "false";
          description
            "If {{false}}, the rule matches only those packets that
             match the (masked) {{param|DestIP}} entry, if
             specified.
          
             If {{true}}, the rule matches all packets except
             those that match the (masked) {{param|DestIP}}
             entry, if specified.";
        }
        leaf SourceIP {
          type types:IPAddress;
          default "";
          description
            "SPD selection criterion.
          
             Source IP address.  {{empty}} indicates this
             criterion is not used, i.e.  is ''ANY''.";
        }
        leaf SourceMask {
          type types:IPAddress;
          default "";
          description
            "SPD selection criterion.
          
             Source IP address mask.  If not {{empty}}, only the
             indicated network portion of the {{param|SourceIP}}
             address is to be used for selection.  {{empty}}
             indicates that the full {{param|SourceIP}} address
             is to be used for selection.";
        }
        leaf SourceIPExclude {
          type boolean;
          default "false";
          description
            "If {{false}}, the rule matches only those packets that
             match the (masked) {{param|SourceIP}} entry, if
             specified.
          
             If {{true}}, the rule matches all packets except
             those that match the (masked) {{param|SourceIP}}
             entry, if specified.";
        }
        leaf Protocol {
          type int32 {
            range "-1..255";
          }
          default "-1";
          description
            "SPD selection criterion.
          
             Protocol number.  A value of -1 indicates this
             criterion is not used, i.e.  is ''ANY''.
          
             Note that {{bibref|RFC4301}} refers to this as the
             ''Next Layer Protocol''.  It is obtained from the
             IPv4 ''Protocol'' or the IPv6 ''Next Header''
             fields.";
        }
        leaf ProtocolExclude {
          type boolean;
          default "false";
          description
            "If {{false}}, the rule matches only those packets that
             match {{param|Protocol}}, if specified.
          
             If {{true}}, the rule matches all packets except
             those that match {{param|Protocol}}, if specified.";
        }
        leaf DestPort {
          type int32 {
            range "-1..65535";
          }
          default "-1";
          description
            "SPD selection criterion.
          
             Destination port number.  A value of -1 indicates
             this criterion is not used, i.e.  is ''ANY''.
          
             The value of this parameter is ignored for protocols
             that do not use ports, e.g.  ICMP (1).";
        }
        leaf DestPortRangeMax {
          type int32 {
            range "-1..65535";
          }
          default "-1";
          description
            "SPD selection criterion.
          
             If specified, indicates a destination port address
             range from {{param|DestPort}} through {{param}}
             (inclusive), in which case {{param}} MUST be greater
             than or equal to {{param|DestPort}}.
          
             A value of -1 indicates that no destination port
             range is specified.";
        }
        leaf DestPortExclude {
          type boolean;
          default "false";
          description
            "If {{false}}, the rule matches only those packets that
             match {{param|DestPort}} (or port range), if
             specified.
          
             If {{true}}, the rule matches all packets except
             those that match {{param|DestPort}} (or port range),
             if specified.";
        }
        leaf SourcePort {
          type int32 {
            range "-1..65535";
          }
          default "-1";
          description
            "SPD selection criterion.
          
             Source port number.  A value of -1 indicates this
             criterion is not used, i.e.  is ''ANY''.
          
             The value of this parameter is ignored for protocols
             that do not use ports, e.g.  ICMP (1).";
        }
        leaf SourcePortRangeMax {
          type int32 {
            range "-1..65535";
          }
          default "-1";
          description
            "SPD selection criterion.
          
             If specified, indicates a source port address range
             from {{param|SourcePort}} through {{param}}
             (inclusive), in which case {{param}} MUST be greater
             than or equal to {{param|SourcePort}}.
          
             A value of -1 indicates that no source port range is
             specified.";
        }
        leaf SourcePortExclude {
          type boolean;
          default "false";
          description
            "If {{false}}, the rule matches only those packets that
             match {{param|SourcePort}} (or port range), if
             specified.
          
             If {{true}}, the rule matches all packets except
             those that match {{param|SourcePort}} (or port
             range), if specified.";
        }
        leaf ProcessingChoice {
          type enumeration {
            enum "Discard";
            enum "Bypass";
            enum "Protect";
          }
          default "Bypass";
          description
            "Indicates how packets that match this rule will be
             processed {{bibref|RFC4301|Section 4.4.1}}.";
        }
        leaf Profile {
          type string;
          description
            "The profile that defines the IPsec treatment for
             matching packets.  {{reference}}
          
             If {{param|ProcessingChoice}} is
             {{enum|Protect|ProcessingChoice}}, {{param}} MUST
             NOT be {{empty}}.  In this case, if it ever becomes
             {{empty}}, e.g.  because the referenced profile is
             deleted, this IPsec Filter table entry is invalid
             and {{param|Status}} MUST be set to
             {{enum|Error_Misconfigured|Status}}.
          
             If {{param|ProcessingChoice}} is not
             {{enum|Protect|ProcessingChoice}}, {{param}} is
             ignored.
          
             Any changes to the referenced profile will have an
             immediate effect on any established IPsec tunnels.
             Such changes will often force IKEv2 sessions and
             child SAs to be re-established.";
        }
      }

      list Profile {
        key "Alias";
        description
          "Profile table that represents the IPsec Security Policy
           Database (SPD) {{bibref|RFC4301|Section 4.4.1}}
           processing info.  Each entry defines the IPsec
           treatment for packets that match the
           {{object|#.Filter}} entries that reference the entry.";
        leaf MaxChildSAs {
          type uint32;
          description
            "Controls the maximum number of child Security
             Association (SA) pairs that can be negotiated by a
             single IKEv2 session.
          
             If a new child SA pair is needed, but the current
             IKEv2 session already has {{param}} child SA pairs,
             an additional IKEv2 session (and therefore an
             additional IPsec tunnel) will be established.
          
             A value of 0 means no specific limit.
          
             Note that support for more than one child SA pair
             per IKEv2 session is OPTIONAL
             {{bibref|RFC5996|Section 1.3}}.";
        }
        leaf RemoteEndpoints {
          type string {
            length "0..64";
          }
          description
            "The host name or IP address of the remote IPsec tunnel
             endpoint.  If more than one name/address is
             supplied, they will be tried in turn, i.e.  they are
             in decreasing order of precedence.";
        }
        leaf ForwardingPolicy {
          type uint32;
          default "0";
          description
            "Identifier of the forwarding policy associated with
             traffic that is associated with this profile.
          
             The forwarding policy can be referenced by entries
             in the
             {{object|##.Routing.Router.{i}.IPv4Forwarding}} and
             {{object|##.Routing.Router.{i}.IPv6Forwarding}}
             tables, and therefore allows SPD selection criteria
             to influence the forwarding decision.";
        }
        leaf Protocol {
          type enumeration {
            enum "AH";
            enum "ESP";
          }
          default "ESP";
          description
            "The \"child\" security protocol.
          
             This is not to be confused with
             {{object|#.Filter}}.{{param|#.Filter.{i}.Protocol}},
             which is an SPD selector that can select packets
             that already have AH or ESP headers.
             {{object}}.{{param}} selects whether AH or ESP will
             be used when encapsulating a packet.";
        }
        leaf IKEv2AuthenticationMethod {
          type string;
          default "";
          description
            "IKEv2 CPE authentication method
             {{bibref|RFC5996|Section 2.15}}.  {{reference|an
             enabled row in the {{object|.Security.Certificate}}
             table or in another table that contains appropriate
             CPE credentials}}
          
             If {{empty}}, or the referenced row is disabled or
             deleted, the CPE chooses the authentication method
             based on local policy.";
        }
        leaf IKEv2AllowedEncryptionAlgorithms {
          type string;
          description
            "Allowed IKEv2 encryption algorithms.";
        }
        leaf ESPAllowedEncryptionAlgorithms {
          type string;
          description
            "Allowed ESP encryption algorithms.";
        }
        leaf IKEv2AllowedPseudoRandomFunctions {
          type string;
          description
            "Allowed IKEv2 pseudo-random functions.";
        }
        leaf IKEv2AllowedIntegrityAlgorithms {
          type string;
          description
            "Allowed IKEv2 integrity algorithms.";
        }
        leaf AHAllowedIntegrityAlgorithms {
          type string;
          default "";
          description
            "Allowed AH integrity algorithms
             {{bibref|IKEv2-params|Transform Type 3}}
             {{bibref|RFC4835|Section 3.2}}.";
        }
        leaf ESPAllowedIntegrityAlgorithms {
          type string;
          default "";
          description
            "Allowed ESP integrity algorithms
             {{bibref|IKEv2-params|Transform Type 3}}
             {{bibref|RFC4835|Section 3.1.1}}.";
        }
        leaf IKEv2AllowedDiffieHellmanGroupTransforms {
          type string;
          description
            "Allowed IKEv2 Diffie-Hellman group transforms.";
        }
        leaf IKEv2DeadPeerDetectionTimeout {
          type uint32;
          description
            "IKEv2 Dead Peer Detection (DPD) timeout in {{units}}.
             {{bibref|RFC5996|section 2.4}}";
        }
        leaf IKEv2NATTKeepaliveTimeout {
          type uint32;
          description
            "IKEv2 NAT traversal (NAT-T) keepalive timeout in
             {{units}}.  {{bibref|RFC3948|Section 4}}";
        }
        leaf AntiReplayWindowSize {
          type uint32;
          default "0";
          description
            "The size of the AH or ESP Anti-Replay Window.
             {{bibref|RFC4302|Section B.2}}
             {{bibref|RFC4303|Section A2}}
          
             A value of 0 means that Sequence Number Verification
             is disabled.";
        }
        leaf DoNotFragment {
          type enumeration {
            enum "Set";
            enum "Clear";
            enum "Copy";
          }
          description
            "Controls the value of the ''Do Not Fragment'' (DF) bit.
             {{bibref|RFC4301|Section 8.1}}";
        }
        leaf DSCPMarkPolicy {
          type int32 {
            range "-2..63";
          }
          description
            "DSCP with which to mark the outer IP header for traffic
             that is associated with this IPsec channel.
          
             A value of -1 indicates copy from the incoming
             packet.
          
             A value of -2 indicates automatic marking of DSCP.
          
             De-tunneled packets are never re-marked.
          
             Automatic DSCP marking behavior is a local matter to
             the CPE, possibly influenced by other Broadband
             Forum standards that it supports.";
        }
        leaf IKEv2SATrafficLimit {
          type uint64;
          description
            "IKEv2 SA lifetime in {{units}}, or zero if there is no
             traffic constraint on its expiration.
          
             If both {{param}} and {{param|IKEv2SATimeLimit}} are
             non-zero, the IKEv2 SA is deleted when the first
             limit is reached.";
        }
        leaf IKEv2SATimeLimit {
          type uint32;
          description
            "IKEv2 SA lifetime in {{units}}, or zero if there is no
             time constraint on its expiration.
          
             If both {{param}} and {{param|IKEv2SATrafficLimit}}
             are non-zero, the IKEv2 SA is deleted when the first
             limit is reached.";
        }
        leaf IKEv2SAExpiryAction {
          type enumeration {
            enum "Renegotiate";
            enum "Delete";
          }
          description
            "Action to take when an IKEv2 SA expires, whether as a
             result of hitting a traffic limit or a time limit.";
        }
        leaf ChildSATrafficLimit {
          type uint64;
          description
            "Child SA lifetime in {{units}}, or zero if there is no
             traffic constraint on its expiration.
          
             If both {{param}} and {{param|ChildSATimeLimit}} are
             non-zero, the child SA is deleted when the first
             limit is reached.";
        }
        leaf ChildSATimeLimit {
          type uint32;
          description
            "Child SA lifetime in {{units}}, or zero if there is no
             time constraint on its expiration.
          
             If both {{param}} and {{param|ChildSATrafficLimit}}
             are non-zero, the child SA is deleted when the first
             limit is reached.";
        }
        leaf ChildSAExpiryAction {
          type enumeration {
            enum "Renegotiate";
            enum "Delete";
          }
          description
            "Action to take when a Child SA expires, whether as a
             result of hitting a traffic limit or a time limit.";
        }

        list SentCPAttr {
          key "Type";
          description
            "Each instance of this object represents an IKEv2
             Configuration Payload (CP) {{bibref|RFC5996|Section
             3.15}} Attribute that MUST, if enabled, be sent in
             IKEv2 CP CFG_REQUEST messages.  All such Attributes
             MUST be listed.";
          leaf Enable {
            type boolean;
            description
              "Enables or disables this {{object}} entry.";
          }
          leaf Type {
            type uint32 {
              range "0..32767";
            }
            description
              "CP Attribute Type as described in
               {{bibref|RFC5996|Section 3.15.1}} and defined in
               {{bibref|IKEv2-params|IKEv2 Configuration Payload
               Attribute Types}}.";
          }
          leaf Value {
            type yang:hex-string {
              length "0..65535";
            }
            description
              "A hexbinary encoded CP Attribute Value as described
               in {{bibref|RFC5996|Section 3.15.1}} and defined
               in {{bibref|IKEv2-params|IKEv2 Configuration
               Payload Attribute Types}}.";
          }
        }
      }

      list Tunnel {
        key "TunnelInterface TunneledInterface";
        config false;
        description
          "Represents an IPsec tunnel, i.e.  a virtual IP interface
           that models an IPsec tunnel entry point and exit
           point.  A {{object}} instance always references (and
           has the same lifetime as) a
           ({{enum|Tunnel|.IP.Interface.{i}.Type}},{{enum|Tunneled|.IP.Interface.{i}.Type}})
           {{object|.IP.Interface}} pair.  The {{object}}
           instance models the IPsec-specific concepts, the
           {{enum|Tunnel|.IP.Interface.{i}.Type}}
           {{object|.IP.Interface}} instance models the generic
           concepts, and the
           {{enum|Tunneled|.IP.Interface.{i}.Type}}
           {{object|.IP.Interface}} instance exists only so it
           can be referenced by forwarding or filter rules.
        
           {{object}} instances are automatically created (as
           needed) when {{object|#.Filter}} instances are enabled
           and disabled.
        
           Each instance's {{param|Filters}} parameter references
           the {{object|#.Filter}} instances that require the
           {{object}} instance to exist.  If this list ever
           becomes {{empty}}, e.g.  because all the referenced
           {{object|#.Filter}} instances have been disabled or
           deleted, the CPE MAY choose not to delete the
           {{object}} instance (and its associated
           ({{enum|Tunnel|.IP.Interface.{i}.Type}},{{enum|Tunneled|.IP.Interface.{i}.Type}})
           {{object|.IP.Interface}} pair).  This can be
           desirable, because {{object|.QoS.Classification}},
           {{object|.Routing.Router.{i}.IPv4Forwarding}},
           {{object|.Routing.Router.{i}.IPv6Forwarding}} etc
           instances might be referencing the
           {{object|.IP.Interface}} instances.";
        leaf TunnelInterface {
          type string;
          description
            "The corresponding auto-created
             {{enum|Tunnel|Device.IP.Interface.{i}.Type}}
             {{object|.IP.Interface}} instance.
             {{reference||delete}}";
        }
        leaf TunneledInterface {
          type string;
          description
            "The corresponding auto-created
             {{enum|Tunneled|Device.IP.Interface.{i}.Type}}
             {{object|.IP.Interface}} instance.
             {{reference||delete}}";
        }
        leaf Filters {
          type string;
          description
            "The {{object|#.Filter}} instances that require this
             {{object}} instance to exist.  {{reference}}";
        }

        container Stats {
          description
            "Statistics for this IPsec tunnel, i.e.  all traffic
             that has passed through the tunnel, including IKEv2
             negotiation, IKEv2 SA and ChildSA traffic.
          
             The CPE MUST reset the tunnel's Stats parameters
             (unless otherwise stated in individual object or
             parameter descriptions) either when the tunnel
             becomes operationally down due to a previous
             administrative down (i.e.  its associated
             {{param|.IP.Interface.{i}.Status}} parameter
             transitions to a down state after the tunnel has
             been disabled) or when the tunnel becomes
             administratively up (i.e.  its associated
             {{param|.IP.Interface.{i}.Enable}} parameter
             transition from {{false}} to {{true}}).
          
             Note that this object does not include generic
             statistics that are available in the associated
             {{object|.IP.Interface.{i}.Stats}} object.";
          leaf DecryptionErrors {
            type types:StatsCounter32;
            description
              "The total number of inbound {{units}} discarded due
               to ESP decryption errors.";
          }
          leaf IntegrityErrors {
            type types:StatsCounter32;
            description
              "The total number of inbound {{units}} discarded due
               to integrity errors.";
          }
          leaf ReplayErrors {
            type types:StatsCounter32;
            description
              "The total number of inbound {{units}} discarded due
               to replay errors.";
          }
          leaf PolicyErrors {
            type types:StatsCounter32;
            description
              "The total number of inbound {{units}} discarded due
               to policy errors.";
          }
          leaf OtherReceiveErrors {
            type types:StatsCounter32;
            description
              "The total number of inbound {{units}} discarded due
               to errors other than decryption, integrity, replay
               or policy errors.  This can include packets
               dropped due to a lack of receive buffers.";
          }
        }
      }

      list IKEv2SA {
        key "Tunnel";
        description
          "Represents an IKEv2 Security Association (SA),
           corresponding to an IKEv2 session.  Instances are
           automatically created and deleted as IKEv2 SAs are
           created and deleted.";
        leaf Status {
          type enumeration {
            enum "Up";
            enum "Down";
            enum "Unknown";
            enum "Dormant";
            enum "Error";
          }
          config false;
          description
            "The current operational state of the IKEv2 SA.";
        }
        leaf Tunnel {
          type string;
          config false;
          description
            "The associated {{object|#.Tunnel}} instance.
             {{reference}}
          
             Note that {{param}} is a unique key, i.e only one
             {{object}} instance is associated with a given
             {{object|#.Tunnel}} instance.  During rekeying
             {{bibref|RFC5996|Section 2.8}}, a new IKEv2 SA is
             created and inherits the existing IKEv2 SA's child
             SAs, then the old IKEv2 SA is deleted.  From the
             management point of view the new and old IKEv2 SAs
             are the same SA and MUST be modeled using the same
             {{object}} instance.";
        }
        leaf LocalAddress {
          type types:IPAddress;
          config false;
          description
            "The local IP address that this IKEv2 SA was negotiated
             with.  This is assigned via IKEv2 and will also be
             available via the associated {{object|#.Tunnel}}'s
             {{param|#.Tunnel.{i}.TunnelInterface}}
             {{object|##.IP.Interface.{i}.IPv4Address}} or
             {{object|##.IP.Interface.{i}.IPv6Address}} table (as
             appropriate).";
        }
        leaf RemoteAddress {
          type types:IPAddress;
          config false;
          description
            "The IP address of the peer that this IKEv2 SA was
             negotiated with.  This will be the IP address of one
             of the security gateways configured via
             {{param|#.Profile.{i}.RemoteEndpoints}}.";
        }
        leaf EncryptionAlgorithm {
          type string {
            length "0..64";
          }
          config false;
          description
            "The encryption algorithm applied to traffic carried by
             this IKEv2 SA.
          
             This will be one of the
             {{param|#.Profile.{i}.IKEv2AllowedEncryptionAlgorithms}}
             from the {{object|#.Profile}} instance via which
             this IKEv2 SA was created.";
        }
        leaf EncryptionKeyLength {
          type uint32;
          config false;
          description
            "The length of the encryption key in {{units}} used for
             the algorithm specified in the
             {{param|EncryptionAlgorithm}} parameter.
          
             The value is 0 if the key length is implicit in the
             specified algorithm or there is no encryption
             applied.";
        }
        leaf PseudoRandomFunction {
          type string {
            length "0..64";
          }
          config false;
          description
            "The pseudo-random function used by this IKEv2 SA.
          
             This will be one of the
             {{param|#.Profile.{i}.IKEv2AllowedPseudoRandomFunctions}}
             from the {{object|#.Profile}} instance via which
             this IKEv2 SA was created.";
        }
        leaf IntegrityAlgorithm {
          type string {
            length "0..64";
          }
          config false;
          description
            "The integrity algorithm applied to the traffic carried
             by this IKEv2 SA.
          
             This will be one of the
             {{param|#.Profile.{i}.IKEv2AllowedIntegrityAlgorithms}}
             from the {{object|#.Profile}} instance via which
             this IKEv2 SA was created.";
        }
        leaf DiffieHellmanGroupTransform {
          type string {
            length "0..64";
          }
          config false;
          description
            "The Diffie-Hellman Group used by this IKEv2 SA.
          
             This will be one of the
             {{param|#.Profile.{i}.IKEv2AllowedDiffieHellmanGroupTransforms}}
             from the {{object|#.Profile}} instance via which
             this IKEv2 SA was created.";
        }
        leaf CreationTime {
          type yang:date-and-time;
          config false;
          description
            "When this IKEv2 SA was set up.";
        }
        leaf NATDetected {
          type enumeration {
            enum "None";
            enum "Local";
            enum "Remote";
            enum "Unsupported";
          }
          config false;
          description
            "Whether NAT traversal is supported by the device and,
             if so, whether a NAT was detected.";
        }

        container Stats {
          config false;
          description
            "Statistics for this IKEv2 Security Association (SA).
          
             The CPE MUST reset the IKEv2 SA's Stats parameters
             (unless otherwise stated in individual object or
             parameter descriptions) whenever the associated
             {{param|#.Tunnel}} instance's Stats parameters are
             reset.";
          leaf BytesSent {
            type types:StatsCounter64;
            description
              "The total number of {{units}} handled in the outbound
               direction by the IKEv2 SA.";
          }
          leaf BytesReceived {
            type types:StatsCounter64;
            description
              "The total number of {{units}} handled in the inbound
               direction by the IKEv2 SA.";
          }
          leaf PacketsSent {
            type types:StatsCounter64;
            description
              "The total number of {{units}} handled in the outbound
               direction by the IKEv2 SA.";
          }
          leaf PacketsReceived {
            type types:StatsCounter64;
            description
              "The total number of {{units}} handled in the inbound
               direction by the IKEv2 SA.";
          }
          leaf ErrorsSent {
            type types:StatsCounter32;
            description
              "The total number of outbound {{units}} from this
               IKEv2 SA discarded for any reason.  This can
               include {{units}} dropped due to a lack of
               transmit buffer space.
            
               Note that this refers to IKE protocol {{units}},
               and not to {{units}} carried by other SAs.";
          }
          leaf DecryptionErrors {
            type types:StatsCounter32;
            description
              "The total number of inbound {{units}} to this IKEv2
               SA discarded due to decryption errors.
            
               Note that this refers to IKEv2 protocol {{units}},
               and not to {units}} carried by other SAs.";
          }
          leaf IntegrityErrors {
            type types:StatsCounter32;
            description
              "The total number of inbound {{units}} to this IKEv2
               SA discarded due to integrity errors.
            
               Note that this refers to IKEv2 protocol {{units}},
               and not to {{units}} carried by other SAs.";
          }
          leaf OtherReceiveErrors {
            type types:StatsCounter32;
            description
              "The total number of inbound {{units}} to this IKEv2
               SA discarded for reasons other than decryption or
               integrity errors.  This can include {{units}}
               dropped due to a lack of receive buffer space.
            
               Note that this refers to IKEv2 protocol {{units}},
               and not to {{units}} carried by other SAs.";
          }
        }

        list ReceivedCPAttr {
          description
            "This is a transitory table that lists all the IKEv2
             Configuration Payload (CP) {{bibref|RFC5996|Section
             3.15}} Attributes that have been received via
             CFG_REPLY messages.  Table entries are automatically
             created to correspond with received Attributes.
             However, it is a local matter to the CPE when to
             delete old table entries.
          
             If the same Attribute is received multiple times, it
             is up to the CPE to decide which entries to include
             (i.e.  whether the same Attribute will be present
             multiple times).  In order to allow for the same
             Attribute to be present multiple times within the
             table, this table has no unique key defined.";
          leaf Type {
            type uint32 {
              range "0..32767";
            }
            config false;
            description
              "CP Attribute Type as described in
               {{bibref|RFC5996|Section 3.15.1}} and defined in
               {{bibref|IKEv2-params|IKEv2 Configuration Payload
               Attribute Types}}.";
          }
          leaf Value {
            type yang:hex-string {
              length "0..65535";
            }
            config false;
            description
              "A hexbinary encoded CP Attribute Value as described
               in {{bibref|RFC5996|Section 3.15.1}} and defined
               in {{bibref|IKEv2-params|IKEv2 Configuration
               Payload Attribute Types}}.";
          }
        }

        list ChildSA {
          key "InboundSPI";
          config false;
          description
            "Represents a child Security Association (SA) pair, i.e.
             an inbound child SA and an outbound child SA.";
          leaf Status {
            type enumeration {
              enum "Up";
              enum "Down";
              enum "Unknown";
              enum "Dormant";
              enum "Error";
            }
            description
              "The current operational state of the child SA pair.";
          }
          leaf InboundSPI {
            type uint32;
            description
              "The inbound child SA's Security Parameter Index
               (SPI).";
          }
          leaf OutboundSPI {
            type uint32;
            description
              "The outbound child SA's Security Parameter Index
               (SPI).";
          }
          leaf CreationTime {
            type yang:date-and-time;
            description
              "The date and time when the child SA was created.";
          }

          container Stats {
            description
              "Statistics for this child Security Association (SA).
            
               The CPE MUST reset the child SA's Stats parameters
               (unless otherwise stated in individual object or
               parameter descriptions) whenever the parent
               {{object|#}} instance's Stats parameters are
               reset.";
            leaf BytesSent {
              type types:StatsCounter64;
              description
                "The number of {{units}} handled by the outbound
                 child SA.";
            }
            leaf BytesReceived {
              type types:StatsCounter64;
              description
                "The number of {{units}} handled by the inbound
                 child SA.";
            }
            leaf PacketsSent {
              type types:StatsCounter64;
              description
                "The number of {{units}} handled by the outbound
                 child SA.";
            }
            leaf PacketsReceived {
              type types:StatsCounter64;
              description
                "The number of {{units}} handled by the inbound
                 child SA.";
            }
            leaf ErrorsSent {
              type types:StatsCounter32;
              description
                "The number of {{units}} discarded by the outbound
                 child SA due to any error.  This can include
                 compression errors or errors due to a lack of
                 transmit buffers.";
            }
            leaf DecryptionErrors {
              type types:StatsCounter32;
              description
                "The number of {{units}} discarded by the inbound
                 child SA due to decryption errors.";
            }
            leaf IntegrityErrors {
              type types:StatsCounter32;
              description
                "The number of {{units}} discarded by the inbound
                 child SA due to integrity errors.";
            }
            leaf ReplayErrors {
              type types:StatsCounter32;
              description
                "The number of {{units}} discarded by the inbound
                 child SA due to replay errors.";
            }
            leaf PolicyErrors {
              type types:StatsCounter32;
              description
                "The number of {{units}} discarded by the inbound
                 child SA due to policy errors.";
            }
            leaf OtherReceiveErrors {
              type types:StatsCounter32;
              description
                "The number of {{units}} discarded by the inbound
                 child SA due to errors other than decryption,
                 integrity, replay or policy errors.  This can
                 include decompression errors or errors due to a
                 lack of receive buffers.";
            }
          }
        }
      }
    }

    container GRE {
      description
        "This object contains parameters associated with the Generic
         Routing Encapsulation (GRE) Tunnel ({{bibref|RFC2784}})
         with Key and Sequence Number extensions
         ({{bibref|RFC2890}}).  This object also provides a means
         to treat packets that are encapsulated within a GRE
         Tunnel by using a set of {{object|Filter}} objects to
         determine the treatment of the packet.";

      list Tunnel {
        key "Alias";
        description
          "GRE Tunnel table, models the GRE Tunnel instance and
           represents the entry point and exit point of the
           tunnel in relation to the WAN interface.  A {{object}}
           object has one or more {{object|Interface}} objects
           that further define the sessions or flows within the
           tunnel.";
        leaf Enable {
          type boolean;
          description
            "Enables or disables the tunnel.";
        }
        leaf Status {
          type enumeration {
            enum "Disabled";
            enum "Enabled";
            enum "Error";
          }
          config false;
          description
            "The current operational state of the tunnel.";
        }
        leaf RemoteEndpoints {
          type string {
            length "0..256";
          }
          description
            "The Fully Qualified Domain Name (FQDN) or IP address of
             the remote GRE tunnel endpoint.  If more than one
             name/address is supplied, they will be tried in
             turn, i.e.  they are in decreasing order of
             precedence.";
        }
        leaf KeepAlivePolicy {
          type enumeration {
            enum "ICMP";
            enum "None";
          }
          default "None";
          description
            "The mechanism used to keep the tunnel from timing out
             at the {{param|ConnectedRemoteEndpoint}}.";
        }
        leaf KeepAliveTimeout {
          type uint32;
          default "10";
          description
            "The tunnel keepalive timeout in {{units}}.";
        }
        leaf KeepAliveThreshold {
          type uint32;
          default "3";
          description
            "Number of KeepAlive messages unacknowledged by the
             {{param|ConnectedRemoteEndpoint}} before the
             {{object}} is perceived failed.";
        }
        leaf DeliveryHeaderProtocol {
          type enumeration {
            enum "IPv4";
            enum "IPv6";
          }
          description
            "The protocol used for the delivery header.";
        }
        leaf DefaultDSCPMark {
          type uint32;
          default "0";
          description
            "If the specified entries in the {{object|#.Filter}}
             table do not match this {{object}} object or an
             instance of the {{object|Interface}} object for this
             {{object}} object, then the value of this parameter
             is applied to the delivery header of the packets in
             this {{object}}.";
        }
        leaf ConnectedRemoteEndpoint {
          type string {
            length "0..256";
          }
          config false;
          description
            "The Fully Qualified Domain Name (FQDN) name or IP
             address of the connected remote GRE tunnel endpoint.";
        }

        container Stats {
          config false;
          description
            "Statistics for this GRE tunnel, i.e.  all traffic that
             has passed through the tunnel.
          
             The device MUST reset the tunnel's Stats parameters
             (unless otherwise stated in individual object or
             parameter descriptions) either when the tunnel
             becomes operationally down due to a previous
             administrative down (i.e., Status parameter
             transitions to a disabled state after the tunnel has
             been disabled) or when the tunnel becomes
             administratively up (i.e.  the Enable parameter
             transitioned from {{false}} to {{true}}).";
          leaf KeepAliveSent {
            type types:StatsCounter32;
            description
              "The total number of KeepAlive {{units}} sent out the
               tunnel.";
          }
          leaf KeepAliveReceived {
            type types:StatsCounter32;
            description
              "The total number of KeepAlive {{units}} received by
               the tunnel.";
          }
          leaf BytesSent {
            type types:StatsCounter64;
            description
              "The total number of {{units}} sent by the tunnel.";
          }
          leaf BytesReceived {
            type types:StatsCounter64;
            description
              "The total number of {{units}} received by the tunnel.";
          }
          leaf PacketsSent {
            type types:StatsCounter64;
            description
              "The total number of {{units}} sent by the tunnel.";
          }
          leaf PacketsReceived {
            type types:StatsCounter64;
            description
              "The total number of {{units}} received by the tunnel.";
          }
          leaf ErrorsSent {
            type types:StatsCounter32;
            description
              "The total number of {{units}} discarded by the tunnel
               due to any error.  This can include packets
               dropped due to a lack of transmit buffers.";
          }
          leaf ErrorsReceived {
            type types:StatsCounter32;
            description
              "The total number of {{units}} received by the tunnel
               that contained errors preventing them from being
               delivered to a higher-layer protocol.";
          }
        }

        list Interface {
          key "Alias";
          description
            "GRE Interface table (a stackable interface object as
             described in {{bibref|TR-181i2|Section 4.2}}).  The
             {{object}} object models the GRE Header as defined
             in {{bibref|RFC2784}} and extensions to the GRE
             Header as defined in {{bibref|RFC2890}}.  The
             {{object}} object provides a way to discriminate how
             sessions or flows are encapsulated within the GRE
             Tunnel.  In addition the {{object}} object
             represents the entry point and exit point of the
             tunnel in relation to the LAN interface.  Unless the
             Key Identifier of {{bibref|RFC2890}} is supported
             there is only one instance of this {{object}} object
             per tunnel.";
          leaf Enable {
            type boolean;
            description
              "Enables or disables the interface.
            
               This parameter is based on ''ifAdminStatus'' from
               {{bibref|RFC2863}}.";
          }
          leaf Status {
            type enumeration {
              enum "Up";
              enum "Down";
              enum "Unknown";
              enum "Dormant";
              enum "NotPresent";
              enum "LowerLayerDown";
              enum "Error";
            }
            config false;
            description
              "The current operational state of the interface (see
               {{bibref|TR-181i2|Section 4.2.2}}).  {{enum}}
            
               When {{param|Enable}} is {{false}} then {{param}}
               SHOULD normally be {{enum|Down}} (or
               {{enum|NotPresent}} or {{enum|Error}} if there is
               a fault condition on the interface).
            
               When {{param|Enable}} is changed to {{true}} then
               {{param}} SHOULD change to {{enum|Up}} if and only
               if the interface is able to transmit and receive
               network traffic; it SHOULD change to
               {{enum|Dormant}} if and only if the interface is
               operable but is waiting for external actions
               before it can transmit and receive network traffic
               (and subsequently change to {{enum|Up}} if still
               operable when the expected actions have
               completed); it SHOULD change to
               {{enum|LowerLayerDown}} if and only if the
               interface is prevented from entering the
               {{enum|Up}} state because one or more of the
               interfaces beneath it is down; it SHOULD remain in
               the {{enum|Error}} state if there is an error or
               other fault condition detected on the interface;
               it SHOULD remain in the {{enum|NotPresent}} state
               if the interface has missing (typically hardware)
               components; it SHOULD change to {{enum|Unknown}}
               if the state of the interface can not be
               determined for some reason.
            
               This parameter is based on ''ifOperStatus'' from
               {{bibref|RFC2863}}.";
          }
          leaf Name {
            type string {
              length "0..64";
            }
            config false;
            description
              "The textual name of the interface as assigned by the
               CPE.";
          }
          leaf LastChange {
            type uint32;
            config false;
            description
              "The accumulated time in {{units}} since the interface
               entered its current operational state.";
          }
          leaf LowerLayers {
            type string;
            description
              "{{list}} {{reference|an interface object that is
               stacked immediately below this interface object}}
               See {{bibref|TR-181i2|Section 4.2.1}}.";
          }
          leaf ProtocolIdOverride {
            type uint32;
            default "0";
            description
              "The Protocol ID assigned to this {{object}}.  The
               Protocol Id is the EtherType value used to
               identify the encapsulated payload.  When set to
               {{null}} the CPE determines the Protocol Id.";
          }
          leaf UseChecksum {
            type boolean;
            default "false";
            description
              "When {{true}}, includes the \"Checksum\" field in the
               GRE header as defined in {{bibref|RFC2784}}.";
          }
          leaf KeyIdentifierGenerationPolicy {
            type enumeration {
              enum "Disabled";
              enum "Provisioned";
              enum "CPE_Generated";
            }
            default "Disabled";
            description
              "The method used to generate the Key Identifier
               extension as defined in.{{bibref|RFC2890}}.";
          }
          leaf KeyIdentifier {
            type uint32;
            default "0";
            description
              "When the value of
               {{param|KeyIdentifierGenerationPolicy}} is
               {{enum|Provisioned|KeyIdentifierGenerationPolicy}}
               this {{param}} parameter is used to identify an
               individual traffic flow within a GRE tunnel, as
               defined in {{bibref|RFC2890}}.";
          }
          leaf UseSequenceNumber {
            type boolean;
            default "false";
            description
              "When {{true}}, includes the \"SequenceNumber\" field
               in the GRE header as defined in {{bibref|RFC2890}}";
          }

          container Stats {
            config false;
            description
              "Statistics for this GRE tunnel interface, i.e.  all
               traffic that has passed through the interface.
            
               The device MUST reset the interface's Stats
               parameters (unless otherwise stated in individual
               object or parameter descriptions) either when the
               interface becomes operationally down due to a
               previous administrative down (i.e., the
               interface's Status parameter transitions to a down
               state after the interface has been disabled) or
               when the interface becomes administratively up
               (i.e.  the Enable parameter transitioned from
               {{false}} to {{true}}).";
            leaf BytesSent {
              type types:StatsCounter64;
              description
                "The total number of {{units}} sent by this
                 interface.";
            }
            leaf BytesReceived {
              type types:StatsCounter64;
              description
                "The total number of {{units}} received by this
                 interface.";
            }
            leaf PacketsSent {
              type types:StatsCounter64;
              description
                "The total number of {{units}} sent by this
                 interface.";
            }
            leaf PacketsReceived {
              type types:StatsCounter64;
              description
                "The total number of {{units}} received by this
                 interface.";
            }
            leaf ErrorsSent {
              type types:StatsCounter32;
              description
                "The total number of {{units}} discarded by this
                 interface due to any error.  This can include
                 packets dropped due to a lack of transmit
                 buffers.";
            }
            leaf ErrorsReceived {
              type types:StatsCounter32;
              description
                "The total number of {{units}} received by this
                 interface that contained errors preventing them
                 from being delivered to a higher-layer protocol.";
            }
            leaf DiscardChecksumReceived {
              type types:StatsCounter32;
              description
                "The total number of {{units}} received by the
                 tunnel interface that are discarded because of
                 Checksum errors.";
            }
            leaf DiscardSequenceNumberReceived {
              type types:StatsCounter32;
              description
                "The total number of {{units}} received by the
                 tunnel interface that are discarded because of
                 Sequence Number errors.";
            }
          }
        }
      }

      list Filter {
        key "Alias";
        description
          "GRE Filter table.  Entries in this table are applied
           against the packets that are to be encapsulated within
           the GRE Tunnel based on the following conditions:
        
           * If the value of the {{param|AllInterfaces}} is
           {{true}}, then this entry will be applied to all
           {{object|#.Tunnel}} and
           {{object|#.Tunnel.{i}.Interface}} instances.
        
           * If the value of {{param|AllInterfaces}} is {{false}}
           and the value of {{param|Interface}} parameter is a
           reference to a row in the {{object|#.Tunnel}} table
           then this entry is applied to all
           {{object|#.Tunnel.{i}.Interface}} instances of the
           {{object|#.Tunnel}} reference.
        
           * If the value of {{param|AllInterfaces}} is {{false}}
           and the value of {{param|Interface}} parameter is a
           reference to a row in the
           {{object|#.Tunnel.{i}.Interface}} table then this
           entry is applied to the
           {{object|#.Tunnel.{i}.Interface}} reference.
        
           * If no entries are matched for the packet, then the
           default treatment (e.g.,
           {{param|#.Tunnel.{i}.DefaultDSCPMark}}) is applied to
           the packet.
        
           For enabled table entries, if {{param|Interface}} is
           not a valid reference and {{param|AllInterfaces}} is
           {{false}}, then the table entry is inoperable and the
           CPE MUST set {{param|Status}} to
           {{enum|Error_Misconfigured|Status}}.";
        leaf Enable {
          type boolean;
          default "false";
          description
            "Enables or disables this filter.";
        }
        leaf Status {
          type enumeration {
            enum "Disabled";
            enum "Enabled";
            enum "Error_Misconfigured";
            enum "Error";
          }
          config false;
          default "Disabled";
          description
            "The status of this filter.  {{enum}}
          
             The {{enum|Error_Misconfigured}} value indicates
             that a necessary configuration value is undefined or
             invalid.
          
             The {{enum|Error}} value MAY be used by the CPE to
             indicate a locally defined error condition.";
        }
        leaf Order {
          type uint32 {
            range "1..max";
          }
          description
            "Position of the {{object}} entry in the order of
             precedence.  A value of ''1'' indicates the first
             entry considered (highest precedence).  For each
             packet, the highest ordered entry that matches the
             filter criteria is applied.  All lower order entries
             are ignored.
          
             When this value is modified, if the value matches
             that of an existing entry, the {{param}} value for
             the existing entry and all lower {{param}} entries
             is incremented (lowered in precedence) to ensure
             uniqueness of this value.  A deletion causes
             {{param}} values to be compacted.  When a value is
             changed, incrementing occurs before compaction.
          
             The value of {{param}} on creation of a {{object}}
             table entry MUST be one greater than the largest
             current value (initially assigned the lowest
             precedence).";
        }
        leaf Interface {
          type string {
            length "0..256";
          }
          default "";
          description
            "Filter criterion.  {{reference}}";
        }
        leaf AllInterfaces {
          type boolean;
          default "false";
          description
            "Filter criterion.  This specifies that all ingress GRE
             tunnel interfaces are associated with the entry.  If
             {{true}}, the value of {{param|Interface}} is
             ignored since all ingress GRE tunnel interfaces are
             indicated.";
        }
        leaf VLANIDCheck {
          type int32 {
            range "-1..max";
          }
          default "-1";
          description
            "Filter criterion.
          
             Current outer Ethernet VLAN ID as defined in 802.1Q.
             A value of -1 indicates this criterion is not used
             for filtering.";
        }
        leaf VLANIDExclude {
          type boolean;
          default "false";
          description
            "If {{false}}, the filter includes only those packets
             that match the {{param|VLANIDCheck}} entry, if
             specified.
          
             If {{true}}, the filter includes all packets except
             those that match the {{param|VLANIDCheck}} entry, if
             specified.";
        }
        leaf DSCPMarkPolicy {
          type int32 {
            range "-2..63";
          }
          description
            "DSCP with which to mark the outer IP header for traffic
             that is associated with the interface criterion.
          
             Automatic DSCP marking behavior is a local matter to
             the device, possibly influenced by other Broadband
             Forum standards that it supports.
          
             * A value of -1 indicates copy from the upstream
             packet.
          
             * A value of -2 indicates automatic marking of DSCP.";
        }
      }
    }

    container MAP {
      description
        "The Mapping of Address and Port (MAP) object {{bibref|MAP}}
         {{bibref|MAP-T}} {{bibref|MAP-DHCP}}.  This object
         applies only to gateway devices that support IPv4 on the
         LAN side, include a {{object|#.NAT}}, and typically have
         only IPv6 connectivity on the WAN side.
      
         See the MAP Theory of Operation
         {{bibref|TR-181i2a8|Appendix XV}} for a description of
         the working of this MAP data model.";
      leaf Enable {
        type boolean;
        description
          "Enables or disables MAP.";
      }

      list Domain {
        key "WANInterface IPv6Prefix";
        description
          "MAP domain settings {{bibref|MAP}} {{bibref|MAP-T}}.
           Each instance models a MAP domain.
        
           MAP supports two transport modes, both of which use
           NAPT44 (modified to use a restricted port range):
        
           * MAP-E ({{param|TransportMode}} =
           {{enum|Encapsulation|TransportMode}}) uses an
           IPv4-in-IPv6 tunnel.
        
           * MAP-T ({{param|TransportMode}} =
           {{enum|Translation|TransportMode}}) uses stateless
           NAT64.
        
           Note: There is an n:1 relationship between a MAP
           domain and the associated {{param|WANInterface}}, i.e.
           in theory multiple MAP domains can be associated with
           a single WAN IP interface (each domain would have its
           own ''End-user IPv6 prefix'' and ''MAP IPv6
           address'').
        
           Note: The {{object}} table includes unique key
           parameters that are strong references.  If a strongly
           referenced object is deleted, the CPE will set the
           referencing parameter to {{empty}}.  However, doing so
           under these circumstances might cause the updated
           {{object}} row to then violate the table's unique key
           constraint; if this occurs, the CPE MUST set
           {{param|Status}} to
           {{enum|Error_Misconfigured|Status}} and disable the
           offending {{object}} row.
        
           {{issue|SZN-MAP|Didn't rename the ''MAP'' bibref to
           ''MAP-E'' because this would require a lot of changes;
           it might be a good idea always to use bibref names
           rather than IDs in the generated HTML because then
           could easily change the name for an existing bibref
           (would require a BBF Report Tool change).}}";
        leaf Enable {
          type boolean;
          default "false";
          description
            "Enables or disables the MAP domain.";
        }
        leaf Status {
          type enumeration {
            enum "Disabled";
            enum "Enabled";
            enum "Error_Misconfigured";
            enum "Error";
          }
          config false;
          description
            "The current operational state of the MAP domain.
          
             The {{enum|Error_Misconfigured}} value indicates
             that a necessary configuration value is undefined or
             invalid.";
        }
        leaf TransportMode {
          type enumeration {
            enum "Encapsulation";
            enum "Translation";
          }
          default "Translation";
          description
            "The transport mode to use.
          
             Corresponds to the {{bibref|MAP-DHCP}}
             ''S46_CONT_MAPE'' and ''S46_CONT_MAPT'' container
             options.";
        }
        leaf WANInterface {
          type string;
          description
            "The IP interface with which this MAP domain is
             associated.  This will always be a NAT-ted upstream
             (WAN) interface.
          
             The ''End-user IPv6 prefix'' {{param|IPv6Prefix}} is
             one of this IP interface's prefixes.
          
             The ''MAP IPv6 address'' is derived from the
             ''End-user IPv6 prefix'' and is one of this IP
             interface's IP addresses, with an
             {{param|##.IP.Interface.{i}.IPv6Address.{i}.Origin}}
             of
             {{enum|MAP|##.IP.Interface.{i}.IPv6Address.{i}.Origin}}.";
        }
        leaf IPv6Prefix {
          type string;
          description
            "The MAP domain's ''End-user IPv6 prefix''.  This MUST
             reference one of {{param|WANInterface}}'s prefixes.
          
             If the ACS configures this prefix directly, the CPE
             MUST use the ACS-configured prefix.  Otherwise, the
             CPE MUST select one of {{param|WANInterface}}'s
             prefixes; the selected prefix will typically have
             {{param|##.IP.Interface.{i}.IPv6Prefix.{i}.Origin}}
             =
             {{enum|PrefixDelegation|##.IP.Interface.{i}.IPv6Prefix.{i}.Origin}}.";
        }
        leaf BRIPv6Prefix {
          type types:IPv6Prefix;
          description
            "The MAP Border Relay (BR) address or prefix.
          
             * For MAP-E this is the BR address and therefore
             MUST be a /128 {{bibref|MAP}}.  Note this address
             can be an IPv6 anycast address.  This address
             corresponds to the {{bibref|MAP-DHCP}}
             ''OPTION_S46_BR'' (Border Relay) option.
          
             * For MAP-T this is the BR prefix {{bibref|MAP-T}}.
             This address prefix corresponds to the
             {{bibref|MAP-DHCP}} ''OPTION_S46_DMR'' (Default
             Mapping Rule) option.
          
             Note: There will be a corresponding
             {{object|.Routing.Router.{i}.IPv4Forwarding}}
             default rule.";
        }
        leaf DSCPMarkPolicy {
          type int32 {
            range "-2..63";
          }
          description
            "DSCP with which to mark the outer IP header for traffic
             that is associated with this MAP domain.
          
             Downstream packets are never re-marked.
          
             Automatic DSCP marking behavior is a local matter to
             the device, possibly influenced by other Broadband
             Forum standards that it supports.
          
             * A value of -1 indicates copy from the incoming
             packet.
          
             * A value of -2 indicates automatic marking of DSCP.";
        }
        leaf PSIDOffset {
          type uint32 {
            range "0..15";
          }
          default "6";
          description
            "''Port-set ID'' (PSID) offset in {{units}}.  The number
             of Port-sets is 2^{{param}}.
          
             Corresponds to the {{bibref|MAP-DHCP}}
             ''S46_PORTPARAMS'' (Port Parameters) option's
             ''offset'' field.";
        }
        leaf PSIDLength {
          type uint32 {
            range "0..16";
          }
          default "0";
          description
            "The length in {{units}} of the ''Port-set id'' (PSID)
             configured in the {{param|PSID}} parameter.
          
             Corresponds to the {{bibref|MAP-DHCP}}
             ''S46_PORTPARAMS'' (Port Parameters) option's
             ''PSID-len'' field.";
        }
        leaf PSID {
          type uint32 {
            range "0..65535";
          }
          default "0";
          description
            "''Port-set ID'' (PSID) to use in preference to the
             value extracted from the ''Embedded Address'' (EA)
             bits.
          
             Only the high order {{param|PSIDLength}} bits of the
             {{param}} value are used, so the parameter is
             ignored when {{param|PSIDLength}} is zero.
          
             Corresponds to the {{bibref|MAP-DHCP}}
             ''S46_PORTPARAMS'' (Port Parameters) option's
             ''PSID'' field.";
        }
        leaf IncludeSystemPorts {
          type boolean;
          default "false";
          description
            "Whether to include low-numbered (system) ports in the
             Port-sets.  Normally ports in the range
             [0:2^(16-{{param|PSIDOffset}})-1] are excluded, e.g.
             for the default {{param|PSIDOffset}} value of 4,
             ports [0:4095] are not included in the Port-sets.
          
             This parameter is related to {{bibref|MAP}}'s ''N'',
             which is defined as ''the number of ports (e.g.,
             1024) excluded from the lower end of the range''.
             The parameter is relevant only when
             {{param|PSIDOffset}} is 0; {{false}} corresponds to
             ''N=1024'' and {{true}} corresponds to ''N=0''.";
        }

        list Rule {
          key "IPv6Prefix";
          description
            "The MAP domain's Mapping Rules {{bibref|MAP}}.  The
             rule with the longest match between its
             {{param|IPv6Prefix}} and the end-user
             {{param|#.IPv6Prefix}} is the Basic Mapping Rule
             (BMR).  Any of the rules (including the BMR) can be
             a Forwarding Mapping Rule.";
          leaf Enable {
            type boolean;
            default "false";
            description
              "Enable or disable this {{object}} instance.";
          }
          leaf Status {
            type enumeration {
              enum "Disabled";
              enum "Enabled";
              enum "Error";
            }
            config false;
            default "Disabled";
            description
              "The status of this {{object}} instance.  {{enum}}
            
               The {{enum|Error}} value MAY be used by the CPE to
               indicate a locally defined error condition.";
          }
          leaf Origin {
            type enumeration {
              enum "DHCPv6";
              enum "Static";
            }
            config false;
            default "Static";
            description
              "The mechanism via which the {{object}} was created.
            
               If the CPE supports MAP configuration via both
               DHCPv6 and CWMP, it is up to the implementation to
               determine how the two mechanisms will interact.";
          }
          leaf IPv6Prefix {
            type types:IPv6Prefix;
            default "/0";
            description
              "The ''Rule IPv6 prefix''.
            
               The Rule IPv6 prefix is a leading part of the
               end-user {{param|#.IPv6Prefix}}, i.e.  its length
               MUST be less than or equal to the length of the
               end-user ''IPv6Prefix'', and it MUST match the
               end-user ''IPv6Prefix''.
            
               Corresponds to the {{bibref|MAP-DHCP}}
               ''S46_RULE'' option's ''ipv6-prefix'' field.";
          }
          leaf IPv4Prefix {
            type types:IPv4Prefix;
            default "/0";
            description
              "The ''Rule IPv4 prefix''.
            
               Corresponds to the {{bibref|MAP-DHCP}}
               ''S46_RULE'' option's ''ipv4-prefix'' field.";
          }
          leaf EABitsLength {
            type uint32 {
              range "0..48";
            }
            default "0";
            description
              "The length in {{units}} of the ''Embedded Address
               (EA) bits'' in the end-user
               {{param|#.IPv6Prefix}}.
            
               Corresponds to the {{bibref|MAP-DHCP}}
               ''S46_RULE'' option's ''ea-len'' field.";
          }
          leaf IsFMR {
            type boolean;
            default "false";
            description
              "Indicates whether this rule is a ''Forwarding Mapping
               Rule'' (FMR), i.e.  can be used for forwarding.
            
               Corresponds to the {{bibref|MAP-DHCP}}
               ''S46_RULE'' option's ''flags'' field's
               ''F-Flag''.";
          }
        }

        container Interface {
          description
            "MAP interface (a stackable interface object as
             described in {{bibref|TR-181i2|Section 4.2}}).  This
             models the LAN side MAP domain interface.";
          leaf Enable {
            type boolean;
            default "false";
            description
              "Enables or disables the interface.
            
               This parameter is based on ''ifAdminStatus'' from
               {{bibref|RFC2863}}.";
          }
          leaf Status {
            type enumeration {
              enum "Up";
              enum "Down";
              enum "Unknown";
              enum "Dormant";
              enum "NotPresent";
              enum "LowerLayerDown";
              enum "Error";
            }
            config false;
            description
              "The current operational state of the interface (see
               {{bibref|TR-181i2|Section 4.2.2}}).  {{enum}}
            
               When {{param|Enable}} is {{false}} then {{param}}
               SHOULD normally be {{enum|Down}} (or
               {{enum|NotPresent}} or {{enum|Error}} if there is
               a fault condition on the interface).
            
               When {{param|Enable}} is changed to {{true}} then
               {{param}} SHOULD change to {{enum|Up}} if and only
               if the interface is able to transmit and receive
               network traffic; it SHOULD change to
               {{enum|Dormant}} if and only if the interface is
               operable but is waiting for external actions
               before it can transmit and receive network traffic
               (and subsequently change to {{enum|Up}} if still
               operable when the expected actions have
               completed); it SHOULD change to
               {{enum|LowerLayerDown}} if and only if the
               interface is prevented from entering the
               {{enum|Up}} state because one or more of the
               interfaces beneath it is down; it SHOULD remain in
               the {{enum|Error}} state if there is an error or
               other fault condition detected on the interface;
               it SHOULD remain in the {{enum|NotPresent}} state
               if the interface has missing (typically hardware)
               components; it SHOULD change to {{enum|Unknown}}
               if the state of the interface can not be
               determined for some reason.
            
               This parameter is based on ''ifOperStatus'' from
               {{bibref|RFC2863}}.";
          }
          leaf Name {
            type string {
              length "0..64";
            }
            config false;
            description
              "The textual name of the interface as assigned by the
               CPE.";
          }
          leaf LastChange {
            type uint32;
            config false;
            description
              "The accumulated time in {{units}} since the interface
               entered its current operational state.";
          }
          leaf LowerLayers {
            type string;
            description
              "{{list}} {{reference|an interface object that is
               stacked immediately below this interface object}}
               See {{bibref|TR-181i2|Section 4.2.1}}.
            
               Note: Since this interface object is a MAP domain
               interface, it is expected that {{param}} will not
               be used.";
          }

          container Stats {
            config false;
            description
              "Throughput statistics for this MAP domain interface.
            
               The CPE MUST reset the interface's Stats
               parameters (unless otherwise stated in individual
               object or parameter descriptions) either when the
               interface becomes operationally down due to a
               previous administrative down (i.e.  the
               interface's {{param|#.Status}} parameter
               transitions to a down state after the interface is
               disabled) or when the interface becomes
               administratively up (i.e.  the interface's
               {{param|#.Enable}} parameter transitions from
               {{false}} to {{true}}).  Administrative and
               operational interface status is discussed in
               {{bibref|TR-181i2|section 4.2.2}}.";
            leaf BytesSent {
              type types:StatsCounter64;
              description
                "The total number of bytes transmitted out of the
                 interface, including framing characters.";
            }
            leaf BytesReceived {
              type types:StatsCounter64;
              description
                "The total number of bytes received on the
                 interface, including framing characters.";
            }
            leaf PacketsSent {
              type types:StatsCounter64;
              description
                "The total number of packets transmitted out of the
                 interface.";
            }
            leaf PacketsReceived {
              type types:StatsCounter64;
              description
                "The total number of packets received on the
                 interface.";
            }
            leaf ErrorsSent {
              type types:StatsCounter32;
              description
                "The total number of outbound packets that could not
                 be transmitted because of errors.";
            }
            leaf ErrorsReceived {
              type types:StatsCounter32;
              description
                "The total number of inbound packets that contained
                 errors preventing them from being delivered to a
                 higher-layer protocol.";
            }
            leaf UnicastPacketsSent {
              type types:StatsCounter64;
              description
                "The total number of packets requested for
                 transmission which were not addressed to a
                 multicast or broadcast address at this layer,
                 including those that were discarded or not sent.";
            }
            leaf UnicastPacketsReceived {
              type types:StatsCounter64;
              description
                "The total number of received packets, delivered by
                 this layer to a higher layer, which were not
                 addressed to a multicast or broadcast address at
                 this layer.";
            }
            leaf DiscardPacketsSent {
              type types:StatsCounter32;
              description
                "The total number of outbound packets which were
                 chosen to be discarded even though no errors had
                 been detected to prevent their being
                 transmitted.  One possible reason for discarding
                 such a packet could be to free up buffer space.";
            }
            leaf DiscardPacketsReceived {
              type types:StatsCounter32;
              description
                "The total number of inbound packets which were
                 chosen to be discarded even though no errors had
                 been detected to prevent their being delivered.
                 One possible reason for discarding such a packet
                 could be to free up buffer space.";
            }
            leaf MulticastPacketsSent {
              type types:StatsCounter64;
              description
                "The total number of packets that higher-level
                 protocols requested for transmission and which
                 were addressed to a multicast address at this
                 layer, including those that were discarded or
                 not sent.";
            }
            leaf MulticastPacketsReceived {
              type types:StatsCounter64;
              description
                "The total number of received packets, delivered by
                 this layer to a higher layer, which were
                 addressed to a multicast address at this layer.";
            }
            leaf BroadcastPacketsSent {
              type types:StatsCounter64;
              description
                "The total number of packets that higher-level
                 protocols requested for transmission and which
                 were addressed to a broadcast address at this
                 layer, including those that were discarded or
                 not sent.
              
                 Note that IPv6 does not define broadcast
                 addresses, so IPv6 packets will never cause this
                 counter to increment.";
            }
            leaf BroadcastPacketsReceived {
              type types:StatsCounter64;
              description
                "The total number of received packets, delivered by
                 this layer to a higher layer, which were
                 addressed to a broadcast address at this layer.
              
                 Note that IPv6 does not define broadcast
                 addresses, so IPv6 packets will never cause this
                 counter to increment.";
            }
            leaf UnknownProtoPacketsReceived {
              type types:StatsCounter32;
              description
                "The total number of packets received via the
                 interface which were discarded because of an
                 unknown or unsupported protocol.";
            }
          }
        }
      }
    }

    container CaptivePortal {
      description
        "This object contains parameters relating to the captive
         portal configuration on the CPE.
      
         The captive portal configuration defines the CPE's
         upstream HTTP (port 80) traffic redirect behavior.
      
         When the captive portal is disabled, upstream HTTP (port
         80) traffic MUST be permitted to all destinations.
      
         When the captive portal is enabled, upstream HTTP (port
         80) traffic MUST be permitted only to destinations
         listed in the {{param|AllowedList}}; traffic to all
         other destinations MUST be redirected to the
         {{param|URL}}.";
      leaf Enable {
        type boolean;
        description
          "Enables or disables the captive portal.";
      }
      leaf Status {
        type enumeration {
          enum "Disabled";
          enum "Enabled";
          enum "Error_URLEmpty";
          enum "Error";
        }
        config false;
        description
          "Indicates the status of the captive portal.  {{enum}}
        
           The {{enum|Error}} value MAY be used by the CPE to
           indicate a locally defined error condition.";
      }
      leaf AllowedList {
        type string;
        description
          "{{list}} List items represent IP addresses to which HTTP
           (port 80) traffic MUST always be permitted, regardless
           of whether the captive portal is enabled.
        
           Each entry in the list MUST be either an IP address,
           or an IP prefix specified using Classless Inter-Domain
           Routing (CIDR) notation {{bibref|RFC4632}}.
        
           An IP prefix is specified as an IP address followed
           (with no intervening white space) by \"/n\", where
           ''n'' (the prefix size) is an integer in the range
           0-32 (for IPv4) or 0-128 (for IPv6) that indicates the
           number of (leftmost) '1' bits of the prefix.
        
           IPv4 example:
        
           * 1.2.3.4 specifies a single IPv4 address, and
           1.2.3.4/24 specifies a class C subnet with subnet mask
           255.255.255.0.
        
           * 1.2.0.0/22 represents the 1024 IPv4 addresses from
           1.2.0.0 to 1.2.3.255.
        
           IPv6 example:
        
           * fec0::220:edff:fe6a:f76 specifies a single IPv6
           address.
        
           * 2001:edff:fe6a:f76::/64 represents the IPv6
           addresses from 2001:edff:fe6a:f76:0:0:0:0 to
           2001:edff:fe6a:f76:ffff:ffff:ffff:ffff.";
      }
      leaf URL {
        type string {
          length "0..2000";
        }
        description
          "Captive portal URL to which upstream HTTP (port 80)
           traffic to destinations not listed in the
           {{param|AllowedList}} will be redirected.
        
           The captive portal URL MUST be an HTTP (not HTTPS)
           URL.
        
           The CPE MUST permit the captive portal URL to be set
           to {{empty}}, which has the effect of disabling the
           captive portal (if {{param|Enable}} is {{true}} and
           the captive portal URL is {{empty}}, {{param|Status}}
           MUST be {{enum|Error_URLEmpty|Status}}).";
      }
    }

    container Routing {
      description
        "Routing object that contains the {{object|Router}} table
         and {{object|RIP}} protocol object.";

      list Router {
        key "Alias";
        description
          "This object allows the handling of the routing and
           forwarding configuration of the device.";
        leaf Enable {
          type boolean;
          default "false";
          description
            "Enables or disables this ''Router'' entry.";
        }
        leaf Status {
          type enumeration {
            enum "Disabled";
            enum "Enabled";
            enum "Error";
          }
          config false;
          default "Disabled";
          description
            "The status of this ''Router'' entry.  {{enum}}
          
             The {{enum|Error}} value MAY be used by the CPE to
             indicate a locally defined error condition.";
        }

        list IPv4Forwarding {
          key "DestIPAddress DestSubnetMask ForwardingPolicy GatewayIPAddress Interface ForwardingMetric";
          description
            "Layer 3 IPv4 forwarding table.
          
             In addition to statically configured routes, this
             table MUST include dynamic routes learned through
             layer 3 routing protocols, including RIP (i.e.  RIP
             version 2), OSPF, DHCPv4, and IPCP.  The CPE MAY
             reject attempts to delete or modify a dynamic route
             entry.
          
             For each incoming packet, the layer 3 forwarding
             decision is conceptually made as follows:
          
             * Only enabled table entries with a matching
             {{param|ForwardingPolicy}} are considered, i.e.
             those that either do not specify a
             {{param|ForwardingPolicy}}, or else specify a
             {{param|ForwardingPolicy}} that matches that of the
             incoming packet.
          
             * Next, table entries that also have a matching
             destination address/mask are considered, and the
             matching entry with the longest prefix is applied to
             the packet (i.e.  the entry with the most specific
             network).  An unspecified destination address is a
             wild-card and always matches, but with a prefix
             length of zero.
          
             For enabled table entries, if {{param|Interface}} is
             not a valid reference to an IPv4-capable interface
             (that is attached to the IPv4 stack), then the table
             entry is inoperable and the CPE MUST set
             {{param|Status}} to
             {{enum|Error_Misconfigured|Status}}.
          
             Note: The {{object}} table includes a unique key
             parameter that is a strong reference.  If a strongly
             referenced object is deleted, the CPE will set the
             referencing parameter to {{empty}}.  However, doing
             so under these circumstances might cause the updated
             {{object}} row to then violate the table's unique
             key constraint; if this occurs, the CPE MUST disable
             the offending {{object}} row.";
          leaf Enable {
            type boolean;
            default "false";
            description
              "Enables or disables the forwarding entry.  On
               creation, an entry is disabled by default.";
          }
          leaf Status {
            type enumeration {
              enum "Disabled";
              enum "Enabled";
              enum "Error_Misconfigured";
              enum "Error";
            }
            config false;
            default "Disabled";
            description
              "Indicates the status of the forwarding entry.
               {{enum}}
            
               The {{enum|Error}} value MAY be used by the CPE to
               indicate a locally defined error condition.
            
               The {{enum|Error_Misconfigured}} value indicates
               that a necessary configuration value is undefined
               or invalid.";
          }
          leaf StaticRoute {
            type boolean;
            config false;
            default "true";
            description
              "If {{true}}, this route is a Static route.";
          }
          leaf DestIPAddress {
            type types:IPv4Address;
            default "";
            description
              "Destination IPv4 address.  {{empty}} indicates no
               destination address is specified.
            
               A Forwarding table entry for which {{param}} and
               {{param|DestSubnetMask}} are both {{empty}} is a
               default route.";
          }
          leaf DestSubnetMask {
            type types:IPv4Address;
            default "";
            description
              "Destination subnet mask.  {{empty}} indicates no
               destination subnet mask is specified.
            
               If a destination subnet mask is specified, the
               {{param}} is ANDed with the destination address
               before comparing with the {{param|DestIPAddress}}.
               Otherwise, the full destination address is used as
               is.
            
               A Forwarding table entry for which
               {{param|DestIPAddress}} and {{param}} are both
               {{empty}} is a default route.";
          }
          leaf ForwardingPolicy {
            type int32 {
              range "-1..max";
            }
            default "-1";
            description
              "Identifier of a set of classes or flows that have the
               corresponding {{param}} value as defined in the
               {{object|Device.QoS}} object.
            
               A value of -1 indicates no {{param}} is specified.
            
               If specified, this forwarding entry is to apply
               only to traffic associated with the specified
               classes and flows.";
          }
          leaf GatewayIPAddress {
            type types:IPv4Address;
            default "";
            description
              "IPv4 address of the gateway.
            
               Only one of {{param}} and Interface SHOULD be
               configured for a route.
            
               If both are configured, {{param}} and
               {{param|Interface}} MUST be consistent with each
               other.";
          }
          leaf Interface {
            type string {
              length "0..256";
            }
            default "";
            description
              "{{reference}} Specifies the egress layer 3 interface
               associated with this entry.  Example:
               Device.IP.Interface.1.
            
               Only one of {{param|GatewayIPAddress}} and
               {{param}} SHOULD be configured for a route.
            
               If both are configured, {{param|GatewayIPAddress}}
               and {{param}} MUST be consistent with each other.
            
               For a route that was configured by setting
               {{param|GatewayIPAddress}} but not {{param}}, read
               access to {{param}} MUST return the full
               hierarchical parameter name for the routes egress
               interface.";
          }
          leaf Origin {
            type enumeration {
              enum "DHCPv4";
              enum "OSPF";
              enum "IPCP";
              enum "RIP";
              enum "Static";
            }
            config false;
            default "Static";
            description
              "Protocol via which the IPv4 forwarding rule was
               learned.  {{enum}}";
          }
          leaf ForwardingMetric {
            type int32 {
              range "-1..max";
            }
            default "-1";
            description
              "Forwarding metric.  A value of -1 indicates this
               metric is not used.";
          }
        }

        list IPv6Forwarding {
          key "DestIPPrefix ForwardingPolicy NextHop Interface ForwardingMetric";
          description
            "Layer 3 IPv6 forwarding table.
          
             In addition to statically configured routes, this
             table MUST include dynamic routes learned through
             layer 3 routing protocols, including RIPng, OSPF,
             DHCPv6, and RA.  The CPE MAY reject attempts to
             delete or modify a dynamic route entry.
          
             For each incoming packet, the layer 3 forwarding
             decision is conceptually made as follows:
          
             * Only enabled table entries with a matching
             {{param|ForwardingPolicy}} are considered, i.e.
             those that either do not specify a
             {{param|ForwardingPolicy}}, or else specify a
             {{param|ForwardingPolicy}} that matches that of the
             incoming packet.
          
             * Next, table entries that also have a matching
             destination prefix are considered, and the matching
             entry with the longest prefix length is applied to
             the packet (i.e.  the entry with the most specific
             network).  An unspecified destination address is a
             wild-card and always matches, but with a prefix
             length of zero.
          
             For enabled table entries, if {{param|Interface}} is
             not a valid reference to an IPv6-capable interface
             (that is attached to the IPv6 stack), then the table
             entry is inoperable and the CPE MUST set
             {{param|Status}} to
             {{enum|Error_Misconfigured|Status}}.
          
             This object is based on ''inetCidrRouteTable'' from
             {{bibref|RFC4292}}.";
          leaf Enable {
            type boolean;
            default "false";
            description
              "Enables or disables this {{object}} entry.";
          }
          leaf Status {
            type enumeration {
              enum "Disabled";
              enum "Enabled";
              enum "Error_Misconfigured";
              enum "Error";
            }
            config false;
            default "Disabled";
            description
              "Indicates the status of the forwarding entry.
               {{enum}}
            
               The {{enum|Error_Misconfigured}} value indicates
               that a necessary configuration value is undefined
               or invalid.
            
               The {{enum|Error}} value MAY be used by the CPE to
               indicate a locally defined error condition.";
          }
          leaf DestIPPrefix {
            type types:IPv6Prefix;
            default "";
            description
              "Destination IPv6 prefix.  {{empty}} indicates that it
               matches all destination prefixes (i.e.  equivalent
               to \"::/0\").  All bits to the right of the prefix
               MUST be zero, e.g.  2001:edff:fe6a:f76::/64.
            
               Routes with a 128-bit prefix length (/128) are
               host routes for a specific IPv6 destination, e.g.
               2001:db8:28:2:713e:a426:d167:37ab/128.";
          }
          leaf ForwardingPolicy {
            type int32 {
              range "-1..max";
            }
            default "-1";
            description
              "Identifier of a set of classes or flows that have the
               corresponding {{param}} value as defined in the
               {{object|.QoS}} object.
            
               A value of -1 indicates no {{param}} is specified.
            
               If specified, this forwarding entry is to apply
               only to traffic associated with the specified
               classes and flows.";
          }
          leaf NextHop {
            type types:IPv6Address;
            default "";
            description
              "IPv6 address of the next hop.
            
               Only one of {{param}} and {{param|Interface}}
               SHOULD be configured for a route.  {{empty}}
               indicates no {{param}} is specified.
            
               If both are configured, {{param}} and
               {{param|Interface}} MUST be consistent with each
               other.";
          }
          leaf Interface {
            type string {
              length "0..256";
            }
            default "";
            description
              "{{reference}} Specifies the egress layer 3 interface
               associated with this entry.  Example:
               ''Device.IP.Interface.1''.
            
               Only one of {{param|NextHop}} and {{param}} SHOULD
               be configured for a route.  {{empty}} indicates no
               {{param}} is specified.
            
               If both are configured, {{param|NextHop}} and
               {{param}} MUST be consistent with each other.
            
               For a route that was configured by setting
               {{param|NextHop}} but not {{param}}, read access
               to {{param}} MUST return the full hierarchical
               parameter name for the route's egress interface.";
          }
          leaf Origin {
            type enumeration {
              enum "DHCPv6";
              enum "OSPF";
              enum "RA";
              enum "RIPng";
              enum "Static";
            }
            config false;
            default "Static";
            description
              "Protocol via which the IPv6 forwarding rule was
               learned.  {{enum}}";
          }
          leaf ForwardingMetric {
            type int32 {
              range "-1..max";
            }
            default "-1";
            description
              "Forwarding metric.  A value of -1 indicates this
               metric is not used.";
          }
          leaf ExpirationTime {
            type yang:date-and-time;
            config false;
            default "9999-12-31T23:59:59Z";
            description
              "The time at which the route will expire, or {{null}}
               if not known.  For an infinite lifetime, the
               parameter value MUST be 9999-12-31T23:59:59Z.
            
               {{param}} is provided by an underlying dynamic
               routing protocol, e.g.  by an {{bibref|RFC4191}}
               route information option.";
          }
        }
      }

      container RIP {
        description
          "Routing Information Protocol (RIP) object.";
        leaf Enable {
          type boolean;
          description
            "Enables or disables RIP on the device.";
        }
        leaf SupportedModes {
          type enumeration {
            enum "Send";
            enum "Receive";
            enum "Both";
          }
          config false;
          description
            "The supported RIP protocol modes.  {{enum}}";
        }

        list InterfaceSetting {
          key "Interface";
          description
            "IP Interface RIP configuration table.
          
             For enabled table entries, if {{param|Interface}} is
             not a valid reference then the table entry is
             inoperable and the CPE MUST set {{param|Status}} to
             {{enum|Error_Misconfigured|Status}}.
          
             Note: The {{object}} table includes a unique key
             parameter that is a strong reference.  If a strongly
             referenced object is deleted, the CPE will set the
             referencing parameter to {{empty}}.  However, doing
             so under these circumstances might cause the updated
             {{object}} row to then violate the table's unique
             key constraint; if this occurs, the CPE MUST set
             {{param|Status}} to
             {{enum|Error_Misconfigured|Status}} and disable the
             offending {{object}} row.
          
             Note: This object only applies to RIP2; i.e.
             version 2 of the RIP protocol is used to accept or
             send over the specified {{param|Interface}}.";
          leaf Enable {
            type boolean;
            default "false";
            description
              "Enables or disables this entry.";
          }
          leaf Status {
            type enumeration {
              enum "Disabled";
              enum "Enabled";
              enum "Error_Misconfigured";
              enum "Error";
            }
            config false;
            default "Disabled";
            description
              "The status of this entry.  {{enum}}
            
               The {{enum|Error_Misconfigured}} value indicates
               that a necessary configuration value is undefined
               or invalid.
            
               The {{enum|Error}} value MAY be used by the CPE to
               indicate a locally defined error condition.";
          }
          leaf Interface {
            type string {
              length "0..256";
            }
            default "";
            description
              "{{reference}} This is the IP interface associated
               with this {{object}} entry.";
          }
          leaf AcceptRA {
            type boolean;
            description
              "When set to {{true}}, RIP route advertisements
               received over {{param|Interface}} are accepted.
            
               When set to {{false}}, RIP route advertisements
               received over {{param|Interface}} are rejected.";
          }
          leaf SendRA {
            type boolean;
            description
              "When set to {{true}}, RIP route advertisements are to
               be sent over {{param|Interface}}.
            
               When set to {{false}}, no RIP route advertisements
               will be sent over {{param|Interface}}.";
          }
        }
      }

      container RouteInformation {
        description
          "Received Router Advertisement (RA) route information
           {{bibref|RFC4191}}.";
        leaf Enable {
          type boolean;
          description
            "Enables or disables receiving route information from
             the RA.";
        }

        list InterfaceSetting {
          key "Interface";
          config false;
          description
            "IP Interface RA route information table.  Contains
             received RA route information {{bibref|RFC4191}}.
             As such, the data in this table cannot be modified.";
          leaf Status {
            type enumeration {
              enum "ForwardingEntryCreated";
              enum "NoForwardingEntry";
              enum "Error";
            }
            description
              "The status of this entry.  {{enum}}
            
               The {{enum|Error}} value MAY be used by the CPE to
               indicate a locally defined error condition.";
          }
          leaf Interface {
            type string {
              length "0..256";
            }
            description
              "{{reference}} This is the IP interface associated
               with this {{object}} entry.";
          }
          leaf SourceRouter {
            type types:IPv6Address;
            description
              "IPv6 Address of the router that sent the RA that
               included this route info.";
          }
          leaf PreferredRouteFlag {
            type enumeration {
              enum "High";
              enum "Medium";
              enum "Low";
            }
            description
              "Flag included in a specific Route Information Option
               within an RA message (Prf flag), as defined in
               {{bibref|RFC4191|Section 2.3}}.  {{enum}}
            
               Note that this is not the Prf flag included in the
               base RA message.  Also see
               {{bibref|RFC4191|Section 2.1}} which discusses how
               this flag is encoded on the wire.";
          }
          leaf Prefix {
            type types:IPv6Prefix;
            description
              "IPv6 address prefix, as received in an instance of
               the Route Information Option of a RA message.";
          }
          leaf RouteLifetime {
            type yang:date-and-time;
            description
              "The time at which {{param|Prefix}} will cease to be
               usable for use as a forwarding entry, or {{null}}
               if not known.  For an infinite lifetime, the
               parameter value MUST be 9999-12-31T23:59:59Z.
            
               {{param}} is received in an instance of the Route
               Information Option of a RA message.";
          }
        }
      }
    }

    container NeighborDiscovery {
      description
        "The Neighbor Discovery Protocol (NDP) object
         {{bibref|RFC4861}}.  This object applies only to IPv6.
         It contains an {{object|InterfaceSetting}} table that
         defines the NDP configuration for individual IP
         interfaces.";
      leaf Enable {
        type boolean;
        description
          "Enables or disables Neighbor Discovery.";
      }

      list InterfaceSetting {
        key "Interface";
        description
          "Per-interface Neighbor Discovery Protocol (NDP)
           configuration {{bibref|RFC4861}}.
        
           For enabled table entries, if {{param|Interface}} is
           not a valid reference to an IPv6-capable interface
           (that is attached to the IPv6 stack), then the table
           entry is inoperable and the CPE MUST set
           {{param|Status}} to
           {{enum|Error_Misconfigured|Status}}.
        
           Note: The {{object}} table includes a unique key
           parameter that is a strong reference.  If a strongly
           referenced object is deleted, the CPE will set the
           referencing parameter to {{empty}}.  However, doing so
           under these circumstances might cause the updated
           {{object}} row to then violate the table's unique key
           constraint; if this occurs, the CPE MUST set
           {{param|Status}} to
           {{enum|Error_Misconfigured|Status}} and disable the
           offending {{object}} row.";
        leaf Enable {
          type boolean;
          default "false";
          description
            "Enables or disables this {{object}} entry.";
        }
        leaf Status {
          type enumeration {
            enum "Disabled";
            enum "Enabled";
            enum "Error_Misconfigured";
            enum "Error";
          }
          config false;
          default "Disabled";
          description
            "The status of this entry.  {{enum}}
          
             The {{enum|Error_Misconfigured}} value indicates
             that a necessary configuration value is undefined or
             invalid.
          
             The {{enum|Error}} value MAY be used by the CPE to
             indicate a locally defined error condition.";
        }
        leaf Interface {
          type string;
          default "";
          description
            "This is the IP interface associated with this
             {{object}} entry.";
        }
        leaf RetransTimer {
          type uint32;
          default "1000";
          description
            "Retransmission interval in {{units}}, as defined in
             {{bibref|RFC4861}}.  For auto-configuration
             purposes, {{param}} specifies the delay between
             consecutive Neighbor Solicitation transmissions
             performed during Duplicate Address Detection (DAD)
             {{bibref|RFC4862|Section 5.4}}, as well as the time
             a node waits after sending the last Neighbor
             Solicitation before ending the DAD process.";
        }
        leaf RtrSolicitationInterval {
          type uint32;
          default "4";
          description
            "Retransmission interval in {{units}}, as defined in
             {{bibref|RFC4861}}.  For auto-configuration
             purposes, {{param}} specifies the delay between
             consecutive Router Solicitation transmissions.";
        }
        leaf MaxRtrSolicitations {
          type uint32;
          default "3";
          description
            "Maximum Number of Router Solicitation Transmission
             messages, as defined in {{bibref|RFC4861}}.  For
             auto-configuration purposes {{param}} specifies the
             Maximum Number of Router Solicitation Transmission
             messages to help the host to conclude that there are
             no routers on the link.";
        }
        leaf NUDEnable {
          type boolean;
          description
            "Enables or disables Neighbor Unreachability Detection
             (NUD) {{bibref|RFC4861|Section 7}}.";
        }
        leaf RSEnable {
          type boolean;
          description
            "Enables or disables Router Solicitation (RS) on
             {{param|Interface}} {{bibref|RFC4861|Section 4.1}}.";
        }
      }
    }

    container RouterAdvertisement {
      description
        "The Router Advertisement (RA) object {{bibref|RFC4861}}.
         This object applies only to IPv6.  It contains an
         {{object|InterfaceSetting}} table that defines the RA
         configuration for individual IP interfaces.
      
         Information received via router advertisement messages
         is automatically propagated to the relevant
         {{object|.IP.Interface}} sub-objects, e.g.  to the
         {{object|.IP.Interface.{i}.IPv6Address}} and
         {{object|.IP.Interface.{i}.IPv6Prefix}} tables.";
      leaf Enable {
        type boolean;
        description
          "Enables or disables Router Advertisement.";
      }

      list InterfaceSetting {
        key "Interface";
        description
          "Per-interface Router Advertisement (RA) configuration
           {{bibref|RFC4861}}.  Table entries are created for use
           in sending Router Advertisements.
        
           For enabled table entries, if {{param|Interface}} is
           not a valid reference to an IPv6-capable interface
           (that is attached to the IPv6 stack), then the table
           entry is inoperable and the CPE MUST set
           {{param|Status}} to
           {{enum|Error_Misconfigured|Status}}.
        
           Note: The {{object}} table includes a unique key
           parameter that is a strong reference.  If a strongly
           referenced object is deleted, the CPE will set the
           referencing parameter to {{empty}}.  However, doing so
           under these circumstances might cause the updated
           {{object}} row to then violate the table's unique key
           constraint; if this occurs, the CPE MUST set
           {{param|Status}} to
           {{enum|Error_Misconfigured|Status}} and disable the
           offending {{object}} row.";
        leaf Enable {
          type boolean;
          default "false";
          description
            "Enables or disables this {{object}} entry.
          
             Defines the value of the ''IsRouter'' and
             ''AdvSendAdvertisements'' flags from
             {{bibref|RFC4861|Section 4.2}}";
        }
        leaf Status {
          type enumeration {
            enum "Disabled";
            enum "Enabled";
            enum "Error_Misconfigured";
            enum "Error";
          }
          config false;
          default "Disabled";
          description
            "The status of this entry.  {{enum}}
          
             The {{enum|Error_Misconfigured}} value indicates
             that a necessary configuration value is undefined or
             invalid.
          
             The {{enum|Error}} value MAY be used by the CPE to
             indicate a locally defined error condition.";
        }
        leaf Interface {
          type string;
          default "";
          description
            "This is the IP interface associated with this
             {{object}} entry.";
        }
        leaf ManualPrefixes {
          type string;
          default "";
          description
            "{{list}} {{reference}}
          
             Manually-configured prefixes that will be sent in
             Router Advertisement messages.  Each referenced
             prefix MUST have a
             {{param|.IP.Interface.{i}.IPv6Prefix.{i}.StaticType}}
             of
             {{enum|Static|.IP.Interface.{i}.IPv6Prefix.{i}.StaticType}}
             or
             {{enum|Child|.IP.Interface.{i}.IPv6Prefix.{i}.StaticType}}.
             Router Advertisement messages MUST include Prefix
             Information Options {{bibref|RFC4861}} for all
             ''Valid''
             ({{param|.IP.Interface.{i}.IPv6Prefix.{i}.ValidLifetime}}
             is infinite or in the future) prefixes in this list.
          
             Prefixes MUST be associated with the interface
             instance referenced by {{param|Interface}}.";
        }
        leaf Prefixes {
          type string;
          config false;
          description
            "{{list}} {{reference}}
          
             All prefixes that will be included in Router
             Advertisement (RA) messages sent out this interface.
             This list can include:
          
             * Prefixes from {{param|ManualPrefixes}} that are
             included in RA messages.
          
             * Prefixes with
             {{param|.IP.Interface.{i}.IPv6Prefix.{i}.Origin}} =
             {{enum|Child|.IP.Interface.{i}.IPv6Prefix.{i}.Origin}}
             or
             {{enum|AutoConfigured|.IP.Interface.{i}.IPv6Prefix.{i}.Origin}}
             associated with the interface instance referenced by
             {{param|Interface}}.";
        }
        leaf MaxRtrAdvInterval {
          type uint32 {
            range "4..1800";
          }
          default "600";
          description
            "The maximum time allowed between sending unsolicited
             multicast Router Advertisements from the interface,
             in {{units}} (see {{bibref|RFC4861|Section 4.2}}).";
        }
        leaf MinRtrAdvInterval {
          type uint32 {
            range "3..1350";
          }
          default "200";
          description
            "The minimum time allowed between sending unsolicited
             multicast Router Advertisements from the interface,
             in {{units}} (see {{bibref|RFC4861|Section 4.2}}).
          
             The value MUST be no greater than 3/4 *
             {{param|MaxRtrAdvInterval}}.
          
             Note: The ''1350'' maximum was derived from the RFC,
             based on 3/4 times the maximum value of
             {{param|MaxRtrAdvInterval}}.  Similarly, the ''200''
             default was derived from the RFC, based on 1/3 times
             the default value of {{param|MaxRtrAdvInterval}}.";
        }
        leaf AdvDefaultLifetime {
          type uint32 {
            range "min..65535";
          }
          default "1800";
          description
            "The value placed in the \"Router Lifetime\" field of
             Router Advertisement messages on this interface, in
             {{units}} (see {{bibref|RFC4861|Section 4.2}}).
          
             The value can be zero or between
             {{param|MaxRtrAdvInterval}} and 9000 {{units}}, but
             these limits can be overridden by specific documents
             that describe how IPv6 operates over different link
             layers.
          
             A value of zero indicates that the router is not to
             be used as a default router.
          
             Note: The ''1800'' default was derived from the RFC,
             based on 3 times the default value of
             {{param|MaxRtrAdvInterval}}.";
        }
        leaf AdvManagedFlag {
          type boolean;
          default "false";
          description
            "The value placed in the \"Managed address
             configuration\" (M) flag field of Router
             Advertisement messages on this interafce (see
             {{bibref|RFC4861|Section 4.2}}, and
             {{bibref|RFC4862}}).";
        }
        leaf AdvOtherConfigFlag {
          type boolean;
          default "false";
          description
            "The value placed in the \"Other configuration\" (O)
             flag field of Router Advertisement messages on this
             interface (see {{bibref|RFC4861|Section 4.2}}, and
             {{bibref|RFC4862}}).";
        }
        leaf AdvMobileAgentFlag {
          type boolean;
          default "false";
          description
            "The value placed in the \"Home agent\" (H) flag field
             of Router Advertisement messages on this interface
             (see {{bibref|RFC3775|Section 7.1}}).";
        }
        leaf AdvPreferredRouterFlag {
          type enumeration {
            enum "High";
            enum "Medium";
            enum "Low";
          }
          default "Medium";
          description
            "The value placed in the \"Default Router Preference\"
             (Prf) field of Router Advertisement messages on this
             interface, as defined in {{bibref|RFC4191|Section
             2.2}}.  {{enum}}
          
             Also see {{bibref|RFC4191|Section 2.1}} which
             discusses how this flag is encoded on the wire.";
        }
        leaf AdvNDProxyFlag {
          type boolean;
          default "false";
          description
            "The value placed in the \"Proxy\" (P) flag field of
             Router Advertisement messages on this interface (see
             {{bibref|RFC4389|Section 4.1.3.3}}).";
        }
        leaf AdvLinkMTU {
          type uint32;
          default "0";
          description
            "The value placed in MTU options of Router Advertisement
             messages on this interface.  A value of zero
             indicates that no MTU options are included (see
             {{bibref|RFC4861|Section 4.6.4}}).";
        }
        leaf AdvReachableTime {
          type uint32 {
            range "min..3600000";
          }
          default "0";
          description
            "The value placed in the \"Reachable Time\" field of
             Router Advertisement messages on this interface, in
             {{units}} (see {{bibref|RFC4861|Section 4.2}}).
          
             The value zero means unspecified (by the router).";
        }
        leaf AdvRetransTimer {
          type uint32;
          default "0";
          description
            "The value placed in the \"Retrans Timer\" field of
             Router Advertisement messages on this interface (see
             {{bibref|RFC4861|Section 4.2}}).
          
             The value zero means unspecified (by the router).";
        }
        leaf AdvCurHopLimit {
          type uint32 {
            range "min..255";
          }
          default "0";
          description
            "The value placed in the \"Cur Hop Limit\" field of
             Router Advertisement messages on this interface (see
             {{bibref|RFC4861|Section 4.2}}).
          
             The value zero means unspecified (by the router).
          
             Note: The default can be overridden with the value
             specified in {{bibref|RFC3232}} that was in effect
             at the time of implementation.";
        }

        list Option {
          key "Tag";
          description
            "This object specifies the options in a Router
             Advertisement (RA) message {{bibref|RFC4861|Section
             4.6}}.  {{object}} entries are created for use in
             sending Router Advertisements (enabled options MUST
             be included in RA messages sent).  This includes
             support for sending DNS information in the RA
             message as described in {{bibref|RFC6106}}.
          
             This table is intended only for options that are not
             modeled elsewhere.  For example, it is not
             appropriate for the MTU option (which is modeled via
             {{param|#.AdvLinkMTU}}).";
          leaf Enable {
            type boolean;
            default "false";
            description
              "Enables or disables this {{object}} entry.";
          }
          leaf Tag {
            type uint32 {
              range "0..65535";
            }
            description
              "Option tag (type) {{bibref|RFC4861|Section 4.6}}.";
          }
          leaf Value {
            type yang:hex-string {
              length "0..65535";
            }
            description
              "A hexbinary encoded option value
               {{bibref|RFC4861|Section 4.6}}.";
          }
        }
      }
    }

    container IPv6rd {
      description
        "Settings allowing a CPE to derive and route IPv6 Rapid
         Deployment (6rd) delegated prefixes as specified in
         {{bibref|RFC5969}}.  The 6rd mechanism is intended to be
         implemented only on what {{bibref|RFC5969}} refers to as
         ''Customer Edge Routers'', i.e.  on gateway devices,
         that support IPv6 on the LAN side and only have IPv4
         connectivity on the WAN side.
      
         See the 6rd Theory of Operation
         {{bibref|TR-181i2a2|Appendix VI}} for a description of
         the working of this 6rd data model.";
      leaf Enable {
        type boolean;
        description
          "Enables or disables IPv6rd.";
      }

      list InterfaceSetting {
        key "Alias";
        description
          "6rd {{bibref|RFC5969}} settings.
        
           A 6rd delegated prefix is expected to be of maximum
           length 64 bits, and is the concatenation of the
           following two items:
        
           * Service provider IPv6 prefix: specified via the
           {{param|SPIPv6Prefix}} parameter
        
           * IPv4 address suffix: the IPv4 address with the first
           {{param|IPv4MaskLength}} bits removed
        
           This object definition is derived from
           {{bibref|RFC5969}} with some minor nomenclature
           changes.";
        leaf Enable {
          type boolean;
          description
            "Enable or disable this {{object}} instance.";
        }
        leaf Status {
          type enumeration {
            enum "Disabled";
            enum "Enabled";
            enum "Error";
          }
          config false;
          description
            "The status of this entry.  {{enum}}
          
             The {{enum|Error}} value MAY be used by the CPE to
             indicate a locally defined error condition.";
        }
        leaf BorderRelayIPv4Addresses {
          type types:IPv4Address;
          description
            "List items are the IPv4 addresses (possibly anycast) of
             the 6rd Relay(s).";
        }
        leaf AllTrafficToBorderRelay {
          type boolean;
          description
            "If {{true}}, the destination address for all 6rd
             traffic will be set (IPv4 destination address) to
             one of the {{param|BorderRelayIPv4Addresses}}.  If
             {{false}}, traffic whose destination address begins
             with the same prefix as {{param|SPIPv6Prefix}} will
             be sent directly to the destination IPv4 address of
             the endpoint, which is in the same 6rd domain.  See
             6rd Theory of Operation for further explanation
             {{bibref|TR-181i2a2|Appendix VI}}.";
        }
        leaf SPIPv6Prefix {
          type types:IPv6Prefix;
          description
            "The Service Provider's 6rd IPv6 prefix for this
             deployment and this 6rd RG.";
        }
        leaf IPv4MaskLength {
          type uint32 {
            range "0..32";
          }
          description
            "The number of high-order {{units}} that are identical
             across all IPv4 addresses within a given 6rd domain.
             This number of {{units}} MUST be removed from the
             start of the IPv4 address when generating the 6rd
             delegated prefix.
          
             For example, if this value is 8, only the final 24
             {{units}} of the subscriber IPv4 prefix will be used
             when creating the IPv6 delegated prefix, determining
             the destination IPv4 encapsulation address, etc.
          
             If the value is 0, then the whole 32 {{units}} of
             the IPv4 address are used in the encoding.";
        }
        leaf AddressSource {
          type string {
            length "0..256";
          }
          description
            "{{reference}} Points to the IPv4 address that is the
             source of the IPv4 address embedded in the IPv6 6rd
             prefix, and used as the source encapsulating IPv4
             address.  If the value is {{empty}} or this
             parameter is not present, the device will use
             internal logic to determine which IPv4 source
             address to use.";
        }
        leaf TunnelInterface {
          type string {
            length "0..256";
          }
          config false;
          description
            "{{reference}} This is an IP interface of ''Type''
             {{enum|Tunnel|.IP.Interface.{i}.Type}} that is
             logically the tunnel entry point for upstream IPv6
             traffic and is also logically the tunnel exit point
             for downstream IPv6 traffic (i.e.  the entry point
             for non-tunneled upstream IPv6 traffic to enter a
             tunnel and become tunneled, or conversely, the exit
             point for downstream IPv6 traffic leaving a tunnel
             after being un-tunneled).
          
             IPv6 traffic that enters {{param}} from the LAN is
             expected to continue on through
             {{param|TunneledInterface}}, and traffic from the
             WAN is expected to come from
             {{param|TunneledInterface}} into {{param}}.
             {{param}} is a logical interface that can allow for
             classification, marking (of IPv6 headers), and
             policing of IPv6 traffic that will be going over a
             6rd tunnel.  These functions are modeled in the
             {{object|.QoS.}} object.
          
             {{param}} can be used also to represent the 6rd
             virtual interface defined in {{bibref|RFC5969}}.
          
             Note: In 6rd, IPv6 packets arriving over one or more
             device LAN IP interfaces are logically fed into this
             {{param}}.  Likewise, 6rd traffic from the WAN gets
             logically sent from this {{param}} to LAN IP
             interfaces.";
        }
        leaf TunneledInterface {
          type string {
            length "0..256";
          }
          config false;
          description
            "{{reference}} This is an IP interface of ''Type''
             {{enum|Tunneled|.IP.Interface.{i}.Type}} that
             provides information about the IPv4 headers used to
             encapsulate the IPv6 packets.
          
             Encapsulated IPv6 traffic that enters {{param}} from
             the WAN is expected to continue on through
             {{param|TunnelInterface}}, and traffic from the LAN
             is expected to come from {{param|TunnelInterface}}
             into {{param}}.  {{param}} is a logical interface
             that can allow for classification, marking (of IPv4
             headers and VLAN tags), and policing of IPv4 packets
             that encapsulate IPv6 packets in 6rd traffic.  These
             functions are modeled in the {{object|.QoS.}}
             object.
          
             Note: In 6rd, {{param}} traffic originating from the
             LAN logically feeds into a WAN-side IPv4 capable IP
             interface that the \"IPv6 6rd tunnel\" goes over.
             6rd traffic that enters over this IPv4 WAN interface
             gets logically sent to this {{param}}.";
        }
      }
    }

    container DSLite {
      description
        "Settings allowing a CPE to configure and route IPv6
         Dual-Stack Lite (DSLite) as specified in
         {{bibref|DSLite}}.  The DS-Lite mechanism is intended to
         be implemented only on gateway devices that support IPv4
         on the LAN side and only have IPv6 connectivity on the
         WAN side.
      
         See the Dual-Stack Lite Theory of Operation
         {{bibref|TR-181i2a2|Appendix VII}} for a description of
         the working of this DS-Lite data model.";
      leaf Enable {
        type boolean;
        description
          "Enables or disables DSLite.";
      }

      list InterfaceSetting {
        key "Alias";
        description
          "DSLite {{bibref|DSLite}} settings.";
        leaf Enable {
          type boolean;
          description
            "Enable or disable this {{object}} instance.";
        }
        leaf Status {
          type enumeration {
            enum "Disabled";
            enum "Enabled";
            enum "Error";
          }
          config false;
          description
            "The status of this entry.  {{enum}}
          
             The {{enum|Error}} value MAY be used by the CPE to
             indicate a locally defined error condition.";
        }
        leaf EndpointAssignmentPrecedence {
          type enumeration {
            enum "DHCPv6";
            enum "Static";
          }
          default "DHCPv6";
          description
            "Indicates the preferred method to be used in assigning
             values to {{param|EndpointName}} when both static
             and dynamic values are available.  See
             {{param|EndpointName}} for further clarification.";
        }
        leaf EndpointAddressTypePrecedence {
          type enumeration {
            enum "FQDN";
            enum "IPv6Address";
          }
          description
            "Indicates the preferred method to be used to assign the
             address of the DS-Lite Endpoint when both
             {{param|EndpointName}} and {{param|EndpointAddress}}
             values are available and the
             {{enum|Static|EndpointAssignmentPrecedence}} method
             is used.  See {{param|EndpointName}} and
             {{param|EndpointAddress}} for further clarification.";
        }
        leaf EndpointAddressInUse {
          type types:IPv6Address;
          config false;
          description
            "Indicates the address currently in use for the tunnel
             concentrator (remote endpoint).  It is derived from
             the values of the
             {{param|EndpointAssignmentPrecedence}},
             {{param|EndpointAddressTypePrecedence}},
             {{param|EndpointName}} and {{param|EndpointAddress}}
             parameters.
          
             It is {{empty}} if no endpoint address is currently
             known.";
        }
        leaf EndpointName {
          type string {
            length "0..256";
          }
          description
            "The Fully Qualified Domain Name (FQDN) of the tunnel
             concentrator (remote endpoint).
          
             This parameter is based on ''OPTION_DS_LITE_NAME''
             from {{bibref|DSLite-options|Section 4}} and can be
             assigned statically (e.g.  present in the factory
             default configuration or set by the ACS) or can be
             updated dynamically (via DHCPv6).  If both
             statically and dynamically assigned, then
             {{param|EndpointAssignmentPrecedence}} indicates
             whether it is the static configuration or the DHCPv6
             configuration that is actually applied to {{param}}.
          
             Note: {{param}} is only writable when
             {{param|EndpointAssignmentPrecedence}} is
             {{enum|Static|EndpointAssignmentPrecedence}};
             otherwise, {{param}} is automatically configured via
             the DHCPv6 received option.";
        }
        leaf EndpointAddress {
          type types:IPv6Address;
          description
            "The address of the tunnel concentrator (remote
             endpoint).
          
             This parameter can only be assigned statically (e.g.
             present in the factory default configuration or set
             by the ACS).";
        }
        leaf Origin {
          type enumeration {
            enum "DHCPv6";
            enum "Static";
          }
          config false;
          description
            "Method used to assign {{param|EndpointAddressInUse}}.";
        }
        leaf TunnelInterface {
          type string {
            length "0..256";
          }
          config false;
          description
            "{{reference}} This is an IP interface of ''Type''
             {{enum|Tunnel|.IP.Interface.{i}.Type}} that is
             logically the tunnel entry point for upstream IPv4
             traffic and is also logically the tunnel exit point
             for downstream IPv4 traffic (i.e.  the entry point
             for non-tunneled upstream IPv4 traffic to enter a
             tunnel and become tunneled, or conversely, the exit
             point for downstream IPv4 traffic leaving a tunnel
             after being un-tunneled).
          
             IPv4 traffic that enters {{param}} is expected to
             continue on through {{param|TunneledInterface}} from
             the LAN, and traffic from the WAN is expected to
             come from TunneledInterface into TunnelInterface.
             TunnelInterface is a logical interface that can
             allow for classification, marking (of IPv4 headers),
             and policing of IPv4 traffic that will be going over
             a DS-Lite tunnel.  These functions are modeled in
             the Device.QoS object.
          
             Note: In DS-Lite, IPv4 packets arriving over one or
             more device LAN IP interfaces are logically fed into
             this {{param}}.  Likewise, DS-Lite traffic from the
             WAN gets logically sent from this {{param}} to LAN
             IP interfaces.";
        }
        leaf TunneledInterface {
          type string {
            length "0..256";
          }
          config false;
          description
            "{{reference}} This is an IP interface of ''Type''
             {{enum|Tunneled|.IP.Interface.{i}.Type}} that
             provides information about the IPv6 headers used to
             encapsulate the IPv4 packets.
          
             Encapsulated IPv4 traffic that enters {{param}} from
             the WAN is expected to continue on through
             {{param|TunnelInterface}}, and traffic from the LAN
             is expected to come from {{param|TunnelInterface}}
             into {{param}}.  {{param}} is a logical interface
             that can allow for classification, marking (of IPv6
             headers and VLAN tags), and policing of IPv6 packets
             that encapsulate IPv4 packets in DS-Lite traffic.
             These functions are modeled in the {{object|.QoS.}}
             object.
          
             Note: In DS-Lite, {{param}} traffic originating from
             the LAN logically feeds into a WAN-side IPv6 capable
             IP interface that the \"DSLite IPv4-in-IPv6 tunnel\"
             goes over.  DS-Lite traffic that enters over this
             IPv6 WAN interface gets logically sent to this
             {{param}}.";
        }
      }
    }

    container QoS {
      description
        "Queue management configuration object.";
      leaf MaxClassificationEntries {
        type uint32;
        config false;
        description
          "The maximum number of entries available in the
           Classification table.";
      }
      leaf MaxAppEntries {
        type uint32;
        config false;
        description
          "The maximum number of entries available in the
           {{object|App}} table.";
      }
      leaf MaxFlowEntries {
        type uint32;
        config false;
        description
          "The maximum number of entries available in the
           {{object|Flow}} table.";
      }
      leaf MaxPolicerEntries {
        type uint32;
        config false;
        description
          "The maximum number of entries available in the
           {{object|Policer}} table.";
      }
      leaf MaxQueueEntries {
        type uint32;
        config false;
        description
          "The maximum number of entries available in the
           {{object|Queue}} table.";
      }
      leaf MaxShaperEntries {
        type uint32;
        config false;
        description
          "The maximum number of entries available in the
           {{object|Shaper}} table.";
      }
      leaf DefaultForwardingPolicy {
        type uint32;
        description
          "Identifier of the forwarding policy associated with
           traffic not associated with any specified classifier.";
      }
      leaf DefaultTrafficClass {
        type uint32;
        description
          "Identifier of the traffic class associated with traffic
           not associated with any specified classifier.";
      }
      leaf DefaultPolicer {
        type string {
          length "0..256";
        }
        description
          "{{reference}} Indicates the ''Policer'' table entry for
           traffic not associated with any specified classifier.
        
           {{empty}} indicates a null policer.";
      }
      leaf DefaultQueue {
        type string {
          length "0..256";
        }
        description
          "{{reference}} Indicates the ''Queue'' table entry for
           traffic not associated with any specified classifier.
           Note: The interpretation of {{empty}} value is
           implementation specific.";
      }
      leaf DefaultDSCPMark {
        type int32 {
          range "-2..max";
        }
        description
          "DSCP to mark traffic not associated with any specified
           classifier.
        
           A value of -1 indicates no change from the incoming
           packet.
        
           A value of -2 indicates automatic marking of DSCP
           based upon the EthernetPriority value of the incoming
           packet as defined in {{bibref|TR-181i2|Annex A}}.";
      }
      leaf DefaultEthernetPriorityMark {
        type int32 {
          range "-2..max";
        }
        description
          "Ethernet priority code (as defined in
           {{bibref|802.1Q-2011}}) to mark traffic not associated
           with any specified classifier.
        
           A value of -1 indicates no change from the incoming
           packet.
        
           A value of -2 indicates automatic marking of
           EthernetPriority based upon the DSCP value of the
           incoming packet as defined in
           {{bibref|TR-181i2a5|Annex A}}.";
      }
      leaf DefaultInnerEthernetPriorityMark {
        type int32 {
          range "-2..max";
        }
        description
          "Ethernet priority code (as defined in
           {{bibref|802.1Q-2011}}) to mark traffic of the inner
           VLAN Tag as defined in 802.1Q, when the PDU is not
           associated with any specified classifier.  This
           parameter is only applicable when the PDU has 2 VLAN
           Tags.
        
           A value of -1 indicates no change from the incoming
           packet.
        
           A value of -2 indicates automatic marking of
           EthernetPriority based upon the DSCP value of the
           incoming packet as defined in {{bibref|TR-181i2|Annex
           A}}.";
      }
      leaf AvailableAppList {
        type string;
        config false;
        description
          "{{list}} List items represent URNs, each indicating a
           protocol supported for use as a ProtocolIdentifier in
           the App table.  This list MAY include any of the URNs
           defined in {{bibref|TR-181i2|Annex A}} as well as
           other URNs defined elsewhere.";
      }

      list Classification {
        key "Alias";
        description
          "Classification table.
        
           For enabled table entries, if {{param|Interface}} is
           not a valid reference and {{param|AllInterfaces}} is
           {{false}}, then the table entry is inoperable and the
           CPE MUST set {{param|Status}} to
           {{enum|Error_Misconfigured|Status}}.
        
           Several of this object's parameters specify DHCP
           option values.  Some cases are version neutral (the
           parameter can apply to both DHCPv4 and DHCPv6), but in
           other cases the representation of the option is
           different for DHCPv4 and DHCPv6, so it is necessary to
           define separate DHCPv4-specific and DHCPv6-specific
           parameters.  Therefore, an instance of this object
           that uses DHCP option values as classification
           criteria will be associated with either DHCPv4 or
           DHCPv6, as indicated by the {{param|DHCPType}}
           parameter.";
        leaf Enable {
          type boolean;
          default "false";
          description
            "Enables or disables this classifier.";
        }
        leaf Status {
          type enumeration {
            enum "Disabled";
            enum "Enabled";
            enum "Error_Misconfigured";
            enum "Error";
          }
          config false;
          default "Disabled";
          description
            "The status of this classifier.  {{enum}}
          
             The {{enum|Error_Misconfigured}} value indicates
             that a necessary configuration value is undefined or
             invalid.
          
             The {{enum|Error}} value MAY be used by the CPE to
             indicate a locally defined error condition.";
        }
        leaf Order {
          type uint32 {
            range "1..max";
          }
          description
            "Position of the {{object}} entry in the order of
             precedence.  A value of ''1'' indicates the first
             entry considered (highest precedence).  For each
             packet, the highest ordered entry that matches the
             classification criteria is applied.  All lower order
             entries are ignored.
          
             When this value is modified, if the value matches
             that of an existing entry, the {{param}} value for
             the existing entry and all lower {{param}} entries
             is incremented (lowered in precedence) to ensure
             uniqueness of this value.  A deletion causes
             {{param}} values to be compacted.  When a value is
             changed, incrementing occurs before compaction.
          
             The value of {{param}} on creation of a {{object}}
             table entry MUST be one greater than the largest
             current value (initially assigned the lowest
             precedence).";
        }
        leaf DHCPType {
          type enumeration {
            enum "DHCPv4";
            enum "DHCPv6";
          }
          default "DHCPv4";
          description
            "The DHCP protocol associated with the {{object}}
             instance.  Affects only parameters that specify DHCP
             option values as classification criteria (all such
             parameter descriptions note this fact).  {{enum}}
          
             If {{param}} is {{enum|DHCPv4}}, then {{object}}
             parameters that are DHCPv6-specific are ignored.  If
             {{param}} is {{enum|DHCPv6}}, then {{object}}
             parameters that are DHCPv4-specific are ignored.";
        }
        leaf Interface {
          type string {
            length "0..256";
          }
          default "";
          description
            "Classification criterion.  {{reference}}
          
             This specifies the ingress interface associated with
             the entry.  It MAY be a layer 1, 2 or 3 interface,
             however, the types of interfaces for which
             ''Classifications'' can be instantiated is a local
             matter to the CPE.
          
             Note that this parameter is permitted to reference
             ''Tunnel'' instances in order to classify upstream
             packets that have just been encapsulated (such
             packets are conceptually similar to
             locally-generated traffic).  For example, this
             parameter might reference a {{object|.GRE.Tunnel}}
             or a {{object|.MAP.Domain}} instance.";
        }
        leaf AllInterfaces {
          type boolean;
          default "false";
          description
            "Classification criterion.  This specifies that all
             ingress interfaces are associated with the entry.
             If {{true}}, the value of {{param|Interface}} is
             ignored since all ingress interfaces are indicated.";
        }
        leaf DestIP {
          type types:IPAddress;
          default "";
          description
            "Classification criterion.
          
             Destination IP address.  {{empty}} indicates this
             criterion is not used for classification.";
        }
        leaf DestMask {
          type types:IPPrefix;
          default "";
          description
            "Destination IP address mask, represented as an IP
             routing prefix using CIDR notation [RFC4632].  The
             IP address part MUST be {{empty}} (and, if
             specified, MUST be ignored).";
        }
        leaf DestIPExclude {
          type boolean;
          default "false";
          description
            "If {{false}}, the class includes only those packets
             that match the (masked) DestIP entry, if specified.
          
             If {{true}}, the class includes all packets except
             those that match the (masked) DestIP entry, if
             specified.";
        }
        leaf SourceIP {
          type types:IPAddress;
          default "";
          description
            "Classification criterion.
          
             Source IP address.  {{empty}} indicates this
             criterion is not used for classification.";
        }
        leaf SourceMask {
          type types:IPPrefix;
          default "";
          description
            "Source IP address mask, represented as an IP routing
             prefix using CIDR notation [RFC4632].  The IP
             address part MUST be {{empty}} (and, if specified,
             MUST be ignored).";
        }
        leaf SourceIPExclude {
          type boolean;
          default "false";
          description
            "If {{false}}, the class includes only those packets
             that match the (masked) {{param|SourceIP}} entry, if
             specified.
          
             If {{true}}, the class includes all packets except
             those that match the (masked) {{param|SourceIP}}
             entry, if specified.";
        }
        leaf Protocol {
          type int32 {
            range "-1..255";
          }
          default "-1";
          description
            "Classification criterion.
          
             Protocol number.  A value of -1 indicates this
             criterion is not used for classification.";
        }
        leaf ProtocolExclude {
          type boolean;
          default "false";
          description
            "If {{false}}, the class includes only those packets
             that match the {{param|Protocol}} entry, if
             specified.
          
             If {{true}}, the class includes all packets except
             those that match the {{param|Protocol}} entry, if
             specified.";
        }
        leaf DestPort {
          type int32 {
            range "-1..65535";
          }
          default "-1";
          description
            "Classification criterion.
          
             Destination port number.  A value of -1 indicates
             this criterion is not used for classification.";
        }
        leaf DestPortRangeMax {
          type int32 {
            range "-1..65535";
          }
          default "-1";
          description
            "Classification criterion.
          
             If specified, indicates the classification criterion
             is to include the port range from {{param|DestPort}}
             through {{param}} (inclusive).  If specified,
             {{param}} MUST be greater than or equal to
             {{param|DestPort}}.
          
             A value of -1 indicates that no port range is
             specified.";
        }
        leaf DestPortExclude {
          type boolean;
          default "false";
          description
            "If {{false}}, the class includes only those packets
             that match the {{param|DestPort}} entry (or port
             range), if specified.
          
             If {{true}}, the class includes all packets except
             those that match the {{param|DestPort}} entry (or
             port range), if specified.";
        }
        leaf SourcePort {
          type int32 {
            range "-1..65535";
          }
          default "-1";
          description
            "Classification criterion.
          
             Source port number.  A value of -1 indicates this
             criterion is not used for classification.";
        }
        leaf SourcePortRangeMax {
          type int32 {
            range "-1..65535";
          }
          default "-1";
          description
            "Classification criterion.
          
             If specified, indicates the classification criterion
             is to include the port range from
             {{param|SourcePort}} through {{param}} (inclusive).
             If specified, {{param}} MUST be greater than or
             equal to SourcePort.
          
             A value of -1 indicates that no port range is
             specified.";
        }
        leaf SourcePortExclude {
          type boolean;
          default "false";
          description
            "If {{false}}, the class includes only those packets
             that match the {{param|SourcePort}} entry (or port
             range), if specified.
          
             If {{true}}, the class includes all packets except
             those that match the {{param|SourcePort}} entry (or
             port range), if specified.";
        }
        leaf SourceMACAddress {
          type types:MACAddress;
          default "";
          description
            "Classification criterion.
          
             Source MAC Address.  {{empty}} indicates this
             criterion is not used for classification.";
        }
        leaf SourceMACMask {
          type types:MACAddress;
          default "";
          description
            "Bit-mask for the MAC address, where matching of a
             packet's MAC address with the
             {{param|SourceMACAddress}} is only to be done for
             bit positions set to one in the mask.  A mask of
             ''FF:FF:FF:FF:FF:FF'' or {{empty}} indicates all
             bits of the {{param|SourceMACAddress}} are to be
             used for classification.";
        }
        leaf SourceMACExclude {
          type boolean;
          default "false";
          description
            "If {{false}}, the class includes only those packets
             that match the (masked) {{param|SourceMACAddress}}
             entry, if specified.
          
             If {{true}}, the class includes all packets except
             those that match the (masked)
             {{param|SourceMACAddress}} entry, if specified.";
        }
        leaf DestMACAddress {
          type types:MACAddress;
          default "";
          description
            "Classification criterion.
          
             Destination MAC Address.  {{empty}} indicates this
             criterion is not used for classification.
          
             The use of destination MAC address as a
             classification criterion is primarily useful only
             for bridged traffic.";
        }
        leaf DestMACMask {
          type types:MACAddress;
          default "";
          description
            "Bit-mask for the MAC address, where matching of a
             packet's MAC address with the
             {{param|DestMACAddress}} is only to be done for bit
             positions set to one in the mask.  A mask of
             ''FF:FF:FF:FF:FF:FF'' or {{empty}} indicates all
             bits of the {{param|DestMACAddress}} are to be used
             for classification.";
        }
        leaf DestMACExclude {
          type boolean;
          default "false";
          description
            "If {{false}}, the class includes only those packets
             that match the (masked) {{param|DestMACAddress}}
             entry, if specified.
          
             If {{true}}, the class includes all packets except
             those that match the (masked)
             {{param|DestMACAddress}} entry, if specified.";
        }
        leaf Ethertype {
          type int32 {
            range "-1..max";
          }
          default "-1";
          description
            "Classification criterion.
          
             Ethertype as indicated in either the Ethernet or
             SNAP Type header.  A value of -1 indicates this
             criterion is not used for classification.";
        }
        leaf EthertypeExclude {
          type boolean;
          default "false";
          description
            "If {{false}}, the class includes only those packets
             that match the {{param|Ethertype}} entry, if
             specified.
          
             If {{true}}, the class includes all packets except
             those that match the {{param|Ethertype}} entry, if
             specified.";
        }
        leaf SSAP {
          type int32 {
            range "-1..max";
          }
          default "-1";
          description
            "Classification criterion.
          
             SSAP element in the LLC header.  A value of -1
             indicates this criterion is not used for
             classification.";
        }
        leaf SSAPExclude {
          type boolean;
          default "false";
          description
            "If {{false}}, the class includes only those packets
             that match the {{param|SSAP}} entry, if specified.
          
             If {{true}}, the class includes all packets except
             those that match the {{param|SSAP}} entry, if
             specified.";
        }
        leaf DSAP {
          type int32 {
            range "-1..max";
          }
          default "-1";
          description
            "Classification criterion.
          
             DSAP element in the LLC header.  A value of -1
             indicates this criterion is not used for
             classification.";
        }
        leaf DSAPExclude {
          type boolean;
          default "false";
          description
            "If {{false}}, the class includes only those packets
             that match the {{param|DSAP}} entry, if specified.
          
             If {{true}}, the class includes all packets except
             those that match the {{param|DSAP}} entry, if
             specified.";
        }
        leaf LLCControl {
          type int32 {
            range "-1..max";
          }
          default "-1";
          description
            "Classification criterion.
          
             Control element in the LLC header.  A value of -1
             indicates this criterion is not used for
             classification.";
        }
        leaf LLCControlExclude {
          type boolean;
          default "false";
          description
            "If {{false}}, the class includes only those packets
             that match the {{param|LLCControl}} entry, if
             specified.
          
             If {{true}}, the class includes all packets except
             those that match the {{param|LLCControl}} entry, if
             specified.";
        }
        leaf SNAPOUI {
          type int32 {
            range "-1..max";
          }
          default "-1";
          description
            "Classification criterion.
          
             OUI element in the SNAP header.  A value of -1
             indicates this criterion is not used for
             classification.";
        }
        leaf SNAPOUIExclude {
          type boolean;
          default "false";
          description
            "If {{false}}, the class includes only those packets
             that match the {{param|SNAPOUI}} entry, if
             specified.
          
             If {{true}}, the class includes all packets except
             those that match the {{param|SNAPOUI}} entry, if
             specified.";
        }
        leaf SourceVendorClassID {
          type string {
            length "0..255";
          }
          default "";
          description
            "Classification criterion.
          
             Used to identify one or more LAN devices, value of
             the DHCPv4 Vendor Class Identifier (Option 60) as
             defined in {{bibref|RFC2132}}, matched according to
             the criterion in {{param|SourceVendorClassIDMode}}.
             Case sensitive.
          
             This is a normal string, e.g.  \"abc\" is
             represented as \"abc\" and not say \"616263\" hex.
             However, if the value includes non-printing
             characters then such characters have to be
             represented using XML escapes, e.g.  #x0a for
             line-feed.
          
             {{empty}} indicates this criterion is not used for
             classification.
          
             Note: This parameter is DHCPv4-specific.  It only
             applies when {{param|DHCPType}} is
             {{enum|DHCPv4|DHCPType}}.";
        }
        leaf SourceVendorClassIDv6 {
          type yang:hex-string {
            length "0..65535";
          }
          default "";
          description
            "Classification criterion.
          
             A hexbinary string used to identify one or more LAN
             devices, value of the DHCPv6 Vendor Class Identifier
             (Option 16) as defined in {{bibref|RFC3315}}.  The
             option value is binary, so an exact match is
             REQUIRED.
          
             {{empty}} indicates this criterion is not used for
             classification.
          
             Note: This parameter is DHCPv6-specific.  It only
             applies when {{param|DHCPType}} is
             {{enum|DHCPv6|DHCPType}}.";
        }
        leaf SourceVendorClassIDExclude {
          type boolean;
          default "false";
          description
            "If {{false}}, the class includes only those packets
             sourced from LAN devices that match the
             {{param|SourceVendorClassID}} entry (for
             {{enum|DHCPv4|DHCPType}}) or the
             {{param|SourceVendorClassIDv6}} entry (for
             {{enum|DHCPv6|DHCPType}}), if specified.
          
             If {{true}}, the class includes all packets except
             those sourced from LAN devices that match the
             {{param|SourceVendorClassID}} entry (for
             {{enum|DHCPv4|DHCPType}}) or the
             {{param|SourceVendorClassIDv6}} entry (for
             {{enum|DHCPv6|DHCPType}}), if specified.";
        }
        leaf SourceVendorClassIDMode {
          type enumeration {
            enum "Exact";
            enum "Prefix";
            enum "Suffix";
            enum "Substring";
          }
          default "Exact";
          description
            "SourceVendorClassID pattern match criterion.  {{enum}}
          
             For example, if {{param|SourceVendorClassID}} is
             \"Example\" then an Option 60 value of \"Example
             device\" will match with {{param}} values of
             {{enum|Prefix}} or {{enum|Substring}}, but not with
             {{enum|Exact}} or {{enum|Suffix}}.";
        }
        leaf DestVendorClassID {
          type string {
            length "0..255";
          }
          default "";
          description
            "Classification criterion.
          
             Used to identify one or more LAN devices, value of
             the DHCPv4 Vendor Class Identifier (Option 60) as
             defined in {{bibref|RFC2132}}, matched according to
             the criterion in {{param|DestVendorClassIDMode}}.
             Case sensitive.
          
             This is a normal string, e.g.  \"abc\" is
             represented as \"abc\" and not say \"616263\" hex.
             However, if the value includes non-printing
             characters then such characters have to be
             represented using XML escapes, e.g.  #x0a for
             line-feed.
          
             {{empty}} indicates this criterion is not used for
             classification.
          
             Note: This parameter is DHCPv4-specific.  It only
             applies when {{param|DHCPType}} is
             {{enum|DHCPv4|DHCPType}}.";
        }
        leaf DestVendorClassIDv6 {
          type yang:hex-string {
            length "0..65535";
          }
          default "";
          description
            "Classification criterion.
          
             A hexbinary string used to identify one or more LAN
             devices, value of the DHCPv6 Vendor Class Identifier
             (Option 16) as defined in {{bibref|RFC3315}}.  The
             option value is binary, so an exact match is
             REQUIRED.
          
             {{empty}} indicates this criterion is not used for
             classification.
          
             Note: This parameter is DHCPv6-specific.  It only
             applies when {{param|DHCPType}} is
             {{enum|DHCPv6|DHCPType}}.";
        }
        leaf DestVendorClassIDExclude {
          type boolean;
          default "false";
          description
            "If {{false}}, the class includes only those packets
             destined for LAN devices that match the
             {{param|DestVendorClassID}} entry (for
             {{enum|DHCPv4|DHCPType}}) or the
             {{param|DestVendorClassIDv6}} entry (for
             {{enum|DHCPv6|DHCPType}}), if specified.
          
             If {{true}}, the class includes all packets except
             those destined for LAN devices that match the
             {{param|DestVendorClassID}} entry (for
             {{enum|DHCPv4|DHCPType}}) or the
             {{param|DestVendorClassIDv6}} entry (for
             {{enum|DHCPv6|DHCPType}}), if specified.";
        }
        leaf DestVendorClassIDMode {
          type enumeration {
            enum "Exact";
            enum "Prefix";
            enum "Suffix";
            enum "Substring";
          }
          default "Exact";
          description
            "{{param|DestVendorClassID}} pattern match criterion.
             {{enum}}
          
             For example, if {{param|DestVendorClassID}} is
             \"Example\" then an Option 60 value of \"Example
             device\" will match with {{param}} values of
             {{enum|Prefix}} or {{enum|Substring}}, but not with
             {{enum|Exact}} or {{enum|Suffix}}.";
        }
        leaf SourceClientID {
          type yang:hex-string {
            length "0..65535";
          }
          default "";
          description
            "Classification criterion.
          
             A hexbinary string used to identify one or more LAN
             devices, value of the DHCP Client Identifier.  The
             DHCP Client Identifier is Option 61 (as defined in
             {{bibref|RFC2132}}) for {{enum|DHCPv4|DHCPType}}, or
             is Option 1 (as defined in {{bibref|RFC3315}}) for
             {{enum|DHCPv6|DHCPType}}.  The option value is
             binary, so an exact match is REQUIRED.
          
             {{empty}} indicates this criterion is not used for
             classification.
          
             Note: DHCPv4 Option values are limited to a length
             of 255, while DHCPv6 Option values can have a
             maximum length of 65535.
          
             Note: This parameter is DHCP version neutral.  The
             specific DHCP version in use with this parameter is
             indicated by {{param|DHCPType}}.
          
             Note: DHCPv6 Option 1 (Client Identifier) is
             sometimes referred to as ''DUID''.";
        }
        leaf SourceClientIDExclude {
          type boolean;
          default "false";
          description
            "If {{false}}, the class includes only those packets
             sourced from LAN devices that match the
             {{param|SourceClientID}} entry, if specified.
          
             If {{true}}, the class includes all packets except
             those sourced from LAN devices that match the
             {{param|SourceClientID}} entry, if specified.";
        }
        leaf DestClientID {
          type yang:hex-string {
            length "0..65535";
          }
          default "";
          description
            "Classification criterion.
          
             A hexbinary string used to identify one or more LAN
             devices, value of the DHCP Client Identifier.  The
             DHCP Client Identifier is Option 61 (as defined in
             {{bibref|RFC2132}}) for {{enum|DHCPv4|DHCPType}}, or
             is Option 1 (as defined in {{bibref|RFC3315}}) for
             {{enum|DHCPv6|DHCPType}}.  The option value is
             binary, so an exact match is REQUIRED.
          
             {{empty}} indicates this criterion is not used for
             classification.
          
             Note: DHCPv4 Option values are limited to a length
             of 255, while DHCPv6 Option values can have a
             maximum length of 65535.
          
             Note: This parameter is DHCP version neutral.  The
             specific DHCP version in use with this parameter is
             indicated by {{param|DHCPType}}.
          
             Note: DHCPv6 Option 1 (Client Identifier) is
             sometimes referred to as ''DUID''.";
        }
        leaf DestClientIDExclude {
          type boolean;
          default "false";
          description
            "If {{false}}, the class includes only those packets
             destined for LAN devices that match the
             {{param|DestClientID}} entry, if specified.
          
             If {{true}}, the class includes all packets except
             those destined for LAN devices that match the
             {{param|DestClientID}} entry, if specified.";
        }
        leaf SourceUserClassID {
          type yang:hex-string {
            length "0..65535";
          }
          default "";
          description
            "Classification criterion.
          
             A hexbinary string used to identify one or more LAN
             devices, value of the DHCP User Class Identifier.
             The DHCP User Class Identifier is Option 77 (as
             defined in {{bibref|RFC3004}}) for
             {{enum|DHCPv4|DHCPType}}, or is Option 15 (as
             defined in {{bibref|RFC3315}}) for
             {{enum|DHCPv6|DHCPType}}.  The option value is
             binary, so an exact match is REQUIRED.
          
             {{empty}} indicates this criterion is not used for
             classification.
          
             Note: DHCPv4 Option values are limited to a length
             of 255, while DHCPv6 Option values can have a
             maximum length of 65535.
          
             Note: This parameter is DHCP version neutral.  The
             specific DHCP version in use with this parameter is
             indicated by {{param|DHCPType}}.";
        }
        leaf SourceUserClassIDExclude {
          type boolean;
          default "false";
          description
            "If {{false}}, the class includes only those packets
             sourced from LAN devices that match the
             {{param|SourceUserClassID}} entry, if specified.
          
             If {{true}}, the class includes all packets except
             those sourced from LAN devices that match the
             {{param|SourceUserClassID}} entry, if specified.";
        }
        leaf DestUserClassID {
          type yang:hex-string {
            length "0..65535";
          }
          default "";
          description
            "Classification criterion.
          
             A hexbinary string used to identify one or more LAN
             devices, value of the DHCP User Class Identifier.
             The DHCP User Class Identifier is Option 77 (as
             defined in {{bibref|RFC3004}}) for
             {{enum|DHCPv4|DHCPType}}, or is Option 15 (as
             defined in {{bibref|RFC3315}}) for
             {{enum|DHCPv6|DHCPType}}.  The option value is
             binary, so an exact match is REQUIRED.
          
             {{empty}} indicates this criterion is not used for
             classification.
          
             Note: DHCPv4 Option values are limited to a length
             of 255, while DHCPv6 Option values can have a
             maximum length of 65535.
          
             Note: This parameter is DHCP version neutral.  The
             specific DHCP version in use with this parameter is
             indicated by {{param|DHCPType}}.";
        }
        leaf DestUserClassIDExclude {
          type boolean;
          default "false";
          description
            "If {{false}}, the class includes only those packets
             destined for LAN devices that match the
             {{param|DestUserClassID}} entry, if specified.
          
             If {{true}}, the class includes all packets except
             those destined for LAN devices that match the
             {{param|DestUserClassID}} entry, if specified.";
        }
        leaf SourceVendorSpecificInfo {
          type yang:hex-string {
            length "0..65535";
          }
          default "";
          description
            "Classification criterion.
          
             A hexbinary string used to identify one or more LAN
             devices, value of the DHCP Vendor-specific
             Information, matched according to the criteria in
             {{param|SourceVendorSpecificInfoEnterprise}} and
             {{param|SourceVendorSpecificInfoSubOption}}.  The
             DHCP Vendor-specific Information is Option 125 (as
             defined in {{bibref|RFC3925}}) for
             {{enum|DHCPv4|DHCPType}}, or is Option 17 (as
             defined in {{bibref|RFC3315}}) for
             {{enum|DHCPv6|DHCPType}}.
          
             {{empty}} indicates this criterion is not used for
             classification.
          
             Note: DHCPv4 Option values are limited to a length
             of 255, while DHCPv6 Option values can have a
             maximum length of 65535.
          
             Note: This parameter is DHCP version neutral.  The
             specific DHCP version in use with this parameter is
             indicated by {{param|DHCPType}}.";
        }
        leaf SourceVendorSpecificInfoExclude {
          type boolean;
          default "false";
          description
            "If {{false}}, the class includes only those packets
             sourced from LAN devices that match the
             {{param|SourceVendorSpecificInfo}} entry, if
             specified.
          
             If {{true}}, the class includes all packets except
             those sourced from LAN devices that match the
             {{param|SourceVendorSpecificInfo}} entry, if
             specified.";
        }
        leaf SourceVendorSpecificInfoEnterprise {
          type uint32;
          default "0";
          description
            "{{param|SourceVendorSpecificInfo}} Enterprise Number as
             defined in {{bibref|RFC3925}}.
          
             The default value (0) is assigned to IANA and will
             probably need to be replaced with an appropriate
             enterprise number.";
        }
        leaf SourceVendorSpecificInfoSubOption {
          type int32 {
            range "0..255";
          }
          default "0";
          description
            "{{param|SourceVendorSpecificInfo}} Sub Option Code as
             defined in {{bibref|RFC3925}}.";
        }
        leaf DestVendorSpecificInfo {
          type yang:hex-string {
            length "0..65535";
          }
          default "";
          description
            "Classification criterion.
          
             A hexbinary string used to identify one or more LAN
             devices, value of the DHCP Vendor-specific
             Information, matched according to the criteria in
             {{param|DestVendorSpecificInfoEnterprise}} and
             {{param|DestVendorSpecificInfoSubOption}}.  The DHCP
             Vendor-specific Information is Option 125 (as
             defined in {{bibref|RFC3925}}) for
             {{enum|DHCPv4|DHCPType}}, or is Option 17 (as
             defined in {{bibref|RFC3315}}) for
             {{enum|DHCPv6|DHCPType}}.
          
             {{empty}} indicates this criterion is not used for
             classification.
          
             Note: DHCPv4 Option values are limited to a length
             of 255, while DHCPv6 Option values can have a
             maximum length of 65535.
          
             Note: This parameter is DHCP version neutral.  The
             specific DHCP version in use with this parameter is
             indicated by {{param|DHCPType}}.";
        }
        leaf DestVendorSpecificInfoExclude {
          type boolean;
          default "false";
          description
            "If {{false}}, the class includes only those packets
             destined for LAN devices that match the
             {{param|DestVendorSpecificInfo}} entry, if
             specified.
          
             If {{true}}, the class includes all packets except
             those destined for LAN devices that match the
             {{param|DestVendorSpecificInfo}} entry, if
             specified.";
        }
        leaf DestVendorSpecificInfoEnterprise {
          type uint32;
          default "0";
          description
            "{{param|DestVendorSpecificInfo}} Enterprise Number as
             defined in {{bibref|RFC3925}}.
          
             The default value (0) is assigned to IANA and will
             probably need to be replaced with an appropriate
             enterprise number.";
        }
        leaf DestVendorSpecificInfoSubOption {
          type int32 {
            range "0..255";
          }
          default "0";
          description
            "{{param|DestVendorSpecificInfo}} Sub Option Code as
             defined in {{bibref|RFC3925}}.";
        }
        leaf TCPACK {
          type boolean;
          default "false";
          description
            "Classification criterion.
          
             If {{false}}, this criterion is not used for
             classification.
          
             If {{true}}, this criterion matches with all TCP
             segments that have the ACK control bit set.";
        }
        leaf TCPACKExclude {
          type boolean;
          default "false";
          description
            "If {{false}}, the class includes only those packets
             that match the {{param|TCPACK}} entry, if specified.
          
             If {{true}}, the class includes all packets except
             those that match the {{param|TCPACK}} entry, if
             specified.";
        }
        leaf IPLengthMin {
          type uint32;
          default "0";
          description
            "Classification criterion.
          
             Minimum IP Packet Length (including header) in
             bytes.";
        }
        leaf IPLengthMax {
          type uint32;
          default "0";
          description
            "Classification criterion.
          
             Maximum IP Packet Length (including header) in
             bytes.
          
             A value of zero indicates that no maximum is
             specified (an umlimited maximum length).";
        }
        leaf IPLengthExclude {
          type boolean;
          default "false";
          description
            "If {{false}}, the class includes only those packets
             whose length (including header) falls within the
             inclusive range {{param|IPLengthMin}} through
             {{param|IPLengthMax}}.  A value of zero for both
             {{param|IPLengthMin}} and {{param|IPLengthMax}}
             allows any length packet.  An equal non-zero value
             of {{param|IPLengthMin}} and {{param|IPLengthMax}}
             allows only a packet with the exact length
             specified.
          
             If {{true}}, the class includes all packets except
             those whose length (including header) falls within
             the inclusive range {{param|IPLengthMin}} through
             {{param|IPLengthMax}}.";
        }
        leaf DSCPCheck {
          type int32 {
            range "-1..63";
          }
          default "-1";
          description
            "Classification criterion.
          
             DiffServ codepoint (defined in {{bibref|RFC2474}}).
          
             If set to a Class Selector Codepoint (defined in
             {{bibref|RFC2474}}), all DSCP values that match the
             first 3 bits will be considered a valid match.
          
             A value of -1 indicates this criterion is not used
             for classification.";
        }
        leaf DSCPExclude {
          type boolean;
          default "false";
          description
            "If {{false}}, the class includes only those packets
             that match the {{param|DSCPCheck}} entry, if
             specified.
          
             If {{true}}, the class includes all packets except
             those that match the {{param|DSCPCheck}} entry, if
             specified.";
        }
        leaf DSCPMark {
          type int32 {
            range "-2..max";
          }
          default "-1";
          description
            "Classification result.
          
             DSCP to mark traffic with that falls into this
             classification entry.
          
             A value of -1 indicates no change from the incoming
             packet.
          
             A value of -2 indicates automatic marking of DSCP
             based upon the EthernetPriority value of the
             incoming packet as defined in
             {{bibref|TR-181i2|Annex A}}.";
        }
        leaf EthernetPriorityCheck {
          type int32 {
            range "-1..max";
          }
          default "-1";
          description
            "Classification criterion.
          
             Current Ethernet priority of a VLAN Tag as defined
             in {{bibref|802.1Q-2011}} or Ethernet Priority field
             as defined in 802.1D.  If more than 1 VLAN tag is
             present, then this parameter represents the outer
             VLAN Tag.  A value of -1 indicates this criterion is
             not used for classification.";
        }
        leaf EthernetPriorityExclude {
          type boolean;
          default "false";
          description
            "If {{false}}, the class includes only those packets
             that match the {{param|EthernetPriorityCheck}}
             entry, if specified.
          
             If {{true}}, the class includes all packets except
             those that match the {{param|EthernetPriorityCheck}}
             entry, if specified.";
        }
        leaf EthernetPriorityMark {
          type int32 {
            range "-2..max";
          }
          default "-1";
          description
            "Classification result.
          
             Ethernet priority code (as defined in
             {{bibref|802.1Q-2011}}) to mark traffic with that
             falls into this classification entry associated with
             the {{param|EthernetPriorityCheck}}.
          
             A value of -1 indicates no change from the incoming
             packet.
          
             A value of -2 indicates automatic marking of
             EthernetPriority based upon the DSCP value of the
             incoming packet as defined in
             {{bibref|TR-181i2|Annex A}}.";
        }
        leaf InnerEthernetPriorityCheck {
          type int32 {
            range "-1..max";
          }
          default "-1";
          description
            "Classification criterion.
          
             Current Ethernet priority of the inner VLAN Tag as
             defined in 802.1Q.  This parameter is only
             applicable when the PDU has 2 VLAN Tags.  A value of
             -1 indicates this criterion is not used for
             classification.";
        }
        leaf InnerEthernetPriorityExclude {
          type boolean;
          default "false";
          description
            "If {{false}}, the class includes only those packets
             that match the {{param|InnerEthernetPriorityCheck}}
             entry, if specified.
          
             If {{true}}, the class includes all packets except
             those that match the
             {{param|InnerEthernetPriorityCheck}} entry, if
             specified.";
        }
        leaf InnerEthernetPriorityMark {
          type int32 {
            range "-2..max";
          }
          default "-1";
          description
            "Classification result.
          
             Ethernet priority code to mark traffic with that
             falls into this classification entry associated with
             the {{param|InnerEthernetPriorityCheck}}.
          
             A value of -1 indicates no change from the incoming
             packet.
          
             A value of -2 indicates automatic marking of
             EthernetPriority based upon the DSCP value of the
             incoming packet as defined in
             {{bibref|TR-181i2|Annex A}}.";
        }
        leaf EthernetDEICheck {
          type int32 {
            range "-1..max";
          }
          default "-1";
          description
            "Classification criterion.
          
             Current Ethernet Drop eligible Indication (DEI) of
             the VLAN tag as defined in 802.1Q.  If 2 VLAN Tags
             are present, then this parameter represents the
             outer VLAN tag.  A value of -1 indicates this
             criterion is not used for classification.";
        }
        leaf EthernetDEIExclude {
          type boolean;
          default "false";
          description
            "If {{false}}, the class includes only those packets
             that match the {{param|EthernetDEICheck}} entry, if
             specified.
          
             If {{true}}, the class includes all packets except
             those that match the {{param|EthernetDEICheck}}
             entry, if specified.";
        }
        leaf VLANIDCheck {
          type int32 {
            range "-1..max";
          }
          default "-1";
          description
            "Classification criterion.
          
             Current Ethernet VLAN ID as defined in 802.1Q.  A
             value of -1 indicates this criterion is not used for
             classification.";
        }
        leaf VLANIDExclude {
          type boolean;
          default "false";
          description
            "If {{false}}, the class includes only those packets
             that match the {{param|VLANIDCheck}} entry, if
             specified.
          
             If {{true}}, the class includes all packets except
             those that match the {{param|VLANIDCheck}} entry, if
             specified.";
        }
        leaf OutOfBandInfo {
          type int32 {
            range "-1..max";
          }
          default "-1";
          description
            "Classification criterion.
          
             Allows traffic to be distinguished based on
             out-of-band information such as physical port or
             application ID.  Primarily intended for, but not
             restricted to, locally sourced traffic.
          
             If specified, this entry applies to traffic with
             matching out-of-band information.  A value of -1
             indicates this criterion is not used for
             classification.";
        }
        leaf ForwardingPolicy {
          type uint32;
          default "0";
          description
            "Classification result.
          
             Identifier of the forwarding policy associated with
             traffic that falls in this classification.";
        }
        leaf TrafficClass {
          type int32 {
            range "-1..max";
          }
          default "-1";
          description
            "Classification result.
          
             Identifier of the traffic class associated with
             traffic that falls in this classification.  If
             specified, at least one {{object|#.Queue}} table
             entry MUST include this traffic class in its
             {{param|#.Queue.{i}.TrafficClasses}} parameter
             (which is a comma-separated list).
          
             A value of -1 indicates a null traffic class.
          
             {{param}} and {{param|App}} are mutually exclusive
             and one of the two MUST be specified.  If {{param}}
             is {{null}}, {{param|App}} MUST be specified, and
             vice versa.";
        }
        leaf Policer {
          type string {
            length "0..256";
          }
          default "";
          description
            "Classification result.  {{reference}}
          
             Indicates the ''Policer'' table entry for traffic
             that falls in this classification.
          
             {{empty}} indicates a null policer.
          
             {{param}} MAY optionally be specified in conjunction
             with {{param|TrafficClass}}.  {{param}} and
             {{param|App}} are mutually exclusive.";
        }
        leaf App {
          type string {
            length "0..256";
          }
          default "";
          description
            "Classification result.  {{reference}}
          
             Indicates the ''App'' table entry for traffic that
             falls in this classification.
          
             {{empty}} indicates a null ''App''.
          
             {{param|TrafficClass}} and {{param}} are mutually
             exclusive and one of the two MUST be specified.  If
             {{param|TrafficClass}} is null, {{param}} MUST be
             specified, and vice versa.";
        }
      }

      list App {
        key "Alias";
        description
          "Application table.";
        leaf Enable {
          type boolean;
          default "false";
          description
            "Enables or disables this App table entry.";
        }
        leaf Status {
          type enumeration {
            enum "Disabled";
            enum "Enabled";
            enum "Error";
          }
          config false;
          default "Disabled";
          description
            "The status of this App table entry.  {{enum}}
          
             The {{enum|Error}} value MAY be used by the CPE to
             indicate a locally defined error condition.";
        }
        leaf ProtocolIdentifier {
          type string {
            length "0..256";
          }
          default "";
          description
            "URN identifying the protocol associated with the given
             application.  A set of defined URNs is given in
             {{bibref|TR-181i2|Annex A}}.";
        }
        leaf Name {
          type string {
            length "0..64";
          }
          default "";
          description
            "Human-readable name associated with this entry in the
             App table.";
        }
        leaf DefaultForwardingPolicy {
          type uint32;
          default "0";
          description
            "Identifier of the forwarding policy associated with
             traffic associated with this App table entry, but
             not associated with any specified flow.";
        }
        leaf DefaultTrafficClass {
          type uint32;
          default "0";
          description
            "Identifier of the traffic class associated with traffic
             associated with this App table entry, but not
             associated with any specified flow.";
        }
        leaf DefaultPolicer {
          type string {
            length "0..256";
          }
          default "";
          description
            "{{reference}} Indicates the ''Policer'' table entry for
             traffic associated with this {{object}} table entry,
             but not associated with any specified flow.
          
             {{empty}} indicates a null policer.";
        }
        leaf DefaultDSCPMark {
          type int32 {
            range "-2..max";
          }
          default "-1";
          description
            "DSCP to mark traffic associated with this App table
             entry, but not associated with any specified flow.
          
             A value of -1 indicates no change from the incoming
             packet.
          
             A value of -2 indicates automatic marking of DSCP
             based upon the EthernetPriority value of the
             incoming packet as defined in
             {{bibref|TR-181i2|Annex A}}.";
        }
        leaf DefaultEthernetPriorityMark {
          type int32 {
            range "-2..max";
          }
          default "-1";
          description
            "Ethernet priority code (as defined in
             {{bibref|802.1Q-2011}}) to mark traffic associated
             with this App table entry, but not associated with
             any specified flow.
          
             A value of -1 indicates no change from the incoming
             packet.
          
             A value of -2 indicates automatic marking of
             EthernetPriority based upon the DSCP value of the
             incoming packet as defined in
             {{bibref|TR-181i2a5|Annex A}}.";
        }
        leaf DefaultInnerEthernetPriorityMark {
          type int32 {
            range "-2..max";
          }
          description
            "Ethernet priority code (as defined in
             {{bibref|802.1Q-2011}}) to mark the inner VLAN Tags
             as defined in 802.1Q with this {{object}} table
             entry where the packet is not associated with any
             specified flow.  This parameter is only applicable
             when the PDU has 2 VLAN Tags.
          
             A value of -1 indicates no change from the incoming
             packet.
          
             A value of -2 indicates automatic marking of
             EthernetPriority based upon the DSCP value of the
             incoming packet as defined in
             {{bibref|TR-181i2|Annex A}}.";
        }
      }

      list Flow {
        key "Alias";
        description
          "Flow table.";
        leaf Enable {
          type boolean;
          default "false";
          description
            "Enables or disables this Flow table entry.";
        }
        leaf Status {
          type enumeration {
            enum "Disabled";
            enum "Enabled";
            enum "Error";
          }
          config false;
          default "Disabled";
          description
            "The status of this Flow table entry.  {{enum}}
          
             The {{enum|Error}} value MAY be used by the CPE to
             indicate a locally defined error condition.";
        }
        leaf Type {
          type string {
            length "0..256";
          }
          default "";
          description
            "URN identifying the type of flow to be associated with
             the specified policer.  A set of defined URNs is
             given in {{bibref|TR-181i2|Annex A}}.";
        }
        leaf TypeParameters {
          type string {
            length "0..256";
          }
          default "";
          description
            "List of name-value pairs representing additional
             criteria to identify the flow type.  The use and
             interpretation is specific to the particular
             FlowType URN.Encoded using the
             \"x-www-form-urlencoded\" content type defined in
             {{bibref|HTML4.01}}.";
        }
        leaf Name {
          type string {
            length "0..64";
          }
          default "";
          description
            "Human-readable name associated with this entry in the
             Flow table.";
        }
        leaf App {
          type string {
            length "0..256";
          }
          default "";
          description
            "{{reference}} Indicates the ''App'' table entry
             associated with this flow.  {{empty}} indicates the
             flow table is not associated with any App table
             entry.";
        }
        leaf ForwardingPolicy {
          type uint32;
          default "0";
          description
            "Identifier of the forwarding policy associated with
             this flow.";
        }
        leaf TrafficClass {
          type uint32;
          default "0";
          description
            "Identifier of the traffic class associated with this
             flow.";
        }
        leaf Policer {
          type string {
            length "0..256";
          }
          default "";
          description
            "{{reference}} Indicates the ''Policer'' table entry for
             traffic that falls in this flow.
          
             {{empty}} indicates a null policer.";
        }
        leaf DSCPMark {
          type int32 {
            range "-2..max";
          }
          default "-1";
          description
            "DSCP to mark traffic with that falls into this flow.
          
             A value of -1 indicates no change from the incoming
             packet.
          
             A value of -2 indicates automatic marking of DSCP
             based upon the EthernetPriority value of the
             incoming packet as defined in
             {{bibref|TR-181i2|Annex A}}.";
        }
        leaf EthernetPriorityMark {
          type int32 {
            range "-2..max";
          }
          default "-1";
          description
            "Ethernet priority code (as defined in
             {{bibref|802.1Q-2011}}) to mark traffic with that
             falls into this flow.
          
             A value of -1 indicates no change from the incoming
             packet.
          
             A value of -2 indicates automatic marking of
             EthernetPriority based upon the DSCP value of the
             incoming packet as defined in
             {{bibref|TR-181i2a5|Annex A}}.";
        }
        leaf InnerEthernetPriorityMark {
          type int32 {
            range "-2..max";
          }
          default "-1";
          description
            "Ethernet priority code (as defined in
             {{bibref|802.1Q-2011}}) to mark the inner VLAN Tags
             with for traffic that falls into this flow.
          
             A value of -1 indicates no change from the incoming
             packet.
          
             A value of -2 indicates automatic marking of
             EthernetPriority based upon the DSCP value of the
             incoming packet as defined in
             {{bibref|TR-181i2|Annex A}}.";
        }
      }

      list Policer {
        key "Alias";
        description
          "Policer table.";
        leaf Enable {
          type boolean;
          default "false";
          description
            "Enables or disables this policer.";
        }
        leaf Status {
          type enumeration {
            enum "Disabled";
            enum "Enabled";
            enum "Error";
          }
          config false;
          default "Disabled";
          description
            "The status of this policer.  {{enum}}
          
             The {{enum|Error}} value MAY be used by the CPE to
             indicate a locally defined error condition.";
        }
        leaf CommittedRate {
          type uint32;
          default "0";
          description
            "Committed rate allowed for this policer in {{units}}.";
        }
        leaf CommittedBurstSize {
          type uint32;
          default "0";
          description
            "Committed Burstsize in bytes.";
        }
        leaf ExcessBurstSize {
          type uint32;
          default "0";
          description
            "Excess Burstsize in bytes.
          
             Applied for a
             {{enum|SingleRateThreeColor|MeterType}} meter.";
        }
        leaf PeakRate {
          type uint32;
          default "0";
          description
            "Peak rate allowed for this Meter in {{units}}.
          
             Applied for {{enum|TwoRateThreeColor|MeterType}}
             meters.";
        }
        leaf PeakBurstSize {
          type uint32;
          default "0";
          description
            "Peak Burstsize in bytes.
          
             Applied for {{enum|TwoRateThreeColor|MeterType}}
             meters.";
        }
        leaf MeterType {
          type string;
          default "SimpleTokenBucket";
          description
            "Identifies the method of traffic measurement to be used
             for this policer.  {{enum}}
          
             {{enum|SimpleTokenBucket}} makes use of
             {{param|CommittedRate}} and
             {{param|CommittedBurstSize}}.
          
             {{enum|SingleRateThreeColor}} makes use of
             {{param|CommittedRate}},
             {{param|CommittedBurstSize}}, and
             {{param|ExcessBurstSize}} as defined in
             {{bibref|RFC2697}}.
          
             {{enum|TwoRateThreeColor}} makes use of
             {{param|CommittedRate}},
             {{param|CommittedBurstSize}}, {{param|PeakRate}},
             and {{param|PeakBurstSize}} as defined in
             {{bibref|RFC2698}}.";
        }
        leaf PossibleMeterTypes {
          type enumeration {
            enum "SimpleTokenBucket";
            enum "SingleRateThreeColor";
            enum "TwoRateThreeColor";
          }
          config false;
          description
            "{{list}} Indicates supported meter types.";
        }
        leaf ConformingAction {
          type string {
            pattern "Null";
            pattern "Drop";
            pattern "[0-9]|[1-5][0-9]|6[0-3]";
            pattern ":[0-7]";
            pattern "([0-9]|[1-5][0-9]|6[0-3]):[0-7]";
          }
          default "Null";
          description
            "Instructions for how to handle traffic that is
             conforming.  {{pattern}}
          
             {{pattern|Null}} corresponds with no action.
          
             ''<DSCP Value>'' is an unsigned integer that
             corresponds with a mark action overwriting the
             traffic's DSCP with the configured DSCP.
          
             ''<:Ethernet Priority>'' is a colon (\":\") followed
             by an unsigned integer (no white space).  It
             corresponds with a mark action overwriting the
             traffic's Ethernet Priority with the configured
             Ethernet Priority.
          
             ''<DSCP Value:Ethernet Priority>'' is an unsigned
             integer followed by a colon (\":\") and a second
             unsigned integer (no white space).  It corresponds
             with a mark action overwriting the traffic's DSCP
             and Ethernet Priority with the configured values.
          
             For example, \"24\" specifies a DSCP value of 24,
             \":3\" specifies an Ethernet Priority of 3, and
             \"24:3\" specifies both.";
        }
        leaf PartialConformingAction {
          type string {
            pattern "Null";
            pattern "Drop";
            pattern "[0-9]|[1-5][0-9]|6[0-3]";
            pattern ":[0-7]";
            pattern "([0-9]|[1-5][0-9]|6[0-3]):[0-7]";
          }
          default "Drop";
          description
            "Instructions for how to handle traffic that is
             partially conforming (colored yellow).  {{pattern}}
          
             {{pattern|Null}} corresponds with no action.
          
             ''<DSCP Value>'' is an unsigned integer that
             corresponds with a mark action overwriting the
             traffic's DSCP with the configured DSCP.Only applies
             for three-color meters.
          
             ''<:Ethernet Priority>'' is a colon (\":\") followed
             by an unsigned integer (no white space).  It
             corresponds with a mark action overwriting the
             traffic's Ethernet Priority with the configured
             Ethernet Priority.
          
             ''<DSCP Value:Ethernet Priority>'' is an unsigned
             integer followed by a colon (\":\") and a second
             unsigned integer (no white space).  It corresponds
             with a mark action overwriting the traffic's DSCP
             and Ethernet Priority with the configured values.
          
             For example, \"24\" specifies a DSCP value of 24,
             \":3\" specifies an Ethernet Priority of 3, and
             \"24:3\" specifies both.";
        }
        leaf NonConformingAction {
          type string {
            pattern "Null";
            pattern "Drop";
            pattern "[0-9]|[1-5][0-9]|6[0-3]";
            pattern ":[0-7]";
            pattern "([0-9]|[1-5][0-9]|6[0-3]):[0-7]";
          }
          default "Drop";
          description
            "Instructions for how to handle traffic that is
             non-conforming.  {{pattern}}
          
             {{pattern|Null}} corresponds with no action.
          
             ''<DSCP Value>'' is an unsigned integer that
             corresponds with a mark action overwriting the
             traffic's DSCP with the configured DSCP.
          
             ''<:Ethernet Priority>'' is a colon (\":\") followed
             by an unsigned integer (no white space).  It
             corresponds with a mark action overwriting the
             traffic's Ethernet Priority with the configured
             Ethernet Priority.
          
             ''<DSCP Value:Ethernet Priority>'' is an unsigned
             integer followed by a colon (\":\") and a second
             unsigned integer (no white space).  It corresponds
             with a mark action overwriting the traffic's DSCP
             and Ethernet Priority with the configured values.
          
             For example, \"24\" specifies a DSCP value of 24,
             \":3\" specifies an Ethernet Priority of 3, and
             \"24:3\" specifies both.";
        }
        leaf TotalCountedPackets {
          type uint32;
          config false;
          default "0";
          description
            "Total number of Packets counted by this policer,
             regardless of meter action.";
        }
        leaf TotalCountedBytes {
          type uint32;
          config false;
          default "0";
          description
            "Total number of Bytes counted by this policer,
             regardless of meter action.";
        }
        leaf ConformingCountedPackets {
          type uint32;
          config false;
          default "0";
          description
            "Number of conforming Packets counted by this policer,
             regardless of meter action.";
        }
        leaf ConformingCountedBytes {
          type uint32;
          config false;
          default "0";
          description
            "Number of conforming Bytes counted by this policer,
             regardless of meter action.";
        }
        leaf PartiallyConformingCountedPackets {
          type uint32;
          config false;
          default "0";
          description
            "Number of partially conforming Packets counted by this
             policer, regardless of meter action.";
        }
        leaf PartiallyConformingCountedBytes {
          type uint32;
          config false;
          default "0";
          description
            "Number of partially conforming Bytes counted by this
             policer, regardless of meter action.";
        }
        leaf NonConformingCountedPackets {
          type uint32;
          config false;
          default "0";
          description
            "Number of non-conforming Packets counted by this
             policer, regardless of meter action.";
        }
        leaf NonConformingCountedBytes {
          type uint32;
          config false;
          default "0";
          description
            "Number of non-conforming Bytes counted by this policer,
             regardless of meter action.";
        }
      }

      list Queue {
        key "Alias";
        description
          "Queue table.  Each entry is associated with a set of
           traffic classes, which are specified via the
           {{param|TrafficClasses}} parameter, and is configured
           with weight, precedence, drop algorithm, scheduler
           algorithm etc as appropriate for the traffic classes.
           An entry can be associated either with all egress
           interfaces (in which case an actual queue will be
           instantiated on each egress interface on which traffic
           of that traffic class can be generated) or else with a
           single specified egress interface.
        
           For enabled table entries, if {{param|Interface}} is
           not a valid reference and {{param|AllInterfaces}} is
           {{false}}, then the table entry is inoperable and the
           CPE MUST set {{param|Status}} to
           {{enum|Error_Misconfigured|Status}}.";
        leaf Enable {
          type boolean;
          default "false";
          description
            "Enables or disables this queue.";
        }
        leaf Status {
          type enumeration {
            enum "Disabled";
            enum "Enabled";
            enum "Error_Misconfigured";
            enum "Error";
          }
          config false;
          default "Disabled";
          description
            "The status of this queue.  {{enum}}
          
             The {{enum|Error_Misconfigured}} value indicates
             that a necessary configuration value is undefined or
             invalid.
          
             The {{enum|Error}} value MAY be used by the CPE to
             indicate a locally defined error condition.";
        }
        leaf TrafficClasses {
          type uint32;
          default "";
          description
            "{{list}} Each list item identifies the set of traffic
             classes associated with this queue.
          
             Traffic is sent to this queue if a
             {{object|#.Classification}}, {{object|#.App}} or
             {{object|#.Flow}} table entry specifies a traffic
             class, e.g.  via the
             {{param|#.Classification.{i}.TrafficClass}}
             parameter.
          
             If more than one queue on a given egress interface
             is associated with a given traffic class, the
             implementation will choose which queue to send
             traffic of this class to.";
        }
        leaf Interface {
          type string {
            length "0..256";
          }
          default "";
          description
            "{{reference}} Specifies the egress interface for which
             the specified queue MUST exist.
          
             This MAY be a layer 1, 2 or 3 interface, however,
             the types of interfaces for which ''Queues'' can be
             instantiated is a local matter to the CPE.";
        }
        leaf AllInterfaces {
          type boolean;
          default "false";
          description
            "Indicates that the specified queue MUST exist for all
             egress interfaces (i.e.  this queue entry is to
             apply to all egress interfaces).  If {{true}}, the
             value of {{param|Interface}} is ignored since all
             egress interfaces are indicated.";
        }
        leaf HardwareAssisted {
          type boolean;
          config false;
          default "false";
          description
            "Indicates whether ''all'' the queues corresponding to
             this table entry are hardware assisted.  If any of
             the queues corresponding to this table entry are not
             hardware assisted, the parameter value MUST be
             {{false}}.";
        }
        leaf BufferLength {
          type uint32;
          config false;
          description
            "Number of bytes in the buffer.
          
             Queue buffer size for all egress interfaces for
             which this queue exists.  If the buffer size is not
             the same for all such egress interfaces, this
             parameter MUST be 0.";
        }
        leaf Weight {
          type uint32;
          default "0";
          description
            "Weight of this queue in case of
             {{enum|WFQ|SchedulerAlgorithm}} or
             {{enum|WRR|SchedulerAlgorithm}}, but only used for
             queues of equal precedence.";
        }
        leaf Precedence {
          type uint32 {
            range "1..max";
          }
          default "1";
          description
            "Precedence of this queue relative to others.  Lower
             numbers imply greater precedence.";
        }
        leaf REDThreshold {
          type uint32 {
            range "min..100";
          }
          default "0";
          description
            "Random Early Detection threshold, used only when
             {{param|DropAlgorithm}} is
             {{enum|RED|DropAlgorithm}}.
          
             This is the minimum threshold (''min_th'') and is
             measured as a percentage of the queue size.  If the
             value is set to zero, the CPE MUST choose a sensible
             value, e.g.  5 (but the value MUST still read back
             as zero).
          
             In this version of the data model, there is no way
             to set the maximum threshold (''max_th'').  The CPE
             MUST choose a sensible value, e.g.  three times the
             minimum threshold.
          
             In this version of the data model, there is no way
             to set the RED weight (''w_q'').  The CPE MUST
             choose a sensible value, e.g.  0.002.";
        }
        leaf REDPercentage {
          type uint32 {
            range "min..100";
          }
          default "0";
          description
            "Random Early Detection percentage, used only when
             {{param|DropAlgorithm}} is
             {{enum|RED|DropAlgorithm}}.
          
             This is the maximum value of the packet marking
             probability (''max_p'').  If the value is set to
             zero, the CPE MUST choose a sensible value, e.g.  10
             (but the value MUST still read back as zero).
          
             In this version of the data model, there is no way
             to set the RED weight (''w_q'').  The CPE MUST
             choose a sensible value, e.g.  0.002.";
        }
        leaf DropAlgorithm {
          type enumeration {
            enum "RED";
            enum "DT";
            enum "WRED";
            enum "BLUE";
          }
          default "DT";
          description
            "Dropping algorithm used for this queue if congested.";
        }
        leaf SchedulerAlgorithm {
          type enumeration {
            enum "WFQ";
            enum "WRR";
            enum "SP";
          }
          default "SP";
          description
            "Scheduling Algorithm used by scheduler.";
        }
        leaf ShapingRate {
          type int32 {
            range "-1..max";
          }
          default "-1";
          description
            "Rate to shape this queue's traffic to.  For leaky
             bucket (constant rate shaping), this is the constant
             rate.  For token bucket (variable rate shaping),
             this is the average rate.
          
             If <= 100, in percent of the rate of the highest
             rate-constrained layer over which the packet will
             travel on egress.
          
             If > 100, in bits per second.
          
             A value of -1 indicates no shaping.
          
             For example, for packets destined for a WAN DSL
             interface, if the egress will be on a PPP or IP link
             with a specified ''ShapingRate'', the percentage is
             calculated relative to this rate.  Otherwise, if the
             ATM layer is rate-constrained, then the rate is
             calculated relative to this rate.  Otherwise, the
             rate is calculated relative to the physical-layer
             DSL rate.";
        }
        leaf ShapingBurstSize {
          type uint32;
          description
            "Burst size in bytes.  For both leaky bucket (constant
             rate shaping) and token bucket (variable rate
             shaping) this is the bucket size and is therefore
             the maximum burst size.";
        }
      }

      list QueueStats {
        key "Queue Interface";
        description
          "Queue statistics table.  This table is managed by the
           ACS, which will create entries only for those {Queue,
           Interface} combinations for which statistics are to be
           collected.
        
           Note: The {{object}} table includes unique key
           parameters that are strong references.  If a strongly
           referenced object is deleted, the CPE will set the
           referencing parameter to {{empty}}.  However, doing so
           under these circumstances might cause the updated
           {{object}} row to then violate the table's unique key
           constraint; if this occurs, the CPE MUST disable the
           offending {{object}} row.";
        leaf Enable {
          type boolean;
          default "false";
          description
            "Enables or disables this object.";
        }
        leaf Status {
          type enumeration {
            enum "Disabled";
            enum "Enabled";
            enum "Error";
          }
          config false;
          default "Disabled";
          description
            "The status of this object.";
        }
        leaf Queue {
          type string {
            length "0..256";
          }
          default "";
          description
            "{{reference}} Indicates ''Queue'' entry with which this
             object is associated.";
        }
        leaf Interface {
          type string {
            length "0..256";
          }
          default "";
          description
            "{{reference}} Specifies the egress interface for which
             this object contains statistics.
          
             This MAY be a layer 1, 2 or 3 interface, however,
             the types of interfaces for which ''QueueStats'' can
             be instantiated is a local matter to the CPE.";
        }
        leaf OutputPackets {
          type uint32;
          config false;
          default "0";
          description
            "Number of packets output through the queue.";
        }
        leaf OutputBytes {
          type uint32;
          config false;
          default "0";
          description
            "Number of bytes output through the queue.";
        }
        leaf DroppedPackets {
          type uint32;
          config false;
          default "0";
          description
            "Number of packets dropped by the queue.";
        }
        leaf DroppedBytes {
          type uint32;
          config false;
          default "0";
          description
            "Number of bytes dropped by the queue.";
        }
        leaf QueueOccupancyPackets {
          type uint32;
          config false;
          default "0";
          description
            "Queue occupancy in packets (gives a measure of queue
             latency).";
        }
        leaf QueueOccupancyPercentage {
          type uint32 {
            range "0..100";
          }
          config false;
          default "0";
          description
            "Queue occupancy measured as a {{units}}, i.e.  100 *
             queue occupancy in bytes / queue size in bytes
             (gives a measure of queue usage).";
        }
      }

      list Shaper {
        key "Interface";
        description
          "Shaper table.  Used to shape the queue(s) associated with
           {{param|Interface}}.  In case of a single queue for
           that interface, determines the egress rate of the
           queue.  In case of multiple queues for that interface
           (possibly with per queue shaping rates), determines
           the aggregate egress rate on that interface.
        
           For enabled table entries, if {{param|Interface}} is
           not a valid reference then the table entry is
           inoperable and the CPE MUST set {{param|Status}} to
           {{enum|Error_Misconfigured|Status}}.
        
           Note: The {{object}} table includes a unique key
           parameter that is a strong reference.  If a strongly
           referenced object is deleted, the CPE will set the
           referencing parameter to {{empty}}.  However, doing so
           under these circumstances might cause the updated
           {{object}} row to then violate the table's unique key
           constraint; if this occurs, the CPE MUST set
           {{param|Status}} to
           {{enum|Error_Misconfigured|Status}} and disable the
           offending {{object}} row.";
        leaf Enable {
          type boolean;
          default "false";
          description
            "Enables or disables this shaper.";
        }
        leaf Status {
          type enumeration {
            enum "Disabled";
            enum "Enabled";
            enum "Error_Misconfigured";
            enum "Error";
          }
          config false;
          default "Disabled";
          description
            "The status of this shaper.  {{enum}}
          
             The {{enum|Error_Misconfigured}} value indicates
             that a necessary configuration value is undefined or
             invalid.
          
             The {{enum|Error}} value MAY be used by the CPE to
             indicate a locally defined error condition.";
        }
        leaf Interface {
          type string {
            length "0..256";
          }
          default "";
          description
            "{{reference}}The interface object associated with this
             ''Shaper'' entry.  It MAY be a layer 1, 2 or 3
             interface, however, the types of interfaces for
             which ''Shapers'' can be instantiated is a local
             matter to the CPE.";
        }
        leaf ShapingRate {
          type int32 {
            range "-1..max";
          }
          default "-1";
          description
            "Rate to shape the associated interface connection's
             egress traffic to.  For leaky bucket (constant rate
             shaping), this is the constant rate.  For token
             bucket (variable rate shaping), this is the average
             rate.
          
             If <= 100, in percent of the rate of the highest
             rate-constrained layer over which the packet will
             travel on egress.
          
             If > 100, in bits per second.
          
             A value of -1 indicates no shaping.
          
             For example, for packets destined for a WAN DSL
             interface, if the ATM layer is rate-constrained,
             then the rate is calculated relative to this rate.
             Otherwise, the rate is calculated relative to the
             physical-layer DSL rate.";
        }
        leaf ShapingBurstSize {
          type uint32;
          description
            "Burst size in bytes.  For both leaky bucket (constant
             rate shaping) and token bucket (variable rate
             shaping) this is the bucket size and is therefore
             the maximum burst size.";
        }
      }
    }

    container LANConfigSecurity {
      description
        "This object contains generic device configuration
         information.";
      leaf ConfigPassword {
        type string {
          length "0..64";
        }
        description
          "A password to allow LAN access to protected
           auto-configuration services.
        
           If the CPE supports TR-064 (LAN-side DSL CPE
           Configuration Protocol), this parameter is to be used
           as the ''dslf-config'' password (as defined in
           TR-064).
        
           If the CPE has a user interface with password
           protection enabled, this parameter is also to be used
           as the user password for password-protected
           operations.  However, this parameter MUST NOT be used
           to set the user password if the parameter
           {{param|.UserInterface.PasswordUserSelectable}} is
           {{true}}.";
      }
    }

    container Hosts {
      config false;
      description
        "This object provides information about each of the hosts on
         the LAN, including those whose IP address was allocated
         by the CPE using DHCP as well as hosts with statically
         allocated IP addresses.  It can also include non-IP
         hosts.";

      list Host {
        key "PhysAddress";
        description
          "Host table.";
        leaf PhysAddress {
          type string {
            length "0..64";
          }
          description
            "Unique physical identifier of the host.  For many layer
             2 technologies this is typically a MAC address.";
        }
        leaf IPAddress {
          type types:IPAddress;
          description
            "Current IP Address of the host.  {{empty}} if no
             address is available.
          
             If more than one IP address for this host is known,
             the CPE will choose a ''primary'' address.  All
             known IP addresses can be listed in the
             {{object|IPv4Address}} and {{object|IPv6Address}}
             tables.";
        }
        leaf AddressSource {
          status deprecated;
          type enumeration {
            enum "DHCP";
            enum "Static";
            enum "AutoIP";
            enum "None";
          }
          description
            "Indicates whether the IP address of the host was
             allocated by the CPE using DHCP, was assigned to the
             host statically, or was assigned using automatic IP
             address allocation.  {{enum}}
          
             This parameter is DEPRECATED because only
             {{enum|None}} and {{enum|DHCP}} made sense (the CPE
             doesn't know whether the address is {{enum|Static}}
             or {{enum|AutoIP}}).  The {{enum|DHCP}} case is now
             handled via the {{param|DHCPClient}} reference.";
        }
        leaf DHCPClient {
          type string;
          description
            "{{reference}} Each list item is the DHCPv4 or DHCPv6
             server's client entry that corresponds to the host.";
        }
        leaf LeaseTimeRemaining {
          status deprecated;
          type int32 {
            range "-1..max";
          }
          description
            "DHCP lease time remaining in {{units}}.  A value of -1
             indicates an infinite lease.  The value MUST be 0
             (zero) if the {{param|AddressSource}} is not
             {{enum|DHCP|AddressSource}}.
          
             This parameter is DEPRECATED because DHCP
             lease/lifetime information can be accessed via the
             {{param|DHCPClient}} reference.";
        }
        leaf AssociatedDevice {
          type string {
            length "0..256";
          }
          description
            "{{noreference}}The value MUST the path name of the
             ''AssociatedDevice'' (or equivalent) table row that
             models the host, or {{null}} if there is no such
             table.
          
             For example:
             ''Device.WiFi.AccessPoint.1.AssociatedDevice.2''";
        }
        leaf Layer1Interface {
          type string {
            length "0..256";
          }
          description
            "{{noreference}}The value MUST be the path name of a row
             in a layer 1 interface table.  If the layer 1 device
             isn’t known, then {{param}} will be {{null}}.
          
             For example: ''Device.Ethernet.Interface.2''";
        }
        leaf Layer3Interface {
          type string {
            length "0..256";
          }
          description
            "{{reference}} If the entry represents a non-IP device,
             then {{param}} will be {{empty}}.";
        }
        leaf VendorClassID {
          status deprecated;
          type string {
            length "0..255";
          }
          description
            "Vendor Class Identifier DHCP option (Option 60) of the
             host.
          
             This is a normal string, e.g.  \"abc\" is
             represented as \"abc\" and not say \"616263\" hex.
             However, if the value includes non-printing
             characters then such characters have to be
             represented using XML escapes, e.g.  #x0a for
             line-feed.
          
             It MAY be defined when {{param|AddressSource}} is
             {{enum|DHCP|AddressSource}}.  {{empty}} indicates
             this option is not used.
          
             Note: DHCPv4 Option values are limited to a length
             of 255, while DHCPv6 Option values can have a
             maximum length of 65535.
          
             This parameter is DEPRECATED because host-supplied
             DHCP options can be accessed via the
             {{param|DHCPClient}} reference.";
        }
        leaf ClientID {
          status deprecated;
          type yang:hex-string {
            length "0..65535";
          }
          description
            "A hexbinary string, Client Identifier DHCP option
             (Option 61) for the specific IP connection of the
             client.  The option value is binary, so an exact
             match is REQUIRED.
          
             It MAY be defined when {{param|AddressSource}} is
             {{enum|DHCP|AddressSource}}.  {{empty}} indicates
             this option is not used.
          
             Note: DHCPv4 Option values are limited to a length
             of 255, while DHCPv6 Option values can have a
             maximum length of 65535.
          
             This parameter is DEPRECATED because host-supplied
             DHCP options can be accessed via the
             {{param|DHCPClient}} reference.";
        }
        leaf UserClassID {
          status deprecated;
          type yang:hex-string {
            length "0..65535";
          }
          description
            "A hexbinary string, User Class Identifier DHCP option
             (Option 77) of the host.
          
             It MAY be defined when {{param|AddressSource}} is
             {{enum|DHCP|AddressSource}}.  {{empty}} indicates
             this option is not used.
          
             Note: DHCPv4 Option values are limited to a length
             of 255, while DHCPv6 Option values can have a
             maximum length of 65535.
          
             This parameter is DEPRECATED because host-supplied
             DHCP options can be accessed via the
             {{param|DHCPClient}} reference.";
        }
        leaf HostName {
          type string {
            length "0..64";
          }
          description
            "The device's host name or {{empty}} if unknown.";
        }
        leaf Active {
          type boolean;
          description
            "Whether or not the host is currently present on the
             LAN.  The method of presence detection is a local
             matter to the CPE.
          
             The ability to list inactive hosts is OPTIONAL.  If
             the CPE includes inactive hosts in this table,
             {{param}} MUST be set to {{false}} for each inactive
             host.  The length of time an inactive host remains
             listed in this table is a local matter to the CPE.";
        }
        leaf ActiveLastChange {
          type yang:date-and-time;
          description
            "The datetime when {{param|Active}} last changed from
             {{true}} to {{false}} or from {{false}} to {{true}}.
             The initial detection of a host SHOULD be treated as
             a transition from {{false}} to {{true}}, showing the
             datetime when the host was first detected.
          
             The ability to list inactive hosts is OPTIONAL.  The
             length of time an inactive host remains listed in
             this table is a local matter to the CPE.
          
             {{issue|PTH-HOST|I changed ''should'' to ''SHOULD''
             (also used {{false}} and {{true}}).}}";
        }

        list IPv4Address {
          key "IPAddress";
          description
            "The host's known IPv4 addresses.  This includes any
             addresses assigned via DHCP, which can also be
             accessed via the {{param|#.DHCPClient}} reference.";
          leaf IPAddress {
            type types:IPv4Address;
            description
              "IPv4 address.";
          }
        }

        list IPv6Address {
          key "IPAddress";
          description
            "The host's known IPv6 addresses.  This includes any
             addresses assigned via DHCP, which can also be
             accessed via the {{param|#.DHCPClient}} reference.";
          leaf IPAddress {
            type types:IPv6Address;
            description
              "IPv6 address.";
          }
        }
      }
    }

    container DNS {
      description
        "Properties for Domain Name Service (DNS).";
      leaf SupportedRecordTypes {
        type enumeration {
          enum "A";
          enum "AAAA";
          enum "SRV";
          enum "PTR";
        }
        config false;
        description
          "The DNS record types that are supported by the device.
           {{enum}}";
      }

      container Client {
        description
          "Client properties for Domain Name Service (DNS).  The DNS
           client resolves FQDN on behalf of device internal
           (client) applications.";
        leaf Enable {
          type boolean;
          description
            "Enables or disables the DNS client.";
        }
        leaf Status {
          type enumeration {
            enum "Disabled";
            enum "Enabled";
            enum "Error";
          }
          config false;
          description
            "The status of the DNS client.  {{enum}}
          
             The {{enum|Error}} value MAY be used by the CPE to
             indicate a locally defined error condition.";
        }

        list Server {
          key "DNSServer";
          description
            "This table contains the DNS Server IP address to be
             used by the DHCP Client (it does ''not'' model a DNS
             Server).  Entries are either automatically created
             as result of DHCP (v4 or v6), IPCP, or RA received
             DNS server information, or are statically configured
             by the ACS.";
          leaf Enable {
            type boolean;
            default "false";
            description
              "Enables or disables this entry.";
          }
          leaf Status {
            type enumeration {
              enum "Disabled";
              enum "Enabled";
              enum "Error";
            }
            config false;
            default "Disabled";
            description
              "The status of this entry.  {{enum}}
            
               The {{enum|Error}} value MAY be used by the CPE to
               indicate a locally defined error condition.";
          }
          leaf DNSServer {
            type types:IPAddress;
            description
              "DNS server IP addresses.
            
               Note: {{param}} is only writable when
               {{param|Type}} is {{enum|Static|Type}}; otherwise,
               {{param}} is automatically configured as result of
               DHCP, IPCP, or RA received DNS server information.";
          }
          leaf Interface {
            type string {
              length "0..256";
            }
            default "";
            description
              "{{reference}} This parameter specifies the IP
               interface over which the DNS query is sent.
            
               If {{empty}} is specified, the CPE MUST use its
               routing policy (Forwarding table entries), if
               necessary, to determine the appropriate interface.
            
               Note: {{param}} is only writable when
               {{param|Type}} is {{enum|Static|Type}}; otherwise,
               {{param}} is automatically configured as result of
               DHCP, IPCP, or RA received DNS server information.";
          }
          leaf Type {
            type enumeration {
              enum "DHCP";
              enum "DHCPv4";
              enum "DHCPv6";
              enum "RouterAdvertisement";
              enum "IPCP";
              enum "Static";
            }
            config false;
            default "Static";
            description
              "Method used to assign the {{param|DNSServer}}
               address.  {{enum}}
            
               Table entries that are automatically created as
               result of DHCP, IPCP, or RA received DNS server
               information will have {{param}} set to
               {{enum|DHCPv4}}, {{enum|DHCPv6}}, {{enum|IPCP}},
               or {{enum|RouterAdvertisement}}, as the case may
               be.  Manually created table entires will have
               their {{param}} set to {{enum|Static}}.";
          }
        }
      }

      container Relay {
        description
          "DNS Relay object.  The DNS proxy (or relay) function
           allows the forwarding of local network DNS queries to
           local or external DNS server(s) {{bibref|RFC5625}}.";
        leaf Enable {
          type boolean;
          description
            "Enables or disables the DNS Relay function.";
        }
        leaf Status {
          type enumeration {
            enum "Disabled";
            enum "Enabled";
            enum "Error";
          }
          config false;
          description
            "The status of the DNS relay.  {{enum}}
          
             The {{enum|Error}} value MAY be used by the CPE to
             indicate a locally defined error condition.";
        }

        list Forwarding {
          key "DNSServer";
          description
            "DNS Server forwarding policy to be used by the DNS
             Relay.  Entries are either automatically created as
             result of DHCP (v4 or v6), IPCP, or RA received DNS
             server information, or are statically configured by
             the ACS.
          
             Note: Management of re-directing queries to the
             device embedded DNS server is not defined in this
             version of the specification.";
          leaf Enable {
            type boolean;
            default "false";
            description
              "Enables or disables this entry.";
          }
          leaf Status {
            type enumeration {
              enum "Disabled";
              enum "Enabled";
              enum "Error";
            }
            config false;
            default "Disabled";
            description
              "The status of this entry.  {{enum}}
            
               The {{enum|Error}} value MAY be used by the CPE to
               indicate a locally defined error condition.";
          }
          leaf DNSServer {
            type types:IPAddress;
            description
              "DNS server IP addresses.
            
               Note: {{param}} is only writable when
               {{param|Type}} is {{enum|Static|Type}}; otherwise,
               {{param}} is automatically configured as result of
               DHCP, IPCP, or RA received DNS server information.";
          }
          leaf Interface {
            type string {
              length "0..256";
            }
            default "";
            description
              "{{reference}} Specifies the IP interface over which
               the DNS query is sent.
            
               If {{empty}} is specified, the CPE MUST use its
               routing policy (IP Forwarding table entries), if
               necessary, to determine the appropriate interface.
            
               Note: {{param}} is only writable when
               {{param|Type}} is {{enum|Static|Type}}; otherwise,
               {{param}} is automatically configured as result of
               DHCP, IPCP, or RA received DNS server information.";
          }
          leaf Type {
            type enumeration {
              enum "DHCP";
              enum "DHCPv4";
              enum "DHCPv6";
              enum "RouterAdvertisement";
              enum "IPCP";
              enum "Static";
            }
            config false;
            default "Static";
            description
              "Method used to assign the {{param|DNSServer}}
               address.  {{enum}}
            
               Table entries that are automatically created as
               result of DHCP, IPCP, or RA received DNS server
               information will have {{param}} set to
               {{enum|DHCPv4}}, {{enum|DHCPv6}}, {{enum|IPCP}},
               or {{enum|RouterAdvertisement}}, as the case may
               be.  Manually created table entires will have
               their {{param}} set to {{enum|Static}}.";
          }
        }
      }

      container Diagnostics {
        description
          "The DNS Diagnostics object containing the
           {{object|NSLookupDiagnostics}} test.";

        container NSLookupDiagnostics {
          description
            "This object defines access to an IP-layer NS Lookup
             test for the specified IP interface.
          
             When initiated, the NS Lookup test will contact
             {{param|DNSServer}} and look up {{param|HostName}}
             {{param|NumberOfRepetitions}} times.
          
             There will be a {{object|Result}} instance for each
             time the device performs a DNS lookup, which is
             determined by the value of
             {{param|NumberOfRepetitions}}.
          
             Any previous {{object|Result}} instances are removed
             when a new test is initiated.";
          leaf DiagnosticsState {
            type enumeration {
              enum "None";
              enum "Requested";
              enum "Complete";
              enum "Error_DNSServerNotResolved";
              enum "Error_Internal";
              enum "Error_Other";
            }
            description
              "Indicates availability of diagnostic data.  {{enum}}
            
               If the ACS sets the value of this parameter to
               {{enum|Requested}}, the CPE MUST initiate the
               corresponding diagnostic test.  When writing, the
               only allowed value is {{enum|Requested}}.  To
               ensure the use of the proper test parameters (the
               writable parameters in this object), the test
               parameters MUST be set either prior to or at the
               same time as (in the same SetParameterValues)
               setting the DiagnosticsState to
               {{enum|Requested}}.
            
               When requested, the CPE SHOULD wait until after
               completion of the communication session with the
               ACS before starting the diagnostic.
            
               When the test is completed, the value of this
               parameter MUST be either {{enum|Complete}} (if the
               test completed successfully), or one of the Error
               values listed above.
            
               If the value of this parameter is anything other
               than {{enum|Complete}}, the values of the results
               parameters for this test are indeterminate.
            
               When the diagnostic initiated by the ACS is
               completed (successfully or not), the CPE MUST
               establish a new connection to the ACS to allow the
               ACS to view the results, indicating the Event code
               \"8 DIAGNOSTICS COMPLETE\" in the Inform message.
            
               After the diagnostic is complete, the value of all
               result parameters (all read-only parameters in
               this object) MUST be retained by the CPE until
               either this diagnostic is run again, or the CPE
               reboots.  After a reboot, if the CPE has not
               retained the result parameters from the most
               recent test, it MUST set the value of this
               parameter to {{enum|None}}.
            
               Modifying any of the writable parameters in this
               object except for this one MUST result in the
               value of this parameter being set to
               {{enum|None}}.
            
               While the test is in progress, modifying any of
               the writable parameters in this object except for
               this one MUST result in the test being terminated
               and the value of this parameter being set to
               {{enum|None}}.
            
               While the test is in progress, setting this
               parameter to {{enum|Requested}} (and possibly
               modifying other writable parameters in this
               object) MUST result in the test being terminated
               and then restarted using the current values of the
               test parameters.";
          }
          leaf Interface {
            type string {
              length "0..256";
            }
            description
              "{{reference}} This parameter specifies the IP-layer
               interface over which the test is to be performed
               (i.e.  the source IP address to use when
               performing the test).
            
               If {{empty}} is specified, the CPE MUST use its
               routing policy (Forwarding table entries), if
               necessary, to determine the appropriate interface.";
          }
          leaf HostName {
            type string {
              length "0..256";
            }
            description
              "Specifies the Host Name that NS Lookup is to look
               for.  The current domain name MUST be used unless
               the name is a fully qualified name.";
          }
          leaf DNSServer {
            type string {
              length "0..256";
            }
            description
              "Specifies the DNS Server name or IP address that NS
               Lookup is to use for the lookup.  The name of this
               server will be resolved using the default DNS
               server unless an IP address is provided.
            
               If {{empty}} is specified, the device's default
               DNS server will be used.";
          }
          leaf Timeout {
            type uint32;
            description
              "Timeout in {{units}} that indicates that a request
               has failed.";
          }
          leaf NumberOfRepetitions {
            type uint32;
            description
              "The number of times the device SHOULD repeat the
               execution of the NSLookup using the same input
               parameters.  If the diagnostics test fails the CPE
               MAY terminate the test without completing the full
               number of repetitions.
            
               Each repetition will use a Result instance to hold
               the NSLookup result data.";
          }
          leaf SuccessCount {
            type uint32;
            config false;
            description
              "Number of successfully executed repetitions.";
          }

          list Result {
            config false;
            description
              "Results from the most recent invocation of the test,
               one instance per repetition.";
            leaf Status {
              type enumeration {
                enum "Success";
                enum "Error_DNSServerNotAvailable";
                enum "Error_HostNameNotResolved";
                enum "Error_Timeout";
                enum "Error_Other";
              }
              description
                "Result Parameter to represent whether the NS Lookup
                 was successful or not.
              
                 Errors for individual Result instances do not
                 get bubbled up to {{param|#.DiagnosticsState}}.
              
                 A failure on a specific attempt does not mean
                 that the overall test failed, but a failure on
                 all attempts means that
                 {{param|#.DiagnosticsState}} SHOULD be
                 {{enum|Error_Other|#.DiagnosticsState}}.";
            }
            leaf AnswerType {
              type enumeration {
                enum "None";
                enum "Authoritative";
                enum "NonAuthoritative";
              }
              description
                "Result parameter to represent whether the answer is
                 Authoritative or not.";
            }
            leaf HostNameReturned {
              type string {
                length "0..256";
              }
              description
                "Result parameter to represent the fully qualified
                 name for the Host Name in the calling parameter
                 (e.g.  HostName.DomainName); if no response was
                 provided, then this parameter is {{empty}}.";
            }
            leaf IPAddresses {
              type types:IPAddress;
              description
                "{{list}} Indicates the IP Address results returned
                 by the NS Lookup; if no response was provided,
                 then this parameter is {{empty}}.";
            }
            leaf DNSServerIP {
              type types:IPAddress;
              description
                "Result parameter to represent the actual DNS Server
                 IP address that the NS Lookup used.";
            }
            leaf ResponseTime {
              type uint32;
              description
                "Response time (for the first response packet) in
                 {{units}}, or 0 if no response was received.";
            }
          }
        }
      }

      container SD {
        description
          "This object contains the DNS Service Discovery
           {{bibref|DNS-SD}} object and parameters necessary to
           discover services and their associated devices.
        
           Upon reboot the the contents of the service table are
           repopulated.  When the DNS.SD service is disabled, the
           contents of the service table is implementation
           specific.";
        leaf Enable {
          type boolean;
          description
            "The parameter, when {{true}}, enables the discovery of
             DNS-SD services hosted by other devices.";
        }

        list Service {
          key "InstanceName ApplicationProtocol TransportProtocol Domain";
          config false;
          description
            "The {{object}} table contains discovered DNS-SD
             services.  DNS.SD service information is provided in
             DNS RR SRV records {{bibref|RFC2782}}.  The Service
             Instance Name {{bibref|DNS-SD|Section 4.1 Structured
             Instance Names}} further specifies information about
             the service name (RFC2782 Service field) and domain
             name (RFC2782 Name field) in the form:
          
             Service Instance Name = <InstanceName> .  <Service>
             .  <Domain>
          
             <Service> = _<ApplicationProtocol> .
             _<TransportProtocol>
          
             RFC2782 Service field will always be equal to
             <InstanceName>.  <Service>
          
             RFC2782 Name field will always be equal to <Domain>
          
             For example, an SSH service might have:
          
             *{{param|InstanceName}} = \"Secure Shell (SSH))\"
          
             *{{param|ApplicationProtocol}} = \"ssh\"
          
             *{{param|TransportProtocol}} = \"TCP\"
          
             *{{param|Domain}} = \"example.com\"
          
             *{{param|Port}} = 22
          
             *{{param|Target}} = \"ssh.example.com.\"";
          leaf InstanceName {
            type string {
              length "0..63";
            }
            description
              "Human-readable instance name {{bibref|DNS-SD|Section
               4.1.1 Instance Names}} (i.e.  The \"<{{param}}>\"
               portion of the '\"Service Instance Name'\").";
          }
          leaf ApplicationProtocol {
            type string {
              length "0..15";
            }
            description
              "The Application Protocol, without the leading
               underscore, associated with the service (e.g.,
               daap) as defined by the DNS-SD service
               {{bibref|DNS-SD|Section 7 Application Protocol
               Names}}.";
          }
          leaf TransportProtocol {
            type enumeration {
              enum "TCP";
              enum "UDP";
            }
            description
              "The Transport Protocol associated with the service as
               defined by the DNS-SD service
               {{bibref|DNS-SD|Section 4.1.2 Service Names}}.";
          }
          leaf Domain {
            type string {
              length "0..256";
            }
            description
              "The value extracted from the Name field of the DNS
               SRV record {{bibref|RFC2782}} which represents the
               fully qualified domain name (FQDN) associated with
               the service as defined by the DNS-SD service
               {{bibref|DNS-SD|Section 4.1.3 Domain Names}}.";
          }
          leaf Port {
            type uint32 {
              range "min..65535";
            }
            description
              "The value extracted from the Port field of the DNS
               SRV record {{bibref|RFC2782}} that is used to
               contact the service.";
          }
          leaf Target {
            type string {
              length "0..256";
            }
            description
              "The fully qualified domain name (FQDN) with the
               trailing dot \".\" of the target host implementing
               the service as in the DNS SRV record
               {{bibref|RFC2782}}.";
          }
          leaf Status {
            type enumeration {
              enum "LeaseActive";
              enum "GoodbyeReceived";
              enum "LeaseExpired";
            }
            description
              "The status of the discovered {{object}} at
               {{param|LastUpdate}} time.  {{enum}}
            
               The ability to instantiate an inactive {{object}}
               is OPTIONAL.
            
               The time an inactive {{object}} remains listed in
               this table is a local matter to the device.";
          }
          leaf LastUpdate {
            type yang:date-and-time;
            description
              "The date and time at which the last advertisement for
               this {{object}} was received.";
          }
          leaf Host {
            type string {
              length "0..256";
            }
            description
              "{{list}} {{reference|all Host table entries, active
               or inactive, that correspond to this discovered
               DNS.SD service.  As such, when entries are added
               or removed from the Host tables the value of this
               parameter MUST be updated accordingly|ignore}}";
          }
          leaf TimeToLive {
            type uint32 {
              range "min..2147483647";
            }
            description
              "The value extracted from the TTL field of the DNS SRV
               record {{bibref|RFC2782}}.";
          }
          leaf Priority {
            type uint32 {
              range "min..65535";
            }
            description
              "The value extracted from the Priority field of the
               DNS SRV record {{bibref|RFC2782}}.";
          }
          leaf Weight {
            type uint32 {
              range "min..65535";
            }
            description
              "A server selection mechanism.  The value extracted
               from the Weight field of the DNS SRV record
               {{bibref|RFC2782}} that specifies the relative
               weight for entries with the same
               {{param|Priority}}.";
          }

          list TextRecord {
            description
              "This object maintains an instance of a (key/value
               pairs) of the service.  The information is
               extracted from DNS TXT records {{bibref|RFC1035}}
               of the discovered service.
            
               When multiple instances of the {{object}} table
               have the same value for the {{param|Key}}
               parameter, the implementation is CPE specific.";
            leaf Key {
              type string {
                length "0..255";
              }
              description
                "The key that identifies the text record";
            }
            leaf Value {
              type string {
                length "0..255";
              }
              description
                "The value of the text record.";
            }
          }
        }
      }
    }

    container NAT {
      description
        "Properties for Network Address Translation (NAT).
      
         The entire {{object}} object only applies to IPv4.";

      list InterfaceSetting {
        key "Interface";
        description
          "NAT settings for an associated IP Interface on which NAT
           is enabled.
        
           For enabled table entries, if {{param|Interface}} is
           not a valid reference then the table entry is
           inoperable and the CPE MUST set {{param|Status}} to
           {{enum|Error_Misconfigured|Status}}.
        
           Note: The {{object}} table includes a unique key
           parameter that is a strong reference.  If a strongly
           referenced object is deleted, the CPE will set the
           referencing parameter to {{empty}}.  However, doing so
           under these circumstances might cause the updated
           {{object}} row to then violate the table's unique key
           constraint; if this occurs, the CPE MUST set
           {{param|Status}} to
           {{enum|Error_Misconfigured|Status}} and disable the
           offending {{object}} row.";
        leaf Enable {
          type boolean;
          default "false";
          description
            "Enables or disables the {{object}} entry, indicating if
             NAT is enabled for the referenced IP Interface
             instance.  On creation, an {{object}} entry is
             disabled by default.";
        }
        leaf Status {
          type enumeration {
            enum "Disabled";
            enum "Enabled";
            enum "Enabled_NATForcedDisabled";
            enum "Enabled_PortMappingDisabled";
            enum "Error_Misconfigured";
            enum "Error";
          }
          config false;
          default "Disabled";
          description
            "The status of this entry.  {{enum}}
          
             The {{enum|Error_Misconfigured}} value indicates
             that a necessary configuration value is undefined or
             invalid.
          
             The {{enum|Error}} value MAY be used by the CPE to
             indicate a locally defined error condition.";
        }
        leaf Interface {
          type string {
            length "0..256";
          }
          default "";
          description
            "{{reference}} The associated IP interface on which NAT
             is to be enabled.";
        }
      }

      list PortMapping {
        key "RemoteHost ExternalPort Protocol";
        description
          "Port mapping table.
        
           This table MUST contain all NAT port mappings
           associated with this connection, including static and
           dynamic port mappings programmatically created via
           local control protocol, such as UPnP.
        
           This table MUST NOT contain dynamic NAT binding
           entries associated with the normal operation of NAT.
        
           If the CPE hosts a firewall, it is assumed that it
           will appropriately configure the firewall for the port
           mapping.
        
           For enabled table entries, if {{param|InternalClient}}
           is {{empty}}, or if {{param|Interface}} is not a valid
           reference and {{param|AllInterfaces}} is {{false}},
           then the table entry is inoperable and the CPE MUST
           set {{param|Status}} to
           {{enum|Error_Misconfigured|Status}}.";
        leaf Enable {
          type boolean;
          default "false";
          description
            "Enables or disables the port mapping instance.  On
             creation, an entry is disabled by default.";
        }
        leaf Status {
          type enumeration {
            enum "Disabled";
            enum "Enabled";
            enum "Error_Misconfigured";
            enum "Error";
          }
          config false;
          default "Disabled";
          description
            "The status of this entry.  {{enum}}
          
             The {{enum|Error_Misconfigured}} value indicates
             that a necessary configuration value is undefined or
             invalid.
          
             The {{enum|Error}} value MAY be used by the CPE to
             indicate a locally defined error condition.";
        }
        leaf Interface {
          type string {
            length "0..256";
          }
          default "";
          description
            "{{reference}} Specifies the IP interface to which this
             port mapping applies.";
        }
        leaf AllInterfaces {
          type boolean;
          default "false";
          description
            "Indicates whether this port mapping applies to all IP
             interfaces that support port mappings.  If {{true}},
             the value of {{param|Interface}} is ignored since
             all supported IP interfaces are indicated.";
        }
        leaf LeaseDuration {
          type uint32;
          description
            "Determines the time to live, in {{units}}, of a port
             mapping lease, where \"time to live\" means the
             number of seconds before the port mapping expires.
          
             A value of 0 means the port mapping is static.
             Support for dynamic (non-static) port mappings is
             OPTIONAL.  That is, the only value for {{param}}
             that MUST be supported is 0.
          
             For a dynamic (non-static) port mapping, when this
             parameter is read, the value represents the time
             remaining on the port mapping lease.  That is, for a
             dynamic port mapping, the value counts down toward
             0.  When a dynamic port mapping lease expires, the
             CPE MUST automatically terminate that port mapping,
             and MUST automatically delete the corresponding
             {{object}} table entry.";
        }
        leaf RemoteHost {
          type string;
          default "";
          description
            "This parameter is the IP address of the source of
             inbound packets.  {{empty}} indicates a
             \"wildcard\", i.e.  any IP address (this will be
             {{empty}} in most cases).  CPE are REQUIRED only to
             support {{empty}}.
          
             When {{param}} is {{empty}}, all traffic sent to the
             {{param|ExternalPort}} on the WAN interface of the
             gateway is forwarded to the {{object|.IP.Interface}}
             associated with the {{param|InternalClient}} on the
             {{param|InternalPort}}.
          
             When {{param}} is specified as one external IP
             address, the NAT will only forward inbound packets
             from this {{param}} to the {{param|InternalClient}},
             all other packets will be dropped.
          
             If a CPE supports non-empty values for {{param}}, it
             MAY additionally support the ability to have more
             than one port mapping with the same
             {{param|ExternalPort}} and {{param|Protocol}}, but
             with differing values of {{param}}.
          
             When wildcard values are used for {{param}} and/or
             {{param|ExternalPort}}, the following precedence
             order applies (with the highest precedence listed
             first):
          
             # Explicit {{param}}, explicit
             {{param|ExternalPort}}
          
             # Explicit {{param}}, zero {{param|ExternalPort}}
          
             # Empty {{param}}, explicit {{param|ExternalPort}}
          
             # Empty {{param}}, zero {{param|ExternalPort}}
          
             If an incoming packet matches the criteria
             associated with more than one entry in this table,
             the CPE MUST apply the port mapping associated with
             the highest precedence entry.";
        }
        leaf ExternalPort {
          type uint32 {
            range "0..65535";
          }
          description
            "The external port (or the first port of a range of
             external ports) that the NAT gateway would listen on
             for traffic to a corresponding
             {{param|InternalPort}}.  Inbound packets to this
             external port on the WAN interface SHOULD be
             forwarded to the {{object|.IP.Interface}} associated
             with the {{param|InternalClient}} on the
             {{param|InternalPort}}.
          
             A value of zero ({{null}}) represents a
             \"wildcard\", i.e.  any port number.  If this value
             is {{null}}, traffic on all external ports (that are
             not otherwise mapped) will be forwarded to
             {{param|InternalClient}}, and the value(s) of
             {{param|InternalPort}} on {{param|InternalClient}}
             are ignored.
          
             When wildcard values are used for
             {{param|RemoteHost}} and/or {{param}}, the following
             precedence order applies (with the highest
             precedence listed first):
          
             # Explicit {{param|RemoteHost}}, explicit {{param}}
          
             # Explicit {{param|RemoteHost}}, zero {{param}}
          
             # Empty {{param|RemoteHost}}, explicit {{param}}
          
             # Empty {{param|RemoteHost}}, zero {{param}}
          
             If an incoming packet matches the criteria
             associated with more than one entry in this table,
             the CPE MUST apply the port mapping associated with
             the highest precedence entry.";
        }
        leaf ExternalPortEndRange {
          type uint32 {
            range "0..65535";
          }
          default "0";
          description
            "Indicates the last port of the external port range that
             starts with {{param|ExternalPort}}.
          
             If an external port range is specified, then the
             behavior described for {{param|ExternalPort}}
             applies to all ports within the range.
          
             A value of zero (0) indicates that no external port
             range is specified, i.e.  that the range consists
             only of {{param|ExternalPort}}.
          
             If {{param|ExternalPort}} is zero (wildcard), the
             value of this parameter MUST be ignored.
          
             If specified, the value of this parameter MUST be
             greater than or equal to the value of
             {{param|ExternalPort}}.";
        }
        leaf InternalPort {
          type uint32 {
            range "0..65535";
          }
          description
            "The port on {{param|InternalClient}} that the gateway
             SHOULD forward traffic to.";
        }
        leaf Protocol {
          type enumeration {
            enum "TCP";
            enum "UDP";
          }
          description
            "The protocol of the port mapping.  {{enum}}";
        }
        leaf InternalClient {
          type string {
            length "0..256";
          }
          default "";
          description
            "The IP address or DNS host name of an internal client
             (on the LAN).
          
             Support for an IP address is mandatory.  If
             {{param}} is specified as an IP address and the LAN
             device's IP address subsequently changes, the port
             mapping MUST remain associated with the original IP
             address.
          
             Support for DNS host names is OPTIONAL.  If
             {{param}} is specified as a DNS host name and the
             LAN device's IP address subsequently changes, the
             port mapping MUST remain associated with this LAN
             device.  In this case, it is the responsibility of
             the CPE to maintain the name-to-address mapping in
             the event of IP address changes.  This can be
             accomplished, for example, by assigning the DNS host
             name via use of DHCP option 12 (Host Name) or option
             81 (FQDN).  Note that the ACS can learn the host
             name associated with a given LAN device via the
             {{object|.Hosts.Host.}} table.
          
             Read access to this parameter MUST always return the
             exact value that was last set by the ACS.  For
             example, if the internal client is set to a DNS host
             name, it MUST read back as a DNS host name and not
             as an IP address.
          
             It MUST be possible to set the {{param}} to the
             broadcast IP address 255.255.255.255 for UDP
             mappings.  This is to enable multiple NAT clients to
             use the same well-known port simultaneously.";
        }
        leaf Description {
          type string {
            length "0..256";
          }
          default "";
          description
            "User-readable description of this port mapping.";
        }
      }
    }

    container PCP {
      description
        "Properties for Port Control Protocol (PCP)
         {{bibref|RFC6887}}.
      
         See the PCP Theory of Operation
         {{bibref|TR-181i2a8|Appendix XIV}} for a description of
         the working of this PCP data model.";
      leaf SupportedVersions {
        type uint32 {
          range "0..65535";
        }
        config false;
        description
          "{{list}} Each list item denotes a PCP version supported
           by the PCP Client.  Currently known versions are 0, 1
           and 2.
        
           This parameter is based on Version from
           {{bibref|RFC6887}}.";
      }
      leaf PreferredVersion {
        type uint32 {
          range "0..65535";
        }
        description
          "This is the version to be used in the first exchange with
           a new PCP Server.
        
           The factory default MUST be the highest supported
           version, as described in {{bibref|RFC6887|Section 9}}.";
      }
      leaf OptionList {
        type uint32 {
          range "0..254";
        }
        config false;
        description
          "{{list}} The list of the PCP Options supported by the PCP
           Client.";
      }

      list Client {
        key "WANInterface";
        description
          "Client properties for Port Control Protocol (PCP).  The
           PCP Client interacts with a PCP Server as defined in
           {{bibref|RFC6887}} for internal device applications or
           LAN device applications via Interworking functions.";
        leaf Enable {
          type boolean;
          description
            "Enables or disables the PCP Client.";
        }
        leaf WANInterface {
          type string;
          config false;
          description
            "{{reference|the interface stack instance representing
             the WAN interface this client operates on}} See
             {{object|.InterfaceStack.}}";
        }
        leaf Status {
          type enumeration {
            enum "Disabled";
            enum "Enabled";
            enum "Error";
          }
          config false;
          description
            "The status of the PCP Client.  {{enum}}
          
             The {{enum|Error}} value MAY be used by the CPE to
             indicate a locally defined error condition.";
        }
        leaf MAPEnable {
          type boolean;
          description
            "Enables or disables the MAP OpCode.";
        }
        leaf PEEREnable {
          type boolean;
          description
            "Enables or disables the PEER OpCode.";
        }
        leaf ANNOUNCEEnable {
          type boolean;
          description
            "Enables or disables the ANNOUNCE OpCode.
          
             When {{false}} the PCP Client does not support
             unsolicited ANNOUNCE messages.";
        }
        leaf THIRDPARTYEnable {
          type boolean;
          description
            "Enables or disables the THIRD_PARTY Option.";
        }
        leaf THIRDPARTYStatus {
          type enumeration {
            enum "Disabled";
            enum "Enabled";
            enum "Error";
          }
          config false;
          description
            "Indicates whether THIRD_PARTY Option is enabled or not.
             {{enum}}
          
             The {{enum|Error}} value MAY be used by the CPE to
             indicate a locally defined error condition.";
        }
        leaf FILTEREnable {
          type boolean;
          description
            "Enables or disables the FILTER option.";
        }

        container PCPProxy {
          description
            "Properties for the Port Control Protocol (PCP) Proxy,
             as specified in {{bibref|PCPProxy}}.";
          leaf Enable {
            type boolean;
            description
              "Enables or disables the PCP Proxy for this PCP
               Client.";
          }
          leaf HighestVersion {
            type uint32 {
              range "0..65535";
            }
            config false;
            description
              "A string identifying the highest version of PCP that
               the proxy supports.
            
               This parameter is based on Version from
               {{bibref|RFC6887}}.";
          }
          leaf Status {
            type enumeration {
              enum "Disabled";
              enum "Enabled";
              enum "Error";
            }
            config false;
            description
              "The status of the PCP Proxy for this PCP Client.
               {{enum}}
            
               The {{enum|Error}} value MAY be used by the CPE to
               indicate a locally defined error condition.";
          }
        }

        container UPnPIWF {
          description
            "Properties for the interworking function between UPnP
             IGD (Internet Gateway Device) and PCP, as specified
             in {{bibref|RFC6970}}.";
          leaf Enable {
            type boolean;
            description
              "Enables or disables the UPnP IGD-PCP Interworking
               Function for this PCP Client.";
          }
          leaf Status {
            type enumeration {
              enum "Disabled";
              enum "Enabled";
              enum "Error";
            }
            config false;
            description
              "The status of the UPnP IGD-PCP Interworking Function
               for this PCP Client.  {{enum}}
            
               The {{enum|Error}} value MAY be used by the CPE to
               indicate a locally defined error condition.";
          }
        }

        list Server {
          key "ServerNameOrAddress";
          description
            "This table contains the PCP Servers to be used by the
             PCP Client.  Entries are either statically
             configured or automatically created via DHCP options
             OPTION_V4_PCP_SERVER and OPTION_V6_PCP_SERVER, as
             per {{bibref|RFC7291}}.
          
             Each OPTION_V4_PCP_SERVER or OPTION_V6_PCP_SERVER
             option corresponds to a {{object}} instance.  If an
             option returns multiple addresses then that
             {{object}} instance has multiple addresses.";
          leaf Enable {
            type boolean;
            default "true";
            description
              "Enables or disables this PCP Server.";
          }
          leaf Status {
            type enumeration {
              enum "Disabled";
              enum "Enabled";
              enum "Connecting";
              enum "Error_Timeout";
              enum "Error_HostNameNotResolved";
              enum "Error_NetworkFailure";
              enum "Error_NotAuthorized";
              enum "Error_Unsupported";
              enum "Error";
            }
            config false;
            default "Disabled";
            description
              "The status of the PCP Server.  {{enum}}
            
               The {{enum|Error}} value MAY be used by the CPE to
               indicate a locally defined error condition.";
          }
          leaf Origin {
            type enumeration {
              enum "DHCPv4";
              enum "DHCPv6";
              enum "Static";
            }
            config false;
            default "Static";
            description
              "Method used to assign {{param|ServerNameOrAddress}}
               and create this table entry.  {{enum}}
            
               Note: In the {{enum|DHCPv4}} and {{enum|DHCPv6}}
               cases, if more than one IP address is received
               {{param|ServerNameOrAddress}} will be the first
               address and {{param|AdditionalServerAddresses}}
               will be the remaining addresses.";
          }
          leaf ServerNameOrAddress {
            type string {
              length "0..256";
            }
            description
              "The FQDN or IP address of the PCP Server, assigned as
               described under {{param|Origin}}.";
          }
          leaf ServerAddressInUse {
            type types:IPAddress;
            config false;
            description
              "The IP address currently in use for the PCP Server,
               derived from the value of
               {{param|ServerNameOrAddress}}.
            
               {{empty}} indicates that no PCP Server address is
               currently known.";
          }
          leaf AdditionalServerAddresses {
            type types:IPAddress;
            config false;
            description
              "PCP Server addresses in addition to
               {{param|ServerNameOrAddress}}.  This can be
               non-empty only if {{param|Origin}} is
               {{enum|DHCPv4|Origin}} or {{enum|DHCPv6|Origin}}
               and if more than one PCP Server address was
               received.";
          }
          leaf ExternalIPAddress {
            type types:IPAddress;
            config false;
            description
              "The external IP address of the PCP-controlled device
               hosting this server.";
          }
          leaf CurrentVersion {
            type uint32 {
              range "0..65535";
            }
            config false;
            description
              "This is the version of PCP resulting from
               client-server Version Negotiation.
            
               This parameter is based on Version from
               {{bibref|RFC6887}}.";
          }
          leaf MaximumFilters {
            type uint32;
            description
              "Indicates the maximum number of inbound filters
               allowed to be associated with a mapping entry on
               this server.";
          }
          leaf PortQuota {
            type uint32 {
              range "min..65535";
            }
            default "0";
            description
              "Indicates the maximum number of ports allocated to
               this PCP Client on this server.
            
               A value of 0 means that there is no limitation.";
          }
          leaf PreferredLifetime {
            type uint32;
            description
              "Indicates the preferred lifetime (in {{units}}) to be
               used for mappings with this server when no
               preference is selected by an application/user.";
          }
          leaf Capabilities {
            type enumeration {
              enum "NAT44";
              enum "StatelessNAT64";
              enum "StatefulNAT64";
              enum "A+PPortRangeRouter";
              enum "SupportsPORTSETOption";
              enum "IPv4Firewall";
              enum "IPv6Firewall";
              enum "NPTv6";
              enum "DSCPReMarkingFunction";
              enum "FLOWDATAAwareFunction";
              enum "ILNPTranslator";
            }
            config false;
            description
              "Indicates the capabilities supported by the PCP
               Server.  {{enum}}";
          }

          list InboundMapping {
            key "InternalPort ProtocolNumber ThirdPartyAddress";
            description
              "Inbound Mapping table.
            
               This table contains all Inbound Mappings requested
               by this PCP Client on this PCP Server.  Such a
               mapping is created by a PCP request with OpCode
               MAP, as described in {{bibref|RFC6887|Section
               11}}.
            
               These requests can be issued from internal device
               applications, from static configuration or from
               other LAN device applications via interworking
               functions such as UPnP IGD or PCP proxies.  The
               {{param|Origin}} parameter indicates which
               mechanism requested the mapping.
            
               For non-{{enum|Static|Origin}} mappings (here
               ''Static'' refers to the mechanism that created
               the mapping, not to the {{param|Lifetime}}), the
               ACS MAY modify the {{param||Enable}} parameter but
               MUST NOT modify any other parameters in the
               mapping or its sub-objects.";
            leaf Enable {
              type boolean;
              default "false";
              description
                "Enables or disables this {{object}} instance.";
            }
            leaf Status {
              type enumeration {
                enum "Disabled";
                enum "Enabled";
                enum "Error_PCPErrorCodeReceived";
                enum "Error";
              }
              config false;
              default "Disabled";
              description
                "The status of this entry.  {{enum}}
              
                 The {{enum|Error_PCPErrorCodeReceived}} value
                 indicates that the PCP Client received an error
                 code from the PCP Server.
              
                 The {{enum|Error}} value MAY be used by the CPE
                 to indicate a locally defined error condition.";
            }
            leaf ErrorCode {
              type uint32 {
                range "1..255";
              }
              config false;
              description
                "Provides the PCP error code when {{param|Status}}
                 is {{enum|Error_PCPErrorCodeReceived|Status}}.
                 Error code values are defined in
                 {{bibref|RFC6887|Section 7.4}}.";
            }
            leaf Origin {
              type enumeration {
                enum "Internal";
                enum "UPnP_IWF";
                enum "PCP_Proxy";
                enum "Static";
              }
              config false;
              description
                "Mechanism via which the mapping was requested.
                 {{enum}}";
            }
            leaf Lifetime {
              type uint32;
              description
                "Determines the time to live, in {{units}}, of this
                 Inbound Mapping lease, i.e.  the remaining time
                 before this port mapping expires.
              
                 A value of 0 means that the port mapping is
                 permanent (referred to as a static mapping in
                 {{bibref|RFC6887}}).
              
                 When a dynamic Inbound Mapping lease expires,
                 the CPE MUST automatically delete the
                 corresponding {{object}} table entry.";
            }
            leaf SuggestedExternalIPAddress {
              type types:IPAddress;
              default "";
              description
                "The external IPv4 or IPv6 Address that the
                 PCP-controlled device will listen on for
                 incoming packets to be forwarded to the PCP
                 Client.
              
                 This is useful for refreshing an Inbound
                 Mapping, especially after the PCP Server loses
                 state.  If the PCP client does not know the
                 external address, or does not have a preference,
                 it MUST use {{empty}}.";
            }
            leaf SuggestedExternalPort {
              type uint32 {
                range "0..65535";
              }
              default "0";
              description
                "The external port (or the first port of a range of
                 external ports) that the PCP-controlled device
                 will listen on for incoming packets.  Those
                 inbound packets will be forwarded to
                 {{param|InternalPort}}.  If the PCP client does
                 not know the external port, or does not have a
                 preference, it MUST use 0.
              
                 This is useful for refreshing an Inbound
                 Mapping, especially after the PCP Server loses
                 state.  If the PCP Client does not know the
                 external port, or does not have a preference, it
                 MUST use 0.";
            }
            leaf SuggestedExternalPortEndRange {
              type uint32 {
                range "0..65535";
              }
              default "0";
              description
                "Indicates the last port of the external port range
                 that starts with
                 {{param|SuggestedExternalPort}}.
              
                 If an external port range is specified, then the
                 behavior described for
                 {{param|SuggestedExternalPort}} applies to all
                 ports within the range.
              
                 A value of zero (0) indicates that no external
                 port range is specified, i.e.  that the range
                 consists only of
                 {{param|SuggestedExternalPort}}.
              
                 If {{param|SuggestedExternalPort}} is zero
                 (wildcard), the value of {{param}} MUST be
                 ignored.
              
                 If specified, the value of this parameter MUST
                 be zero or be greater than or equal to the value
                 of {{param|SuggestedExternalPort}}.";
            }
            leaf InternalPort {
              type uint32 {
                range "1..65535";
              }
              description
                "The port on this PCP Client's
                 {{param|##.WANInterface}} that the
                 PCP-controlled device forwards incoming packets
                 to.";
            }
            leaf ProtocolNumber {
              type int32 {
                range "-1..255";
              }
              description
                "The protocol number of the {{object}}.  Values are
                 taken from {{bibref|IANA-protocolnumbers}}.
              
                 The value -1 means ''all protocols''.";
            }
            leaf ThirdPartyAddress {
              type types:IPAddress;
              description
                "Under certain conditions, the PCP Client can create
                 a PCP mapping on behalf of another device, by
                 using the THIRD_PARTY option, as specified in
                 {{bibref|RFC6887|Section 7.3}}.  In that case,
                 {{param}} is the IP address of the device for
                 which the PCP operation is requested.
              
                 For non-third-party mappings, {{param}} SHOULD
                 be {{empty}}.";
            }
            leaf Description {
              type string {
                length "0..256";
              }
              default "";
              description
                "User-readable description of this {{object}}.";
            }
            leaf AssignedExternalIPAddress {
              type types:IPAddress;
              config false;
              default "";
              description
                "The external IPAddress returned by the PCP Server.
                 The IP address that the PCP-controlled device is
                 listening on for incoming packets to a
                 corresponding PCP Client.";
            }
            leaf AssignedExternalPort {
              type uint32 {
                range "0..65535";
              }
              config false;
              description
                "The external port returned by the PCP Server.  The
                 external port (or the first port of a range of
                 external ports) that the PCP-controlled device
                 is listening on for incoming packets to a
                 corresponding {{param|InternalPort}}.  Inbound
                 packets to this external port on the External
                 interface of the PCP-controlled device is
                 forwarded to the on the {{param|InternalPort}}.";
            }
            leaf AssignedExternalPortEndRange {
              type uint32 {
                range "0..65535";
              }
              config false;
              default "0";
              description
                "Indicates the last port of the external port range
                 that starts with {{param|AssignedExternalPort}}.
              
                 If an external port range is specified, then the
                 behavior described for
                 {{param|AssignedExternalPort}} applies to all
                 ports within the range.
              
                 A value of zero (0) indicates that no external
                 port range is specified, i.e.  that the range
                 consists only of {{param|AssignedExternalPort}}.";
            }

            list Filter {
              key "Alias";
              description
                "Filter table.
              
                 This table contains all Filters restricting this
                 Inbound Mapping, as defined in
                 {{bibref|RFC6887|}}.";
              leaf RemoteHostIPAddress {
                type types:IPAddress;
                default "";
                description
                  "Permitted remote peer IP address for this filter.";
              }
              leaf PrefixLength {
                type uint32 {
                  range "1..128";
                }
                default "128";
                description
                  "Indicates how many bits of
                   {{param|RemoteHostIPAddress}} are relevant for
                   this filter.";
              }
              leaf RemotePort {
                type uint32 {
                  range "0..65535";
                }
                description
                  "Permitted remote peer port number for this
                   filter.
                
                   The value 0 indicates ''all ports''.";
              }
              leaf RemotePortEndRange {
                type uint32 {
                  range "0..65535";
                }
                config false;
                default "0";
                description
                  "Indicates the last port of the remote port range
                   that starts with {{param|RemotePort}}.
                
                   If an external port range is specified, then
                   the behavior described for
                   {{param|RemotePort}} applies to all ports
                   within the range.
                
                   A value of zero (0) indicates that no remote
                   port range is specified, i.e.  that the range
                   consists only of {{param|RemotePort}}.";
              }
            }
          }

          list OutboundMapping {
            key "InternalPort ProtocolNumber ThirdPartyAddress RemoteHostIPAddress RemotePort";
            description
              "Outbound Mapping table.
            
               This table contains all Outbound Mappings
               requested by this PCP Client on this PCP Server.
               Such a mapping is created by a PCP request with
               OpCode PEER, as described in
               {{bibref|RFC6887|Section 12}}.
            
               These requests can be issued from internal device
               applications, from static configuration or from
               other LAN device applications via interworking
               functions such as UPnP IGD or PCP proxies.  The
               {{param|Origin}} parameter indicates which
               mechanism requested the mapping.
            
               For non-{{enum|Static|Origin}} mappings (here
               ''Static'' refers to the mechanism that created
               the mapping, not to the {{param|Lifetime}}), the
               ACS MAY modify the {{param||Enable}} parameter but
               MUST NOT modify any other parameters in the
               mapping or its sub-objects.";
            leaf Enable {
              type boolean;
              default "false";
              description
                "Enables or disables this {{object}} instance.";
            }
            leaf Status {
              type enumeration {
                enum "Disabled";
                enum "Enabled";
                enum "Error_PCPErrorCodeReceived";
                enum "Error";
              }
              config false;
              default "Disabled";
              description
                "The status of this entry.  {{enum}}
              
                 The {{enum|Error_PCPErrorCodeReceived}} value
                 indicates that the PCP Client received an error
                 code from the PCP Server.
              
                 The {{enum|Error}} value MAY be used by the CPE
                 to indicate a locally defined error condition.";
            }
            leaf ErrorCode {
              type uint32 {
                range "1..255";
              }
              config false;
              description
                "Provides the PCP Error code when {{param|Status}}
                 is {{enum|Error_PCPErrorCodeReceived|Status}}.
                 Error code values are defined in
                 {{bibref|RFC6887|Section 7.4}}.";
            }
            leaf Origin {
              type enumeration {
                enum "Internal";
                enum "UPnP_IWF";
                enum "PCP_Proxy";
                enum "Static";
              }
              config false;
              description
                "Mechanism via which the mapping was requested.
                 {{enum}}";
            }
            leaf Lifetime {
              type uint32;
              description
                "Determines the time to live, in {{units}}, of this
                 Outbound Mapping lease, i.e.  the remaining time
                 before this port mapping expires.
              
                 A value of 0 means that the port mapping is
                 permanent (referred to as a static mapping in
                 {{bibref|RFC6887}}).
              
                 When a dynamic Outbound Mapping lease expires,
                 the CPE MUST automatically delete the
                 corresponding {{object}} table entry.";
            }
            leaf SuggestedExternalIPAddress {
              type types:IPAddress;
              default "";
              description
                "The external IPv4 or IPv6 Address that the
                 PCP-controlled device will use to send outgoing
                 packets covered by this mapping.
              
                 This is useful for refreshing a mapping,
                 especially after the PCP Server has lost state.
                 If the PCP Client does not know the external
                 address, or does not have a preference, it MUST
                 use {{empty}}.";
            }
            leaf SuggestedExternalPort {
              type uint32 {
                range "0..65535";
              }
              default "0";
              description
                "The external port that the PCP-controlled device
                 will use to send outgoing packets covered by
                 this mapping.
              
                 This is useful for refreshing a mapping,
                 especially after the PCP Server has lost state.
                 If the PCP Client does not know the external
                 port, or does not have a preference, it MUST use
                 0.";
            }
            leaf RemoteHostIPAddress {
              type types:IPAddress;
              description
                "The remote peer's IP address, as seen from the PCP
                 Client, for this Outbound Mapping.";
            }
            leaf InternalPort {
              type uint32 {
                range "1..65535";
              }
              description
                "The port on PCP Client WAN Interface that the
                 PCP-controlled device SHOULD listen to for this
                 mapping.";
            }
            leaf RemotePort {
              type uint32 {
                range "1..65535";
              }
              description
                "The remote peer's port, as seen from the PCP
                 Client, for this Outbound Mapping.";
            }
            leaf ProtocolNumber {
              type int32 {
                range "-1..255";
              }
              description
                "The protocol number of the {{object}}.  Values are
                 taken from the {{bibref|IANA-protocolnumbers}}.
              
                 The value -1 means ''all protocols''.";
            }
            leaf ThirdPartyAddress {
              type types:IPAddress;
              description
                "Under certain conditions, the PCP Client can create
                 a PCP mapping on behalf of another device, by
                 using the THIRD_PARTY option, as specified in
                 {{bibref|RFC6887|Section 7.3}}.  In that case,
                 {{param}} is the IP address of the device for
                 which the PCP operation is requested.
              
                 For non-third-party mappings, {{param}} SHOULD
                 be {{empty}}.";
            }
            leaf Description {
              type string {
                length "0..256";
              }
              default "";
              description
                "User-readable description of this {{object}}.";
            }
            leaf AssignedExternalIPAddress {
              type types:IPAddress;
              config false;
              default "";
              description
                "The external IP address returned by the PCP Server.
                 The IP address that the PCP-controlled device
                 uses to send outgoing packets corresponding to
                 this mapping.";
            }
            leaf AssignedExternalPort {
              type uint32 {
                range "0..65535";
              }
              config false;
              description
                "The external port returned by the PCP Server.  The
                 port that the PCP-controlled device uses to send
                 outgoing packets corresponding to this mapping.";
            }
          }
        }
      }
    }

    container DHCPv4 {
      description
        "The Dynamic Host Configuration Protocol (DHCP) IPv4 object
         {{bibref|RFC2131}}.  This entire object applies to IPv4
         only.  It contains the {{object|Client}},
         {{object|Server}}, and {{object|Relay}} objects.";

      list Client {
        key "Interface";
        min-elements 1;
        description
          "This object contains DHCP client settings for an
           associated ''IP Interface'' indicated by
           {{param|Interface}}.
        
           For enabled table entries, if {{param|Interface}} is
           not a valid reference then the table entry is
           inoperable and the CPE MUST set {{param|Status}} to
           {{enum|Error_Misconfigured|Status}}.
        
           Note: The {{object}} table includes a unique key
           parameter that is a strong reference.  If a strongly
           referenced object is deleted, the CPE will set the
           referencing parameter to {{empty}}.  However, doing so
           under these circumstances might cause the updated
           {{object}} row to then violate the table's unique key
           constraint; if this occurs, the CPE MUST set
           {{param|Status}} to
           {{enum|Error_Misconfigured|Status}} and disable the
           offending {{object}} row.";
        leaf Enable {
          type boolean;
          default "false";
          description
            "Enables or disables the DHCP Client entry.";
        }
        leaf Interface {
          type string {
            length "0..256";
          }
          default "";
          description
            "{{reference}} The IP Interface associated with the
             ''Client'' entry.";
        }
        leaf Status {
          type enumeration {
            enum "Disabled";
            enum "Enabled";
            enum "Error_Misconfigured";
            enum "Error";
          }
          config false;
          default "Disabled";
          description
            "The status of this table entry.  {{enum}}
          
             The {{enum|Error_Misconfigured}} value indicates
             that a necessary configuration value is undefined or
             invalid.
          
             The {{enum|Error}} value MAY be used by the CPE to
             indicate a locally defined error condition.";
        }
        leaf DHCPStatus {
          type enumeration {
            enum "Init";
            enum "Selecting";
            enum "Requesting";
            enum "Rebinding";
            enum "Bound";
            enum "Renewing";
          }
          config false;
          description
            "The DHCP Client status as defined in
             {{bibref|RFC2131}}.  {{enum}}
          
             Note: This value is only relevant when the DHCP
             Client is operationally enabled (i.e.  when
             {{param|Status}} is {{enum|Enabled|Status}}).";
        }
        leaf Renew {
          type boolean; /* command */
          default "false";
          description
            "When set to {{true}}, the DHCP client will renew its
             DHCP lease.";
        }
        leaf IPAddress {
          type types:IPv4Address;
          config false;
          default "";
          description
            "IPv4 Address option received from the DHCP Server.
             {{empty}} when {{param|Status}} is not equal to
             {{enum|Bound|DHCPStatus}}.";
        }
        leaf SubnetMask {
          type types:IPv4Address;
          config false;
          default "";
          description
            "Subnet mask option received from the DHCP Server.
             {{empty}} when {{param|Status}} is not equal to
             {{enum|Bound|DHCPStatus}}.
          
             Value is information received via DHCP Option 1.";
        }
        leaf IPRouters {
          type types:IPv4Address;
          config false;
          default "";
          description
            "{{list}} Items represent IP Router IPv4 Address(es)
             received from the DHCP server.  {{empty}} when
             {{param|Status}} is not equal to
             {{enum|Bound|DHCPStatus}}.
          
             Value is information received via DHCP Options 3, 33
             or 121.";
        }
        leaf DNSServers {
          type types:IPv4Address;
          config false;
          default "";
          description
            "{{list}} Items represent DNS Server IPv4 Address(es)
             received from the DHCP server.  {{empty}} when
             {{param|Status}} is not equal to
             {{enum|Bound|DHCPStatus}}.
          
             Value is information received via DHCP Option 6.";
        }
        leaf LeaseTimeRemaining {
          type int32 {
            range "-1..max";
          }
          config false;
          default "0";
          description
            "DHCP lease time remaining in {{units}}.  A value of -1
             indicates an infinite lease.";
        }
        leaf DHCPServer {
          type types:IPv4Address;
          config false;
          default "";
          description
            "The IPv4 address of the current DHCP server.";
        }
        leaf PassthroughEnable {
          type boolean;
          default "false";
          description
            "If {{false}}, the DHCP Client retrieved IP address
             information is configured on the referenced
             {{param|Interface}} object.
          
             If {{true}}, the DHCP Client retrieved information
             is propagated to the parameters in the referenced
             {{param|PassthroughDHCPPool}} object, replacing any
             existing configuration (including ''MinAddress'',
             ''MaxAddress'', ''SubnetMask'', ''IPRouters'', and
             ''DNSServers'').";
        }
        leaf PassthroughDHCPPool {
          type string {
            length "0..256";
          }
          default "";
          description
            "{{reference}}When {{param}} is set to {{empty}},
             {{param|PassthroughEnable}} MUST be set to {{false}}
             (i.e.  passthrough can not be enabled without a pool
             reference specified).";
        }

        list SentOption {
          key "Tag";
          description
            "Each instance of this object represents a DHCP option
             that MUST, if enabled, be sent in DHCP client
             requests.  All sent DHCP options MUST be listed.";
          leaf Enable {
            type boolean;
            default "false";
            description
              "Enables or disables this SentOption table entry.";
          }
          leaf Tag {
            type uint32 {
              range "1..254";
            }
            description
              "Option tag as defined in {{bibref|RFC2132}}.";
          }
          leaf Value {
            type yang:hex-string {
              length "0..255";
            }
            default "";
            description
              "A hexbinary encoded option value.";
          }
        }

        list ReqOption {
          key "Tag";
          description
            "Each instance of this object represents a DHCP option
             that MUST, if enabled, be requested in DHCP client
             requests.  All requested DHCP options MUST be
             listed.";
          leaf Enable {
            type boolean;
            default "false";
            description
              "Enables or disables this ReqOption table entry.";
          }
          leaf Order {
            type uint32 {
              range "1..max";
            }
            description
              "Position of the option in the DHCP client request.  A
               value of ''1'' indicates the first entry.
            
               When this value is modified, if the value matches
               that of an existing entry, the {{param}} value for
               the existing entry and all lower {{param}} entries
               is incremented to ensure uniqueness of this value.
               A deletion causes {{param}} values to be
               compacted.  When a value is changed, incrementing
               occurs before compaction.
            
               The value of {{param}} on creation of a {{object}}
               table entry MUST be one greater than the largest
               current value.";
          }
          leaf Tag {
            type uint32 {
              range "1..254";
            }
            description
              "Option tag as defined in {{bibref|RFC2132}}.";
          }
          leaf Value {
            type yang:hex-string {
              length "0..255";
            }
            config false;
            default "";
            description
              "A hexbinary encoded, most recently received DHCP
               option value.
            
               If no option value has been received, then the
               value MUST represent {{empty}}.
            
               Received DHCP option values MAY, but need not,
               persist across CPE reboots.";
          }
        }
      }

      container Server {
        description
          "DHCP server configuration.";
        leaf Enable {
          type boolean;
          description
            "Enables or disables the DHCP server.";
        }

        list Pool {
          key "Alias";
          description
            "DHCP conditional serving pool table.
          
             Each instance of this object defines a DHCP
             conditional serving pool.  Client requests are
             associated with pools based on criteria such as
             source interface, supplied DHCP options, and MAC
             address.
          
             Overlapping pool ranges MUST be supported.
          
             For enabled table entries, if {{param|Interface}} is
             not a valid reference, or {{param|MinAddress}},
             {{param|MaxAddress}}, or {{param|SubnetMask}} is not
             a valid value, then the table entry is inoperable
             and the CPE MUST set {{param|Status}} to
             {{enum|Error_Misconfigured|Status}}.";
          leaf Enable {
            type boolean;
            default "false";
            description
              "Enables or disables the Pool entry.";
          }
          leaf Status {
            type enumeration {
              enum "Disabled";
              enum "Enabled";
              enum "Error_Misconfigured";
              enum "Error";
            }
            config false;
            default "Disabled";
            description
              "The status of this entry.  {{enum}}
            
               The {{enum|Error_Misconfigured}} value indicates
               that a necessary configuration value is undefined
               or invalid.
            
               The {{enum|Error}} value MAY be used by the CPE to
               indicate a locally defined error condition.";
          }
          leaf Order {
            type uint32 {
              range "1..max";
            }
            description
              "Position of the {{object}} entry in the order of
               precedence.  A value of ''1'' indicates the first
               entry considered (highest precedence).  For each
               DHCP request, the highest ordered entry that
               matches the association criteria is applied.  All
               lower order entries are ignored.
            
               When this value is modified, if the value matches
               that of an existing entry, the {{param}} value for
               the existing entry and all lower {{param}} entries
               is incremented (lowered in precedence) to ensure
               uniqueness of this value.  A deletion causes
               {{param}} values to be compacted.  When a value is
               changed, incrementing occurs before compaction.
            
               The value of {{param}} on creation of a {{object}}
               table entry MUST be one greater than the largest
               current value (initially assigned the lowest
               precedence).";
          }
          leaf Interface {
            type string {
              length "0..256";
            }
            default "";
            description
              "{{reference}} The IP Interface associated with the
               ''Pool'' entry.";
          }
          leaf VendorClassID {
            type string {
              length "0..255";
            }
            default "";
            description
              "Pool association criterion.
            
               Used to identify one or more LAN devices, value of
               the DHCP Vendor Class Identifier (Option 60) as
               defined in {{bibref|RFC2132}}, matched according
               to the criterion in {{param|VendorClassIDMode}}.
               Case sensitive.
            
               This is a normal string, e.g.  \"abc\" is
               represented as \"abc\" and not say \"616263\" hex.
               However, if the value includes non-printing
               characters then such characters have to be
               represented using XML escapes, e.g.  #x0a for
               line-feed.
            
               {{empty}} indicates this criterion is not used for
               conditional serving.";
          }
          leaf VendorClassIDExclude {
            type boolean;
            default "false";
            description
              "If {{false}}, matching packets are those that match
               the {{param|VendorClassID}} entry, if specified.
            
               If {{true}}, matching packets are those that do
               not match the {{param|VendorClassID}} entry, if
               specified.";
          }
          leaf VendorClassIDMode {
            type enumeration {
              enum "Exact";
              enum "Prefix";
              enum "Suffix";
              enum "Substring";
            }
            default "Exact";
            description
              "{{param|VendorClassID}} pattern match criterion.
               {{enum}}
            
               For example, if {{param|VendorClassID}} is
               \"Example\" then an Option 60 value of \"Example
               device\" will match with {{param}} values of
               {{enum|Prefix}} or {{enum|Substring}}, but not
               with {{enum|Exact}} or {{enum|Suffix}}.";
          }
          leaf ClientID {
            type yang:hex-string {
              length "0..255";
            }
            default "";
            description
              "Pool association criterion.
            
               A hexbinary string used to identify one or more
               LAN devices, value of the DHCP Client Identifier
               (Option 61) as defined in {{bibref|RFC2132}}.  The
               option value is binary, so an exact match is
               REQUIRED.
            
               {{empty}} indicates this criterion is not used for
               conditional serving.";
          }
          leaf ClientIDExclude {
            type boolean;
            default "false";
            description
              "If {{false}}, matching packets are those that match
               the {{param|ClientID}} entry, if specified.
            
               If {{true}}, matching packets are those that do
               not match the {{param|ClientID}} entry, if
               specified.";
          }
          leaf UserClassID {
            type yang:hex-string {
              length "0..255";
            }
            default "";
            description
              "Pool association criterion.
            
               A hexbinary string used to identify one or more
               LAN devices, value of the DHCP User Class
               Identifier (Option 77) as defined in
               {{bibref|RFC3004}}.
            
               {{empty}} indicates this criterion is not used for
               conditional serving.";
          }
          leaf UserClassIDExclude {
            type boolean;
            default "false";
            description
              "If {{false}}, matching packets are those that match
               the {{param|UserClassID}} entry, if specified.
            
               If {{true}}, matching packets are those that do
               not match the {{param|UserClassID}} entry, if
               specified.";
          }
          leaf Chaddr {
            type types:MACAddress;
            default "";
            description
              "Pool association criterion.
            
               Hardware address (MAC address) of the physical
               interface of the DHCP client.
            
               {{empty}} indicates this criterion is not used for
               conditional serving.";
          }
          leaf ChaddrMask {
            type types:MACAddress;
            default "";
            description
              "Bit-mask for the MAC address, where matching of a
               packet's MAC address with the {{param|Chaddr}} is
               only to be done for bit positions set to one in
               the mask.  A mask of FF:FF:FF:FF:FF:FF or
               {{empty}} indicates all bits of the
               {{param|Chaddr}} are to be used for conditional
               serving classification.";
          }
          leaf ChaddrExclude {
            type boolean;
            default "false";
            description
              "If {{false}}, matching packets are those that match
               the (masked) {{param|Chaddr}} entry, if specified.
            
               If {{true}}, matching packets are those that do
               not match the (masked) {{param|Chaddr}} entry, if
               specified.";
          }
          leaf MinAddress {
            type types:IPv4Address;
            description
              "Specifies first IPv4 address in the pool to be
               assigned by the DHCP server on the LAN interface.
            
               The parameter value can be overwritten by dynamic
               values retrieved via a DHCP client with
               {{param|##.Client.{i}.PassthroughEnable}} or a PPP
               interface with
               {{param|.PPP.Interface.{i}.IPCP.PassthroughEnable}}
               equal to {{true}}.";
          }
          leaf MaxAddress {
            type types:IPv4Address;
            description
              "Specifies last IPv4 address in the pool to be
               assigned by the DHCP server on the LAN interface.
            
               The parameter value can be overwritten by dynamic
               values retrieved via a DHCP client with
               {{param|##.Client.{i}.PassthroughEnable}} or a PPP
               interface with
               {{param|.PPP.Interface.{i}.IPCP.PassthroughEnable}}
               equal to {{true}}.";
          }
          leaf ReservedAddresses {
            type types:IPv4Address;
            default "";
            description
              "{{list}} List items represent addresses marked
               reserved from the address allocation pool.";
          }
          leaf SubnetMask {
            type types:IPv4Address;
            description
              "Specifies the client's network subnet mask.
            
               The parameter value can be overwritten by dynamic
               values retrieved via a DHCP client with
               {{param|##.Client.{i}.PassthroughEnable}} or a PPP
               interface with
               {{param|.PPP.Interface.{i}.IPCP.PassthroughEnable}}
               equal to {{true}}.";
          }
          leaf DNSServers {
            type types:IPv4Address;
            description
              "{{list}} List items represent DNS servers offered to
               DHCP clients.  Support for more than three DNS
               Servers is OPTIONAL.
            
               The parameter value can be overwritten by dynamic
               values retrieved via a DHCP client with
               {{param|##.Client.{i}.PassthroughEnable}} or a PPP
               interface with
               {{param|.PPP.Interface.{i}.IPCP.PassthroughEnable}}
               equal to {{true}}.";
          }
          leaf DomainName {
            type string {
              length "0..64";
            }
            description
              "Sets the domain name to provide to clients on the LAN
               interface.";
          }
          leaf IPRouters {
            type types:IPv4Address;
            description
              "{{list}} List items represent addresses of routers on
               this subnet.  Also known as default gateway.
               Support for more than one Router address is
               OPTIONAL.
            
               The parameter value can be overwritten by dynamic
               values retrieved via a DHCP client with
               {{param|##.Client.{i}.PassthroughEnable}} or a PPP
               interface with
               {{param|.PPP.Interface.{i}.IPCP.PassthroughEnable}}
               equal to {{true}}.";
          }
          leaf LeaseTime {
            type int32 {
              range "-1..max";
            }
            default "86400";
            description
              "Specifies the lease time in {{units}} of client
               assigned addresses.  A value of -1 indicates an
               infinite lease.";
          }

          list StaticAddress {
            key "Chaddr";
            description
              "DHCP static address table.
            
               Entries in this table correspond to what
               {{bibref|RFC2131}} calls \"manual allocation\",
               where a client's IP address is assigned by the
               network administrator, and DHCP is used simply to
               convey the assigned address to the client.
            
               Each instance of this object specifies a hardware
               address (MAC address) and an IP address within the
               pool.  When serving from this pool, this IP
               address MUST, if available, be assigned to the
               DHCP client with this hardware address, and MUST
               NOT be assigned to any other client.
            
               Note that it is possible that an IP address in
               this table is present in one or more of the other
               conditional serving pools, in which case it is
               possible that such an address will be assigned to
               a different client.";
            leaf Enable {
              type boolean;
              default "false";
              description
                "Enables or disables the StaticAddress table entry.
              
                 Disabling an entry does not return the IP
                 address to the pool.";
            }
            leaf Chaddr {
              type types:MACAddress;
              default "";
              description
                "Hardware address (MAC address) of the physical
                 interface of the DHCP client.";
            }
            leaf Yiaddr {
              type types:IPv4Address;
              default "";
              description
                "IPv4 address to be assigned by the DHCP server to
                 the DHCP client with the specified hardware
                 address (MAC address).";
            }
          }

          list Option {
            key "Tag";
            description
              "This object specifies the DHCP options that MUST, if
               enabled, be returned to clients whose DHCP
               requests are associated with this pool.";
            leaf Enable {
              type boolean;
              default "false";
              description
                "Enables or disables this Option table entry.";
            }
            leaf Tag {
              type uint32 {
                range "1..254";
              }
              description
                "Option tag as defined in {{bibref|RFC2132}}.";
            }
            leaf Value {
              type yang:hex-string {
                length "0..255";
              }
              default "";
              description
                "A hexbinary encoded option value.";
            }
          }

          list Client {
            key "Chaddr";
            config false;
            description
              "DHCPv4 client table.
            
               This table lists details of DHCPv4 clients that
               matched the filter criteria of this {{object|#}}
               entry.";
            leaf Chaddr {
              type types:MACAddress;
              description
                "MAC address of the DHCPv4 client.";
            }
            leaf Active {
              type boolean;
              description
                "Whether or not the DHCPv4 client is currently
                 present on the LAN.  The method of presence
                 detection is a local matter to the CPE.
              
                 The ability to list inactive DHCPv4 clients is
                 OPTIONAL.  If the CPE includes inactive DHCPv4
                 clients in this table, {{param}} MUST be set to
                 {{false}} for each inactive DHCPv4 client.  The
                 length of time an inactive DHCPv4 client remains
                 listed in this table is a local matter to the
                 CPE.";
            }

            list IPv4Address {
              key "IPAddress";
              description
                "IPv4 addresses assigned to this client.";
              leaf IPAddress {
                type types:IPv4Address;
                description
                  "IPv4 address.";
              }
              leaf LeaseTimeRemaining {
                type yang:date-and-time;
                description
                  "The time at which the DHCP lease will expire or
                   {{null}} if not known.  For an infinite lease,
                   the parameter value MUST be
                   9999-12-31T23:59:59Z.";
              }
            }

            list Option {
              description
                "DHCPv4 options supplied by this client, e.g.
                 ''VendorClassID'' (Option 60), ''ClientID''
                 (option 61) or ''UserClassID'' (Option 77).";
              leaf Tag {
                type uint32 {
                  range "0..255";
                }
                description
                  "Option tag as defined in {{bibref|RFC2132}}.";
              }
              leaf Value {
                type yang:hex-string {
                  length "0..255";
                }
                description
                  "A hexbinary encoded option value.";
              }
            }
          }
        }
      }

      container Relay {
        description
          "DHCP Relay Agent (conditional relaying).";
        leaf Enable {
          type boolean;
          description
            "Enables or disables the DHCP Relay Agent function.";
        }
        leaf Status {
          type enumeration {
            enum "Disabled";
            enum "Enabled";
            enum "Error";
          }
          config false;
          description
            "The status of the DHCP relay.  {{enum}}
          
             The {{enum|Error}} value MAY be used by the CPE to
             indicate a locally defined error condition.";
        }

        list Forwarding {
          key "Alias";
          description
            "DHCP Relay Agent Forwarding table.
          
             For enabled table entries, if {{param|Interface}} is
             not a valid reference then the table entry is
             inoperable and the CPE MUST set {{param|Status}} to
             {{enum|Error_Misconfigured|Status}}.";
          leaf Enable {
            type boolean;
            default "false";
            description
              "Enables or disables the Forwarding entry.";
          }
          leaf Status {
            type enumeration {
              enum "Disabled";
              enum "Enabled";
              enum "Error_Misconfigured";
              enum "Error";
            }
            config false;
            default "Disabled";
            description
              "The status of this entry.  {{enum}}
            
               The {{enum|Error_Misconfigured}} value indicates
               that a necessary configuration value is undefined
               or invalid.
            
               The {{enum|Error}} value MAY be used by the CPE to
               indicate a locally defined error condition.";
          }
          leaf Order {
            type uint32 {
              range "1..max";
            }
            description
              "Position of the {{object}} entry in the order of
               precedence.  A value of ''1'' indicates the first
               entry considered (highest precedence).  For each
               DHCP request, the highest ordered entry that
               matches the association criteria is applied.  All
               lower order entries are ignored.
            
               When this value is modified, if the value matches
               that of an existing entry, the {{param}} value for
               the existing entry and all lower {{param}} entries
               is incremented (lowered in precedence) to ensure
               uniqueness of this value.  A deletion causes
               {{param}} values to be compacted.  When a value is
               changed, incrementing occurs before compaction.
            
               The value of {{param}} on creation of a {{object}}
               table entry MUST be one greater than the largest
               current value (initially assigned the lowest
               precedence).";
          }
          leaf Interface {
            type string {
              length "0..256";
            }
            default "";
            description
              "{{reference}} The IP Interface associated with the
               ''Forwarding'' entry.";
          }
          leaf VendorClassID {
            type string {
              length "0..255";
            }
            default "";
            description
              "Pool association criterion.
            
               Used to identify one or more LAN devices, value of
               the DHCP Vendor Class Identifier (Option 60) as
               defined in {{bibref|RFC2132}}, matched according
               to the criterion in {{param|VendorClassIDMode}}.
               Case sensitive.
            
               This is a normal string, e.g.  \"abc\" is
               represented as \"abc\" and not say \"616263\" hex.
               However, if the value includes non-printing
               characters then such characters have to be
               represented using XML escapes, e.g.  #x0a for
               line-feed.
            
               {{empty}} indicates this criterion is not used as
               a relay classification criterion.";
          }
          leaf VendorClassIDExclude {
            type boolean;
            default "false";
            description
              "If {{false}}, matching packets are those that match
               the {{param|VendorClassID}} entry, if specified.
            
               If {{true}}, matching packets are those that do
               not match the {{param|VendorClassID}} entry, if
               specified.";
          }
          leaf VendorClassIDMode {
            type enumeration {
              enum "Exact";
              enum "Prefix";
              enum "Suffix";
              enum "Substring";
            }
            default "Exact";
            description
              "{{param|VendorClassID}} pattern match criterion.
               {{enum}}
            
               For example, if {{param|VendorClassID}} is
               \"Example\" then an Option 60 value of \"Example
               device\" will match with {{param}} values of
               {{enum|Prefix}} or {{enum|Substring}}, but not
               with {{enum|Exact}} or {{enum|Suffix}}.";
          }
          leaf ClientID {
            type yang:hex-string {
              length "0..255";
            }
            default "";
            description
              "Pool association criterion.
            
               A hexbinary string used to identify one or more
               LAN devices, value of the DHCP Client Identifier
               (Option 61) as defined in {{bibref|RFC2132}}.  The
               option value is binary, so an exact match is
               REQUIRED.
            
               {{empty}} indicates this criterion is not used as
               a relay classification criterion.";
          }
          leaf ClientIDExclude {
            type boolean;
            default "false";
            description
              "If {{false}}, matching packets are those that match
               the {{param|ClientID}} entry, if specified.
            
               If {{true}}, matching packets are those that do
               not match the {{param|ClientID}} entry, if
               specified.";
          }
          leaf UserClassID {
            type yang:hex-string {
              length "0..255";
            }
            default "";
            description
              "Pool association criterion.
            
               A hexbinary string used to identify one or more
               LAN devices, value of the DHCP User Class
               Identifier (Option 77) as defined in
               {{bibref|RFC3004}}.
            
               {{empty}} indicates this criterion is not used as
               a relay classification criterion.";
          }
          leaf UserClassIDExclude {
            type boolean;
            default "false";
            description
              "If {{false}}, matching packets are those that match
               the {{param|UserClassID}} entry, if specified.
            
               If {{true}}, matching packets are those that do
               not match the {{param|UserClassID}} entry, if
               specified.";
          }
          leaf Chaddr {
            type types:MACAddress;
            default "";
            description
              "Pool association criterion.
            
               Hardware address (MAC address) of the physical
               interface of the DHCP client.
            
               {{empty}} indicates this criterion is not used as
               a relay classification criterion.";
          }
          leaf ChaddrMask {
            type types:MACAddress;
            default "";
            description
              "Bit-mask for the MAC address, where matching of a
               packet's MAC address with the {{param|Chaddr}} is
               only to be done for bit positions set to one in
               the mask.  A mask of FF:FF:FF:FF:FF:FF or
               {{empty}} indicates all bits of the
               {{param|Chaddr}} are to be used for relay
               classification.";
          }
          leaf ChaddrExclude {
            type boolean;
            default "false";
            description
              "If {{false}}, matching packets are those that match
               the (masked) {{param|Chaddr}} entry, if specified.
            
               If {{true}}, matching packets are those that do
               not match the (masked) {{param|Chaddr}} entry, if
               specified.";
          }
          leaf LocallyServed {
            type boolean;
            default "false";
            description
              "If {{true}}, incoming DHCP requests will be forwarded
               to the CPE DHCP Server.  If {{false}}, incoming
               DHCP requests will be forwarded to the
               {{param|DHCPServerIPAddress}} configured for this
               forwarding entry.";
          }
          leaf DHCPServerIPAddress {
            type types:IPv4Address;
            description
              "IPv4 address of the DHCP server, where the request
               has to be sent to when there is a conditional
               match with this forwarding entry and
               {{param|LocallyServed}} is {{false}}.  If
               {{param|LocallyServed}} is {{false}} and this
               parameter is not configured, then the DHCP request
               is dropped.";
          }
        }
      }
    }

    container DHCPv6 {
      description
        "The Dynamic Host Configuration Protocol (DHCP) IPv6 object
         {{bibref|RFC3315}}.  This entire object applies to IPv6
         only.  It contains the {{object|Client}} and
         {{object|Server}} objects.";

      list Client {
        key "Interface";
        min-elements 1;
        description
          "This object contains DHCPv6 client settings for an
           associated ''IP Interface'' indicated by
           {{param|Interface}}.
        
           For enabled table entries, if {{param|Interface}} is
           not a valid reference to an IPv6-capable interface
           (that is attached to the IPv6 stack), then the table
           entry is inoperable and the CPE MUST set
           {{param|Status}} to
           {{enum|Error_Misconfigured|Status}}.
        
           Note: The {{object}} table includes a unique key
           parameter that is a strong reference.  If a strongly
           referenced object is deleted, the CPE will set the
           referencing parameter to {{empty}}.  However, doing so
           under these circumstances might cause the updated
           {{object}} row to then violate the table's unique key
           constraint; if this occurs, the CPE MUST set
           {{param|Status}} to
           {{enum|Error_Misconfigured|Status}} and disable the
           offending {{object}} row.";
        leaf Enable {
          type boolean;
          default "false";
          description
            "Enables or disables this {{object}} entry.";
        }
        leaf Interface {
          type string {
            length "0..256";
          }
          default "";
          description
            "{{reference}} The IP Interface associated with the
             {{object}} entry.  This will reference an
             IPv6-capable interface (that is attached to the IPv6
             stack), otherwise the table entry will be
             inoperable.";
        }
        leaf Status {
          type enumeration {
            enum "Disabled";
            enum "Enabled";
            enum "Error_Misconfigured";
            enum "Error";
          }
          config false;
          default "Disabled";
          description
            "The status of this table entry.  {{enum}}
          
             The {{enum|Error_Misconfigured}} value indicates
             that a necessary configuration value is undefined or
             invalid.
          
             The {{enum|Error}} value MAY be used by the CPE to
             indicate a locally defined error condition.";
        }
        leaf DUID {
          type yang:hex-string {
            length "0..130";
          }
          config false;
          description
            "The client's DHCP Unique Identifier (DUID)
             {{bibref|RFC3315|Section 9}}.  {{param}} is set by
             the CPE.";
        }
        leaf RequestAddresses {
          type boolean;
          default "true";
          description
            "Enables or disables inclusion of the ''Identity
             Association (IA) for Non-Temporary Address'' option
             OPTION_IA_NA(3) {{bibref|RFC3315|Section 22.4}} in
             Solicit messages.";
        }
        leaf RequestPrefixes {
          type boolean;
          default "false";
          description
            "Enables or disables inclusion of the ''Identity
             Association (IA) for Prefix Delegation'' option
             OPTION_IA_PD(25) {{bibref|RFC3633|Section 10}} in
             Solicit messages.
          
             Note that this is only appropriate for an upstream
             interface on a requesting router, e.g.  for an RG
             WAN interface.";
        }
        leaf RapidCommit {
          type boolean;
          default "false";
          description
            "Enables or disables inclusion of the ''Rapid Commit''
             option OPTION_RAPID_COMMIT(14)
             {{bibref|RFC3315|Section 22.14}} in Solicit
             messages.";
        }
        leaf Renew {
          type boolean; /* command */
          default "false";
          description
            "When set to {{true}}, the {{object}} will renew its
             DHCPv6-supplied information (i.e.  the CPE will do a
             renew or information request as needed, updating
             both stateful and stateless parameter values
             discovered by this Client instance).";
        }
        leaf SuggestedT1 {
          type int32 {
            range "-1..max";
          }
          description
            "T1 value, in {{units}}, that the client SHOULD use when
             sending IA options, e.g.  OPTION_IA_NA
             {{bibref|RFC3315|Section 22.4}} and OPTION_IA_PD
             {{bibref|RFC3633|Section 10}}.
          
             A value of -1 indicates that no T1 value is
             specified.";
        }
        leaf SuggestedT2 {
          type int32 {
            range "-1..max";
          }
          description
            "T2 value, in {{units}}, that the client SHOULD use when
             sending IA options, e.g.  OPTION_IA_NA
             {{bibref|RFC3315|Section 22.4}} and OPTION_IA_PD
             {{bibref|RFC3633|Section 10}}.
          
             A value of -1 indicates that no T2 value is
             specified.";
        }
        leaf SupportedOptions {
          type uint32;
          config false;
          description
            "{{list}} The options that the client is able to process
             in server responses.  This list MUST include both
             top-level and encapsulated options, e.g.  if the
             client is able to process OPTION_IA_NA (3) with an
             encapsulated OPTION_IAADDR (5), the list would be
             expected to include both 3 and 5.";
        }
        leaf RequestedOptions {
          type uint32;
          description
            "{{list}} An ordered list of the top-level options (i.e.
             not encapsulated options) that the client will
             explicitly request from the server.
          
             This parameter is intended only for options that are
             not necessary for the basic operation of the
             protocol, and are not modeled elsewhere.  For
             example, it is appropriate for OPTION_DNS_SERVERS
             {{bibref|RFC3646}} but is not appropriate for
             OPTION_SERVERID (which is part of the protocol),
             OPTION_IA_NA (which is modeled via
             {{param|RequestAddresses}}) or OPTION_IA_PD (which
             is modeled via {{param|RequestPrefixes}}).  However,
             the CPE MUST NOT reject an attempt to set this
             parameter to a value that includes options that it
             regards as inappropriate; instead, it MUST accept
             the requested options and handle them as best it
             can.
          
             Loosely speaking, these are the options that the
             client will include in OPTION_ORO {{bibref|RFC3315}}
             but the client is free to decide (in accordance with
             {{bibref|RFC3315}}) in which messages to request
             which option, whether also to request additional
             options, whether not to request inappropriate
             options, and in which order to request any options
             that are also in {{param|SupportedOptions}}.";
        }

        list Server {
          key "SourceAddress";
          config false;
          description
            "This is a transitory table that lists the discovered
             DHCPv6 servers (it does ''not'' model a local DHCP
             server).  Table entries are automatically created to
             correspond with these servers.  However, it is a
             local matter to the CPE when to delete old table
             entries.";
          leaf SourceAddress {
            type types:IPv6Address;
            description
              "The IP address from which the message most recently
               received from this server was sent.";
          }
          leaf DUID {
            type yang:hex-string {
              length "0..130";
            }
            description
              "The server's DHCP Unique Identifier (DUID)
               {{bibref|RFC3315|Section 9}} as received via
               OPTION_SERVERID.";
          }
          leaf InformationRefreshTime {
            type yang:date-and-time;
            description
              "The OPTION_INFORMATION_REFRESH_TIME value
               {{bibref|RFC4242}} that was most recently received
               from this server, converted to the ''dateTime'' at
               which the associated information will expire.  If
               no such option has been received, the parameter
               value MUST be the \"Unknown Time\" {{null}}.  If
               the information will never expire, the parameter
               value MUST be infinite time 9999-12-31T23:59:59Z.";
          }
        }

        list SentOption {
          key "Tag";
          description
            "The top-level options and option values (including any
             encapsulated options) that the client will send to
             the server.
          
             This table is intended only for options that are not
             part of the basic operation of the protocol, and
             whose values are simple, do not often change and are
             not modeled elsewhere.  For example, it is
             appropriate for OPTION_USER_CLASS (whose value is a
             list of user classes) but is not appropriate for
             OPTION_RECONF_MSG (which is part of the protocol),
             OPTION_IA_NA (which is modeled via
             {{param|#.RequestAddresses}}) or OPTION_RAPID_COMMIT
             (which is modeled via {{param|#.RapidCommit}}).";
          leaf Enable {
            type boolean;
            default "false";
            description
              "Enables or disables this {{object}} entry.";
          }
          leaf Tag {
            type uint32 {
              range "0..65535";
            }
            description
              "Option tag (code) {{bibref|RFC3315|Section 22.1}}.";
          }
          leaf Value {
            type yang:hex-string {
              length "0..65535";
            }
            default "";
            description
              "A hexbinary encoded option data
               {{bibref|RFC3315|Section 22.1}}.
            
               Note: The length of the option data is
               ''option-len'' octets, as specified in
               {{bibref|RFC3315|Section 22.1}}.";
          }
        }

        list ReceivedOption {
          config false;
          description
            "This is a transitory table that lists all the options
             received from all servers.  Table entries are
             automatically created to correspond with received
             options.  However, it is a local matter to the CPE
             when to delete old table entries.
          
             If the same option is received multiple times,
             whether from one or more servers, it is up to the
             CPE to decide which entries to include (i.e.
             whether the same option will be present multiple
             times).  In order to allow for the same option to be
             present multiple times within the table, this table
             has no unique key defined.";
          leaf Tag {
            type uint32 {
              range "0..65535";
            }
            description
              "Option tag (code) {{bibref|RFC3315|Section 22.1}}.";
          }
          leaf Value {
            type yang:hex-string {
              length "0..65535";
            }
            description
              "A hexbinary encoded option data
               {{bibref|RFC3315|Section 22.1}}.";
          }
          leaf Server {
            type string;
            description
              "{{reference}} This is the server that sent the option
               to the client.  Each {{object}} entry MUST have an
               associated server.";
          }
        }
      }

      container Server {
        description
          "DHCPv6 server configuration.";
        leaf Enable {
          type boolean;
          description
            "Enables or disables the DHCPv6 server function.";
        }

        list Pool {
          key "Order";
          description
            "DHCPv6 server pool table.
          
             Each instance of this object defines a DHCPv6 server
             pool.  Client requests are associated with pools
             based on criteria such as source interface, supplied
             DHCPv6 options, and source address.
          
             Overlapping pool ranges MUST be supported.
          
             For enabled table entries, if {{param|Interface}} is
             not a valid reference to an IPv6-capable interface
             (that is attached to the IPv6 stack) then the table
             entry is inoperable and the CPE MUST set
             {{param|Status}} to
             {{enum|Error_Misconfigured|Status}}.";
          leaf Enable {
            type boolean;
            default "false";
            description
              "Enables or disables this {{object}} entry.";
          }
          leaf Status {
            type enumeration {
              enum "Disabled";
              enum "Enabled";
              enum "Error_Misconfigured";
              enum "Error";
            }
            config false;
            default "Disabled";
            description
              "The status of this entry.  {{enum}}
            
               The {{enum|Error_Misconfigured}} value indicates
               that a necessary configuration value is undefined
               or invalid.
            
               The {{enum|Error}} value MAY be used by the CPE to
               indicate a locally defined error condition.";
          }
          leaf Order {
            type uint32 {
              range "1..max";
            }
            description
              "Position of the {{object}} entry in the order of
               precedence.  A value of ''1'' indicates the first
               entry considered (highest precedence).  For each
               DHCPv6 request, the highest ordered entry that
               matches the association criteria is applied.  All
               lower order entries are ignored.
            
               When this value is modified, if the value matches
               that of an existing entry, the {{param}} value for
               the existing entry and all lower {{param}} entries
               is incremented (lowered in precedence) to ensure
               uniqueness of this value.  A deletion causes
               {{param}} values to be compacted.  When a value is
               changed, incrementing occurs before compaction.
            
               The value of {{param}} on creation of a {{object}}
               table entry MUST be one greater than the largest
               current value (initially assigned the lowest
               precedence).";
          }
          leaf Interface {
            type string {
              length "0..256";
            }
            default "";
            description
              "{{reference}} The IP Interface associated with the
               {{object}} entry.";
          }
          leaf DUID {
            type yang:hex-string {
              length "0..130";
            }
            default "";
            description
              "Pool association criterion.
            
               A hexbinary string used to identify one or more
               LAN devices, value of the DHCPv6 Client Identifier
               (Option 1) {{bibref|RFC3315|Section 22.2}}.  The
               option value is binary, so an exact match is
               REQUIRED.
            
               {{empty}} indicates this criterion is not used.
            
               Note: DHCPv6 Option 1 (DUID) is sometimes referred
               to as ''Client Identifier''.";
          }
          leaf DUIDExclude {
            type boolean;
            default "false";
            description
              "If {{false}}, matching packets are those that match
               the {{param|DUID}} entry, if specified.
            
               If {{true}}, matching packets are those that do
               not match the {{param|DUID}} entry, if specified.";
          }
          leaf VendorClassID {
            type yang:hex-string {
              length "0..65535";
            }
            default "";
            description
              "Pool association criterion.
            
               A hexbinary string used to identify one or more
               LAN devices, value of the DHCPv6 Vendor Class
               Identifier (Option 16) {{bibref|RFC3315|Section
               22.16}}.  The option value is binary, so an exact
               match is REQUIRED.
            
               {{empty}} indicates this criterion is not used.";
          }
          leaf VendorClassIDExclude {
            type boolean;
            default "false";
            description
              "If {{false}}, matching packets are those that match
               the {{param|VendorClassID}} entry, if specified.
            
               If {{true}}, matching packets are those that do
               not match the {{param|VendorClassID}} entry, if
               specified.";
          }
          leaf UserClassID {
            type yang:hex-string {
              length "0..65535";
            }
            default "";
            description
              "Pool association criterion.
            
               A hexbinary string used to identify one or more
               LAN devices, value of the DHCPv6 User Class
               Identifier (Option 15) {{bibref|RFC3315|Section
               22.15}}.
            
               {{empty}} indicates this criterion is not used.";
          }
          leaf UserClassIDExclude {
            type boolean;
            default "false";
            description
              "If {{false}}, matching packets are those that match
               the {{param|UserClassID}} entry, if specified.
            
               If {{true}}, matching packets are those that do
               not match the {{param|UserClassID}} entry, if
               specified.";
          }
          leaf SourceAddress {
            type types:IPv6Address;
            default "";
            description
              "Pool association criterion.
            
               Source address (link-layer address) of DHCPv6
               messages sent from the DHCPv6 client.  This
               criterion is only likely to be useful if this is a
               link-layer address.
            
               {{empty}} indicates this criterion is not used for
               serving.";
          }
          leaf SourceAddressMask {
            type types:IPv6Address;
            default "";
            description
              "Bit-mask for the source address, where matching of a
               packet's source address with the
               {{param|SourceAddress}} is only to be done for bit
               positions set to one in the mask.  A mask of
               {{empty}} indicates all bits of the
               {{param|SourceAddress}} are to be used.";
          }
          leaf SourceAddressExclude {
            type boolean;
            default "false";
            description
              "If {{false}}, matching packets are those that match
               the (masked) {{param|SourceAddress}} entry, if
               specified.
            
               If {{true}}, matching packets are those that do
               not match the (masked) {{param|SourceAddress}}
               entry, if specified.";
          }
          leaf IANAEnable {
            type boolean;
            description
              "Enables or disables IANA offers.";
          }
          leaf IANAManualPrefixes {
            type string;
            default "";
            description
              "{{list}} {{reference}}
            
               Manually-configured prefixes from which IA_NA
               addresses will be assigned.  Each referenced
               prefix MUST have a
               {{param|.IP.Interface.{i}.IPv6Prefix.{i}.StaticType}}
               of
               {{enum|Static|.IP.Interface.{i}.IPv6Prefix.{i}.StaticType}}
               or
               {{enum|Child|.IP.Interface.{i}.IPv6Prefix.{i}.StaticType}}.
               All clients that request IA_NA and match filter
               criteria on this {{param|Interface}} MUST be
               offered IA_NA addresses from all of the ''Valid''
               ({{param|.IP.Interface.{i}.IPv6Prefix.{i}.ValidLifetime}}
               is infinite or in the future) /64 prefixes in this
               list.
            
               Prefixes MUST be associated with the interface
               instance referenced by {{param|Interface}}.";
          }
          leaf IANAPrefixes {
            type string;
            config false;
            description
              "{{list}} {{reference}}
            
               All prefixes from which IA_NA addresses will be
               assigned.  This list can include:
            
               * Prefixes from {{param|IANAManualPrefixes}} that
               are used for IA_NA offers.
            
               * Prefixes with
               {{param|.IP.Interface.{i}.IPv6Prefix.{i}.Origin}}
               =
               {{enum|Child|.IP.Interface.{i}.IPv6Prefix.{i}.Origin}}
               or
               {{enum|AutoConfigured|.IP.Interface.{i}.IPv6Prefix.{i}.Origin}}
               associated with the interface instance referenced
               by {{param|Interface}}.";
          }
          leaf IAPDEnable {
            type boolean;
            description
              "Enables or disables IAPD offers.";
          }
          leaf IAPDManualPrefixes {
            type string;
            default "";
            description
              "{{list}} {{reference}}
            
               Manually-configured prefixes from which IA_PD
               prefixes will be derived.  This list can include:
            
               * Prefixes with
               {{param|.IP.Interface.{i}.IPv6Prefix.{i}.Origin}}
               =
               {{enum|Static|.IP.Interface.{i}.IPv6Prefix.{i}.Origin}}
               or
               {{enum|PrefixDelegation|.IP.Interface.{i}.IPv6Prefix.{i}.Origin}}
               associated with upstream interfaces (i.e.
               interfaces for which the physical layer interface
               object has ''Upstream'' = {{true}}).
            
               * Prefixes with
               {{param|.IP.Interface.{i}.IPv6Prefix.{i}.StaticType}}
               =
               {{enum|Static|.IP.Interface.{i}.IPv6Prefix.{i}.StaticType}}
               or
               {{enum|Child|.IP.Interface.{i}.IPv6Prefix.{i}.StaticType}}
               associated with with the interface instance
               referenced by {{param|Interface}}.
            
               All clients that request IA_PD and match filter
               criteria on this {{param|Interface}} MUST be
               offered IA_PD prefixes derived from all of the
               ''Valid''
               ({{param|.IP.Interface.{i}.IPv6Prefix.{i}.ValidLifetime}}
               is infinite or in the future) prefixes in this
               list.";
          }
          leaf IAPDPrefixes {
            type string;
            config false;
            description
              "{{list}} {{reference}}
            
               All prefixes for which IA_PD prefixes will be
               assigned.  This list can include:
            
               * Prefixes from {{param|IAPDManualPrefixes}} that
               are used for IA_PD offers.
            
               * Prefixes with
               {{param|.IP.Interface.{i}.IPv6Prefix.{i}.Origin}}
               =
               {{enum|PrefixDelegation|.IP.Interface.{i}.IPv6Prefix.{i}.Origin}}
               or
               {{enum|AutoConfigured|.IP.Interface.{i}.IPv6Prefix.{i}.Origin}}
               associated with upstream interfaces (i.e.
               interfaces for which the physical layer interface
               object has ''Upstream'' = {{true}}).
            
               * Prefixes with
               {{param|.IP.Interface.{i}.IPv6Prefix.{i}.Origin}}
               =
               {{enum|Child|.IP.Interface.{i}.IPv6Prefix.{i}.Origin}}
               or
               {{enum|AutoConfigured|.IP.Interface.{i}.IPv6Prefix.{i}.Origin}}
               associated with the interface instance referenced
               by {{param|Interface}}.";
          }
          leaf IAPDAddLength {
            type uint32 {
              range "min..64";
            }
            description
              "The RECOMMENDED minimum number of bits to add to
               {{param|IAPDManualPrefixes}} or
               {{param|IAPDPrefixes}} in order to determine the
               length of prefixes that are offered in an IA_PD.
               The device is responsible for ensuring that it
               does not delegate a prefix longer than /64.  The
               device can have additional logic that is used (in
               conjunction with this parameter) to determine the
               actual length of prefixes offered in an IA_PD.";
          }

          list Client {
            key "SourceAddress";
            config false;
            description
              "DHCPv6 client table.
            
               This table lists details of DHCPv6 clients that
               matched the filter criteria of this {{object|#}}
               entry.";
            leaf SourceAddress {
              type types:IPv6Address;
              description
                "Source address of the DHCPv6 client.";
            }
            leaf Active {
              type boolean;
              description
                "Whether or not the DHCPv6 client is currently
                 present on the LAN.  The method of presence
                 detection is a local matter to the CPE.
              
                 The ability to list inactive DHCPv6 clients is
                 OPTIONAL.  If the CPE includes inactive DHCPv6
                 clients in this table, {{param}} MUST be set to
                 {{false}} for each inactive DHCPv6 client.  The
                 length of time an inactive DHCPv6 client remains
                 listed in this table is a local matter to the
                 CPE.";
            }

            list IPv6Address {
              key "IPAddress";
              description
                "IPv6 addresses assigned to this client via IA_NA.";
              leaf IPAddress {
                type types:IPv6Address;
                description
                  "IPv6 address.";
              }
              leaf PreferredLifetime {
                type yang:date-and-time;
                description
                  "The time at which this address will cease to be
                   preferred (i.e.  will become deprecated), or
                   {{null}} if not known.  For an infinite
                   lifetime, the parameter value MUST be
                   9999-12-31T23:59:59Z.";
              }
              leaf ValidLifetime {
                type yang:date-and-time;
                description
                  "The time at which this address will cease to be
                   valid (i.e.  will become invalid), or {{null}}
                   if unknown.  For an infinite lifetime, the
                   parameter value MUST be 9999-12-31T23:59:59Z.";
              }
            }

            list IPv6Prefix {
              key "Prefix";
              description
                "IPv6 prefixes delegated to this client via IA_PD.";
              leaf Prefix {
                type types:IPv6Prefix;
                description
                  "IPv6 address prefix.";
              }
              leaf PreferredLifetime {
                type yang:date-and-time;
                description
                  "The time at which this prefix will cease to be
                   preferred (i.e.  will become deprecated), or
                   {{null}} if not known.  For an infinite
                   lifetime, the parameter value MUST be
                   9999-12-31T23:59:59Z.";
              }
              leaf ValidLifetime {
                type yang:date-and-time;
                description
                  "The time at which this prefix will cease to be
                   valid (i.e.  will become invalid), or {{null}}
                   if unknown.  For an infinite lifetime, the
                   parameter value MUST be 9999-12-31T23:59:59Z.";
              }
            }

            list Option {
              description
                "DHCPv6 options supplied by this client, e.g.
                 ''DUID'' (Option 1), ''UserClassID'' (Option 15)
                 or ''VendorClassID'' (option 16).";
              leaf Tag {
                type uint32 {
                  range "0..65535";
                }
                description
                  "Option tag (code) {{bibref|RFC3315|Section
                   22.1}}.";
              }
              leaf Value {
                type yang:hex-string {
                  length "0..65535";
                }
                description
                  "A hexbinary encoded option value.";
              }
            }
          }

          list Option {
            key "Tag";
            description
              "This object specifies the DHCPv6 options that MUST,
               if enabled, be offered to clients whose DHCPv6
               requests are associated with this pool.  If
               {{param|PassthroughClient}} is specified, and the
               referenced client has a value for a given option
               then the {{param|PassthroughClient}} option value
               will be sent instead of {{param|Value}}.
               Otherwise, {{param|Value}} will be sent.";
            leaf Enable {
              type boolean;
              default "false";
              description
                "Enables or disables this {{object}} entry.";
            }
            leaf Tag {
              type uint32 {
                range "0..65535";
              }
              description
                "Option tag (code) {{bibref|RFC3315|Section 22.1}}.";
            }
            leaf Value {
              type yang:hex-string {
                length "0..65535";
              }
              default "";
              description
                "A hexbinary encoded option value.";
            }
            leaf PassthroughClient {
              type string {
                length "0..256";
              }
              default "";
              description
                "{{reference}} Indicates whether this {{object}}
                 entry is configured for passthrough.
              
                 If {{param}} is specified, and the referenced
                 client (since boot) has received a value from an
                 associated upstream DHCPv6 server for the given
                 {{param|Tag}} option, then the referenced
                 client's option value will be sent instead of
                 {{param|Value}}.  Otherwise, {{param|Value}}
                 will be sent.
              
                 {{empty}} indicates that passthrough is not
                 configured for this {{object}} entry.";
            }
          }
        }
      }
    }

    container IEEE8021x {
      description
        "IEEE 802.1x object {{bibref|802.1x-2004}}, where
         {{object|Supplicant}} models authentication supplicants.";

      list Supplicant {
        key "Interface";
        min-elements 1;
        description
          "802.1x supplicant authentication provisioning and status
           information associated with an interface to be
           authenticated (e.g.  an {{object|.Ethernet.Link}}
           instance).
        
           For enabled table entries, if {{param|Interface}} is
           not a valid reference then the table entry is
           inoperable and the CPE MUST set {{param|Status}} to
           {{enum|Error_Misconfigured|Status}}.
        
           Note: The {{object}} table includes a unique key
           parameter that is a strong reference.  If a strongly
           referenced object is deleted, the CPE will set the
           referencing parameter to {{empty}}.  However, doing so
           under these circumstances might cause the updated
           {{object}} row to then violate the table's unique key
           constraint; if this occurs, the CPE MUST set
           {{param|Status}} to
           {{enum|Error_Misconfigured|Status}} and disable the
           offending {{object}} row.";
        leaf Enable {
          type boolean;
          default "false";
          description
            "This parameter controls whether this resource will
             utilize the 802.1x protocol as a supplicant for
             device authentication purposes.";
        }
        leaf Status {
          type enumeration {
            enum "Disabled";
            enum "Enabled";
            enum "Error_Misconfigured";
            enum "Error";
          }
          config false;
          default "Disabled";
          description
            "The current operational status of this 802.1x
             supplicant.  {{enum}}
          
             The {{enum|Error_Misconfigured}} value indicates
             that a necessary configuration value is undefined or
             invalid.
          
             The {{enum|Error}} value MAY be used by the CPE to
             indicate a locally defined error condition.";
        }
        leaf Interface {
          type string {
            length "0..256";
          }
          default "";
          description
            "{{reference}} The interface on which authentication is
             to be performed.  Example: Device.Ethernet.Link.1";
        }
        leaf PAEState {
          type enumeration {
            enum "Disconnected";
            enum "Logoff";
            enum "Connecting";
            enum "Authenticating";
            enum "Authenticated";
            enum "Held";
            enum "Restart";
            enum "ForceAuth";
            enum "ForceUnauth";
          }
          config false;
          description
            "The current supplicant state machine as defined in
             {{bibref|802.1x-2004|9.5.1}}, Supplicant PAE (Port
             Access Entity) State.  {{enum}}";
        }
        leaf EAPIdentity {
          type string {
            length "0..256";
          }
          description
            "The identity to be exchanged between the supplicant and
             authenticator.";
        }
        leaf MaxStart {
          type uint32 {
            range "1..10";
          }
          description
            "The maximum number of times the device will attempt to
             send an EAP start message before authentication
             fails as defined in {{bibref|802.1x-2004|9.5.1}},
             maxStart.
          
             This is in support of {{bibref|802.1x-2004|Section
             8.4.6}}, Migration Considerations.";
        }
        leaf StartPeriod {
          type uint32 {
            range "1..max";
          }
          description
            "The period in {{units}} a supplicant will wait before
             the device will attempt to re-send an EAP start
             message as defined in {{bibref|802.1x-2004|9.5.1}},
             startPeriod.";
        }
        leaf HeldPeriod {
          type uint32 {
            range "1..max";
          }
          description
            "The hold-off period in {{units}} a supplicant will wait
             before re-attempting authentication as defined in
             {{bibref|802.1x-2004|9.5.1}}, heldPeriod.";
        }
        leaf AuthPeriod {
          type uint32;
          description
            "The period in {{units}} after which a request will be
             considered timed out as defined in
             {{bibref|802.1x-2004|9.5.1}}, authPeriod.";
        }
        leaf AuthenticationCapabilities {
          type enumeration {
            enum "EAP-TLS";
            enum "EAP-MD5";
          }
          config false;
          description
            "{{list}} Indicates the authentication methods supported
             by the device.  {{enum}}";
        }
        leaf StartFailurePolicy {
          type enumeration {
            enum "FailAuthentication";
            enum "AssumeAuthentication";
          }
          description
            "The action to be taken when authentication has failed,
             when the network fails to respond to the
             supplicant's start message, and the retries have
             been exceeded (since network does not yet support
             802.1x).  {{enum}}
          
             This is in support of {{bibref|802.1x-2004|Section
             8.4.6}}, Migration Considerations.";
        }
        leaf AuthenticationSuccessPolicy {
          type enumeration {
            enum "NoAction";
            enum "RenewConnection";
          }
          description
            "The action to be taken when authentication succeeds and
             a connection has already received an address and/or
             policy settings.  {{enum}}";
        }
        leaf Reset {
          type boolean; /* command */
          description
            "When set to {{true}}, the device MUST reset the session
             by performing an initial authentication attempt as
             defined in {{bibref|802.1x-2004|9.6.1.3}},
             Initialize Port by sending out the EAP start
             message.
          
             The device MUST initiate the reset after completion
             of the current CWMP session.  The device MAY delay
             resetting the resource in order to avoid
             interruption of a user service such as an ongoing
             voice call.";
        }
        leaf Disconnect {
          type boolean; /* command */
          description
            "When set to {{true}}, the device MUST disconnect
             (forced unauthentication) the resource.
          
             The device MUST initiate the disconnect after
             completion of the current CWMP session.  The device
             MAY delay re-authentication of the resource in order
             to avoid interruption of a user service such as an
             ongoing voice call.";
        }

        container Stats {
          config false;
          description
            "802.1x Authentication Supplicant EAP statistics
             information for this resource.";
          leaf ReceivedFrames {
            type uint32;
            default "0";
            description
              "The number of EAPOL frames of any type that have been
               received by this Supplicant;
               {{bibref|802.1x-2004|9.5.2}}, EAPOL frames
               received.";
          }
          leaf TransmittedFrames {
            type uint32;
            default "0";
            description
              "The number of EAPOL frames of any type that have been
               transmitted by this Supplicant;
               {{bibref|802.1x-2004|9.5.2}}, EAPOL frames
               transmitted.";
          }
          leaf TransmittedStartFrames {
            type uint32;
            default "0";
            description
              "The number of EAPOL Start frames that have been
               transmitted by this Supplicant;
               {{bibref|802.1x-2004|9.5.2}}, EAPOL Start frames
               transmitted.";
          }
          leaf TransmittedLogoffFrames {
            type uint32;
            default "0";
            description
              "The number of EAPOL Logoff frames that have been
               transmitted by this Supplicant;
               {{bibref|802.1x-2004|9.5.2}}, EAPOL Logoff frames
               transmitted.";
          }
          leaf TransmittedResponseIdFrames {
            type uint32;
            default "0";
            description
              "The number of EAP Resp/Id frames that have been
               transmitted; {{bibref|802.1x-2004|9.5.2}}, EAP
               Resp/Id frames transmitted.";
          }
          leaf TransmittedResponseFrames {
            type uint32;
            default "0";
            description
              "The number of valid EAP Response frames (other than
               Resp/Id frames) that have been transmitted by this
               Supplicant; {{bibref|802.1x-2004|9.5.2}}, EAP Resp
               frames transmitted.";
          }
          leaf ReceivedRequestIdFrames {
            type uint32;
            default "0";
            description
              "The number of EAP Req/Id frames that have been
               received by this Supplicant;
               {{bibref|802.1x-2004|9.5.2}}, EAP Req/Id frames
               received.";
          }
          leaf ReceivedRequestFrames {
            type uint32;
            default "0";
            description
              "The number of EAP Request frames (other than Rq/Id
               frames) that have been received by this
               Supplicant; {{bibref|802.1x-2004|9.5.2}}, EAP Req
               frames received.";
          }
          leaf ReceivedInvalidFrames {
            type uint32;
            default "0";
            description
              "The number of EAPOL frames that have been received by
               this Supplicant in which the frame type is not
               recognized; {{bibref|802.1x-2004|9.5.2}}, EAP Req
               frames received.";
          }
          leaf ReceivedLengthErrorFrames {
            type uint32;
            default "0";
            description
              "The number of EAPOL frames that have been received by
               this Supplicant in which the Packet Body Length
               field is invalid; {{bibref|802.1x-2004|9.5.2}},
               EAP length error frames received.";
          }
          leaf LastFrameVersion {
            type uint32;
            description
              "The protocol version number carried in the most
               recently received EAPOL frame;
               {{bibref|802.1x-2004|9.5.2}}, Last EAPOL frame
               version";
          }
          leaf LastFrameSourceMACAddress {
            type types:MACAddress;
            description
              "The source MAC address carried in the most recently
               received EAPOL frame;
               {{bibref|802.1x-2004|9.5.2}}, Last EAPOL frame
               source.";
          }
        }

        container EAPMD5 {
          description
            "802.1x Authentication Supplicant provisioning
             information used for MD5 shared secret exchange.
             This object will not exist if EAP-MD5 is not a
             supported authentication type.";
          leaf Enable {
            type boolean;
            description
              "This parameter enables or disables the supplicant's
               support for EAP-MD5.";
          }
          leaf SharedSecret {
            type string {
              length "0..256";
            }
            description
              "The shared secret to be exchanged between the
               supplicant and authenticator.";
          }
        }

        container EAPTLS {
          description
            "802.1x Authentication Supplicant provisioning
             information used for TLS certificate authentication.
             This object will not exist if the EAP-TLS is not a
             supported authentication type.";
          leaf Enable {
            type boolean;
            description
              "This parameter enables or disables the supplicant's
               support for EAP-TLS.";
          }
          leaf MutualAuthenticationEnable {
            type boolean;
            description
              "The parameter controls if the supplicant will
               authenticate the authenticator.";
          }
        }
      }
    }

    container Users {
      description
        "Users object that contains the {{object|User}} table.";

      list User {
        key "Username";
        description
          "This object contains parameters relating to the user
           characteristics.";
        leaf Enable {
          type boolean;
          default "false";
          description
            "Enables/disables this user object instance.
          
             If the User being configured is currently accessing
             the device then a disable MUST apply to the next
             user session and the current user session MUST NOT
             be abruptly terminated.";
        }
        leaf RemoteAccessCapable {
          type boolean;
          default "false";
          description
            "Allows this user to remotely access the UserInterface
             via the mechanism defined in
             {{object|.UserInterface.RemoteAccess.}}";
        }
        leaf Username {
          type string {
            length "0..64";
          }
          default "";
          description
            "Name of the current user.  MUST NOT be {{empty}} for an
             enabled entry.";
        }
        leaf Password {
          type string {
            length "0..64";
          }
          description
            "The user's password.";
        }
        leaf Language {
          type string {
            length "0..16";
          }
          default "";
          description
            "String describing the default language for the local
             configuration interface, specified according to
             {{bibref|RFC3066}}.
          
             If {{empty}},
             {{param|.UserInterface.CurrentLanguage}} is used.";
        }
      }
    }

    container SmartCardReaders {
      description
        "SmartCardReaders object that contains the
         {{object|SmartCardReader}} table.";

      list SmartCardReader {
        key "Name";
        description
          "This object describes the characteristics of the smart
           card reader.";
        leaf Enable {
          type boolean;
          description
            "Enables or disables this smart card reader.";
        }
        leaf Status {
          type enumeration {
            enum "Disabled";
            enum "Enabled";
            enum "Error";
          }
          config false;
          description
            "Indicates the status of this smart card reader.";
        }
        leaf Name {
          type string {
            length "0..256";
          }
          config false;
          description
            "Human-readable name associated with this smart card
             reader.";
        }
        leaf Reset {
          type boolean;
          description
            "When set to {{true}}, resets the SmartCard Reader and
             the associated SmartCard.";
        }
        leaf ResetTime {
          type yang:date-and-time;
          config false;
          description
            "The time at which this SmartCard Reader was reset.
          
             Reset can be caused by:
          
             * {{param|Status}} transition from Disabled to
             Enabled
          
             * {{param|Reset}} set to {{true}}.
          
             * An internal reset of the SmartCard Reader
             (including a reboot of the device).
          
             Unknown Time value indicates that this SmartCard
             Reader has never been reset, which can only happen
             if it has never been enabled.";
        }
        leaf DecryptionFailedCounter {
          type uint32;
          config false;
          description
            "Counter incremented once each time decryption cannot be
             carried out.
          
             This counter relates to the smart card reader, not
             to the smart card itself, i.e.  it is reset when the
             {{param|Reset}} parameter is used and not when a
             Smart Card is inserted or removed.";
        }
        leaf DecryptionFailedNoKeyCounter {
          type uint32;
          config false;
          description
            "Counter incremented once each time the key is not
             available to decrypt it.  This is a subset of the
             more general {{param|DecryptionFailedCounter}}
             within the same object and thus will always be less
             than that parameter.
          
             This counter relates to the smart card reader, not
             to the smart card itself, i.e.  it is reset when the
             {{param|Reset}} parameter is used and not when a
             Smart Card is inserted or removed.";
        }

        container SmartCard {
          config false;
          description
            "Status of currently associated smart card.";
          leaf Status {
            type enumeration {
              enum "None";
              enum "Running";
              enum "Error";
            }
            description
              "Status of the Smart Card.";
          }
          leaf Type {
            type enumeration {
              enum "CA";
              enum "DRM";
              enum "UICC";
            }
            description
              "Smart Card Type.  {{enum}}
            
               Vendors can extend the enumerated values with
               vendor specific extensions, in which case the
               rules outlined in {{bibref|TR-106a2|Section 3.3}}
               MUST be adhered to.";
          }
          leaf Application {
            type enumeration {
              enum "SIM";
              enum "USIM";
              enum "ISIM";
            }
            description
              "{{list}} Indicates Smart Card Application(s).
               {{param}} is only relevant when {{param|Type}} has
               a value of UICC, otherwise it is {{empty}}.
               {{enum}}
            
               Vendors can extend the enumerated values with
               vendor specific extensions, in which case the
               rules outlined in {{bibref|TR-106a2|Section 3.3}}
               MUST be adhered to.";
          }
          leaf SerialNumber {
            type string {
              length "0..256";
            }
            description
              "The Smart Card Serial Number or {{empty}} if the
               Smart Card serial Number is not available, e.g.
               in the case of IPTV due to restrictions of the
               Service Delivery Platform.";
          }
          leaf ATR {
            type string {
              length "0..1024";
            }
            description
              "The Smart Card answer to a reset action.  Issued by
               the Smart Card upon reset.";
          }
        }
      }
    }

    container UPnP {
      description
        "This object contains all UPnP related objects and
         parameters including Device and Discovery related
         objects and parameters.";

      container Device {
        description
          "This object defines the UPnP devices and UPnP services
           that are implemented by the CPE.";
        leaf Enable {
          type boolean;
          description
            "Enables/Disables UPnP support.";
        }
        leaf UPnPMediaServer {
          type boolean;
          description
            "Enables/Disables UPnP Media Server.";
        }
        leaf UPnPMediaRenderer {
          type boolean;
          description
            "Enables/Disables UPnP Media Renderer.";
        }
        leaf UPnPWLANAccessPoint {
          type boolean;
          description
            "Enables/Disables UPnP Wireless Access Point.";
        }
        leaf UPnPQoSDevice  {
          type boolean;
          description
            "Enables/Disables UPnP QoS Device.";
        }
        leaf UPnPQoSPolicyHolder {
          type boolean;
          description
            "Enables/Disables UPnP QoS Policy Holder.";
        }
        leaf UPnPIGD {
          type boolean;
          description
            "Enables/Disables UPnP IGD.";
        }
        leaf UPnPDMBasicMgmt {
          type boolean;
          description
            "Enables/Disables UPnP-DM Basic Management.";
        }
        leaf UPnPDMConfigurationMgmt {
          type boolean;
          description
            "Enables/Disables UPnP-DM Configuration Management.";
        }
        leaf UPnPDMSoftwareMgmt {
          type boolean;
          description
            "Enables/Disables UPnP-DM Software Management.";
        }

        container Capabilities {
          config false;
          description
            "This object defines what UPnP capabilities this device
             has.";
          leaf UPnPArchitecture {
            type uint32;
            description
              "Numeric value indicating the major version of the
               supported UPnP architecture.
            
               If UPnP 1.1 is supported the value is 1.  If UPnP
               2.0 is supported the value is 2.
            
               A value of 0 indicates no UPnP support.";
          }
          leaf UPnPArchitectureMinorVer {
            type uint32;
            description
              "Numeric value indicating the minor version of the
               supported UPnP architecture.
            
               If UPnP 1.1 is supported the value is 1.  If UPnP
               2.0 is supported the value is 0.
            
               If {{param|UPnPArchitecture}} is 0 then this
               parameter SHOULD be ignored.";
          }
          leaf UPnPMediaServer {
            type uint32;
            description
              "Numeric value indicating the supported revision for
               UPnP Media Server.
            
               A value of 0 indicates no support.";
          }
          leaf UPnPMediaRenderer {
            type uint32;
            description
              "Numeric value indicating the supported revision for
               UPnP Media Renderer.
            
               A value of 0 indicates no support.";
          }
          leaf UPnPWLANAccessPoint {
            type uint32;
            description
              "Numeric value indicating the supported revision for
               UPnP Wireless Access Point.
            
               A value of 0 indicates no support.";
          }
          leaf UPnPBasicDevice {
            type uint32;
            description
              "Numeric value indicating the supported revision for
               UPnP Basic Device.
            
               A value of 0 indicates no support.";
          }
          leaf UPnPQoSDevice {
            type uint32;
            description
              "Numeric value indicating the supported revision for
               UPnP Qos Device.
            
               A value of 0 indicates no support.";
          }
          leaf UPnPQoSPolicyHolder {
            type uint32;
            description
              "Numeric value indicating the supported revision for
               UPnP Qos Policy Holder.
            
               A value of 0 indicates no support.";
          }
          leaf UPnPIGD {
            type uint32;
            description
              "Numeric value indicating the supported revision for
               UPnP IGD.
            
               A value of 0 indicates no support.";
          }
          leaf UPnPDMBasicMgmt {
            type uint32;
            description
              "Numeric value indicating the supported revision for
               UPnP-DM Basic Management.
            
               A value of 0 indicates no support.";
          }
          leaf UPnPDMConfigurationMgmt {
            type uint32;
            description
              "Numeric value indicating the supported revision for
               UPnP-DM Configuration Management.
            
               A value of 0 indicates no support.";
          }
          leaf UPnPDMSoftwareMgmt {
            type uint32;
            description
              "Numeric value indicating the supported revision for
               UPnP-DM Software Management.
            
               A value of 0 indicates no support.";
          }
        }
      }

      container Discovery {
        config false;
        description
          "UPnP {{bibref|UPnP-DAv1}} SSDP discovered root devices,
           embedded devices and embedded services.
        
           The CPE MAY, but need not, retain some or all of the
           information in this object across reboots.";

        list RootDevice {
          key "UUID";
          description
            "UPnP root device table.  This table contains an entry
             for each UPnP root device that has been discovered
             via SSDP.";
          leaf Status {
            type enumeration {
              enum "LeaseActive";
              enum "LeaseExpired";
              enum "ByebyeReceived";
            }
            description
              "The status of the UPnP root device.  {{enum}}
            
               The ability to list inactive UPnP root devices is
               OPTIONAL.  The length of time an inactive device
               remains listed in this table is a local matter to
               the CPE.";
          }
          leaf UUID {
            type string {
              length "0..36";
              pattern "[0-9A-Fa-f]{8}-([0-9A-Fa-f]{4}-){3}[0-9A-Fa-f]{12}";
            }
            description
              "This UPnP root device's UUID (Universally Unique
               IDentifier) {{bibref|RFC4122}}, extracted from any
               of its USN (Unique Service Name) headers.  This is
               a 36-byte string that uniquely identifies the
               device, the following is an example:
            
               : ''02c29d2a-dbfd-2d91-99c9-306d537e9856''
            
               {{pattern}}";
          }
          leaf USN {
            type string {
              length "0..256";
            }
            description
              "The value of the USN (Unique Service Name) header for
               this UPnP root device.  Three discovery messages
               are sent for root devices, and this SHOULD be the
               value of the USN header of the following form:
            
               :
               ''uuid:device-UUID::urn:domain-name:device:deviceType:v''
            
               SSDP is an unreliable protocol and it is possible
               that no discovery message containing the USN
               header of the above form was ever received.  If
               so, one of the other two forms MAY be used:
            
               : ''uuid:device-UUID::upnp:rootdevice''
            
               : ''uuid:device-UUID'' (for root device UUID)";
          }
          leaf LeaseTime {
            type uint32;
            description
              "The UPnP root device lease time in {{units}},
               extracted from the CACHE-CONTROL header.";
          }
          leaf Location {
            type string {
              length "0..256";
            }
            description
              "The value of the LOCATION header for this UPnP root
               device, which is the URL of the root device's DDD
               (Device Description Document).";
          }
          leaf Server {
            type string {
              length "0..256";
            }
            description
              "The value of the SERVER header for this UPnP root
               device, which is a string of the following form:
            
               : ''OS/version UPnP/udaversion product/version''
            
               where '''UPnP''' is a literal string,
               '''udaversion''' is the version of the UPnP Device
               Architecture.";
          }
          leaf Host {
            type string {
              length "0..256";
            }
            description
              "{{list}} Indicates the full path names of all Host
               table entries, whether active or inactive, that
               correspond to this UPnP root device.
            
               As such entries are added to or removed from the
               Host tables, the value of this parameter MUST be
               updated accordingly.";
          }
          leaf LastUpdate {
            type yang:date-and-time;
            description
              "The date and time at which the last advertisement
               from this {{object}} was received.";
          }
        }

        list Device {
          key "UUID";
          description
            "UPnP embedded device table.  This table contains an
             entry for each UPnP embedded device that has been
             discovered via SSDP.";
          leaf Status {
            type enumeration {
              enum "LeaseActive";
              enum "LeaseExpired";
              enum "ByebyeReceived";
            }
            description
              "The status of the UPnP embedded device.  {{enum}}
            
               The ability to list inactive UPnP embedded devices
               is OPTIONAL.  The length of time an inactive
               device remains listed in this table is a local
               matter to the CPE.";
          }
          leaf UUID {
            type string {
              length "0..36";
              pattern "[0-9A-Fa-f]{8}-([0-9A-Fa-f]{4}-){3}[0-9A-Fa-f]{12}";
            }
            description
              "This UPnP embedded device's UUID (Universally Unique
               IDentifier) {{bibref|RFC4122}}, extracted from any
               of its USN (Unique Service Name) headers.  This is
               a 36-byte string that uniquely identifies the
               device, the following is an example:
            
               : ''02c29d2a-dbfd-2d91-99c9-306d537e9856''
            
               {{pattern}}";
          }
          leaf USN {
            type string {
              length "0..256";
            }
            description
              "The value of the USN (Unique Service Name) header for
               this UPnP embedded device.  Two discovery messages
               are sent for embedded devices, and this SHOULD be
               the value of the USN header of the following form:
            
               :
               ''uuid:device-UUID::urn:domain-name:device:deviceType:v''
            
               SSDP is an unreliable protocol and it is possible
               that no discovery message containing the USN
               header of the above form was ever received.  If
               so, the other form MAY be used:
            
               : ''uuid:device-UUID''";
          }
          leaf LeaseTime {
            type uint32;
            description
              "The UPnP embedded device lease time in {{units}},
               extracted from the CACHE-CONTROL header.";
          }
          leaf Location {
            type string {
              length "0..256";
            }
            description
              "The value of the LOCATION header for this UPnP
               embedded device, which is the URL of the root
               device's DDD (Device Description Document).";
          }
          leaf Server {
            type string {
              length "0..256";
            }
            description
              "The value of the SERVER header for this UPnP embedded
               device, which is a string of the following form:
            
               : ''OS/version UPnP/udaversion product/version''
            
               where '''UPnP''' is a literal string,
               '''udaversion''' is the version of the UPnP Device
               Architecture.";
          }
          leaf Host {
            type string {
              length "0..256";
            }
            description
              "{{list}} Indicates the full path names of all Host
               table entries, whether active or inactive, that
               correspond to this UPnP embedded device.
            
               As such entries are added to or removed from the
               Host tables, the value of this parameter MUST be
               updated accordingly.";
          }
          leaf LastUpdate {
            type yang:date-and-time;
            description
              "The date and time at which the last advertisement
               from this {{object}} was received.";
          }
        }

        list Service {
          key "USN";
          description
            "UPnP embedded service table.  This table contains an
             entry for each UPnP embedded service that has been
             discovered via SSDP.";
          leaf Status {
            type enumeration {
              enum "LeaseActive";
              enum "LeaseExpired";
              enum "ByebyeReceived";
            }
            description
              "The status of the UPnP embedded service.  {{enum}}
            
               The ability to list inactive UPnP embedded
               services is OPTIONAL.  The length of time an
               inactive service remains listed in this table is a
               local matter to the CPE.";
          }
          leaf USN {
            type string {
              length "0..256";
            }
            description
              "The value of the USN (Unique Service Name) header for
               this UPnP embedded service.  This is of the
               following form:
            
               :
               ''uuid:device-UUID::urn:domain-name:service:serviceType:v''";
          }
          leaf LeaseTime {
            type uint32;
            description
              "The UPnP embedded service lease time in {{units}},
               extracted from the CACHE-CONTROL header.";
          }
          leaf Location {
            type string {
              length "0..256";
            }
            description
              "The value of the LOCATION header for this UPnP
               embedded service, which is the URL of the root
               device's DDD (Device Description Document).";
          }
          leaf Server {
            type string {
              length "0..256";
            }
            description
              "The value of the SERVER header for this UPnP embedded
               service, which is a string of the following form:
            
               : ''OS/version UPnP/udaversion product/version''
            
               where '''UPnP''' is a literal string,
               '''udaversion''' is the version of the UPnP Device
               Architecture.";
          }
          leaf Host {
            type string {
              length "0..256";
            }
            description
              "{{list}} Indicates the full path names of all Host
               table entries, whether active or inactive, that
               correspond to this UPnP embedded service.
            
               As such entries are added to or removed from the
               Host tables, the value of this parameter MUST be
               updated accordingly.";
          }
          leaf LastUpdate {
            type yang:date-and-time;
            description
              "The date and time at which the last advertisement
               from this {{object}} was received.";
          }
          leaf ParentDevice {
            type string {
              length "0..256";
            }
            description
              "{{reference|the {{object|#.RootDevice}} or
               {{object|#.Device}} table entries that embeds this
               {{object}}}} This parameter is populated by
               extracting the \"device-UUID\" from the service's
               USN and matching the value against the root device
               or embedded device UUID value.";
          }
        }
      }

      container Description {
        config false;
        description
          "This object contains information from the Description
           Document discovered from the UPnP Devices and
           Services.";

        list DeviceDescription {
          key "URLBase";
          description
            "This table contains information read from the Device
             Description Document of discovered root devices.
          
             The CPE MAY, but need not, retain some or all of the
             information in this table after the associated SSDP
             advertisement (objects in the UPnP.Discovery.
             object tables) expires.
          
             In case the SSDP advertisement expires and the CPE
             deletes the related instances from the tables in
             UPnP.Discovery., the reference to such instances
             MUST be set to the empty string.";
          leaf URLBase {
            type string {
              length "0..256";
            }
            description
              "The value extracted from the URLBase element in the
               Device Description Document of the discovered root
               device.  If the URLBase element in the root
               device's Device Description Document is empty or
               absent, the URL from which the device description
               was retrieved (e.g.  the LOCATION from the SSDP
               message) is utilized as the URLBase.
            
               Note: the URLBase element is not recommended by
               {{bibref|UPnP-DAv1}} and is not permitted by
               {{bibref|UPnP-DAv11}}, so the value of {{param}}
               will usually be the URL from which the device
               description was retrieved.";
          }
          leaf SpecVersion {
            type string {
              length "0..256";
              pattern "\d+\.\d+";
            }
            description
              "The UPnP Device Architecture version extracted from
               the specVersion element in the Device Description
               Document of the discovered root device.  The
               {{param}} is encoded as \"major revison.minor
               revision\".  {{pattern}}";
          }
          leaf Host {
            type string {
              length "0..256";
            }
            description
              "{{list}} {{reference|the Host table entries
               associated with the root device from which the
               device description was retrieved|ignore}}";
          }
        }

        list DeviceInstance {
          key "UDN";
          description
            "This table contains the information from Device
             Description Document retrieved for a discovered UPnP
             root or embedded device.";
          leaf UDN {
            type yang:uuid;
            description
              "Unique Device Name of this device represented as a
               UUID for the device.
            
               This value is extracted from the UDN element in
               the Device Description Document with the leading
               uuid: removed.";
          }
          leaf ParentDevice {
            type string {
              length "0..256";
            }
            description
              "{{reference|a {{object}} table entry (if this is an
               embedded device) or {{empty}} (if this is a root
               device)}}";
          }
          leaf DiscoveryDevice {
            type string {
              length "0..256";
            }
            description
              "{{reference|a {{object|##.Discovery.RootDevice}}
               table entry (if this is a root device) or a
               {{object|##.Discovery.Device}} table entry (if
               this is an embedded device)}}
            
               This {{param}} value can be {{empty}} because the
               referenced object has been deleted or the CPE was
               unable to retrieve the Description Document due to
               some out-of-band error.  The determination to
               delete this {{object}} or use {{empty}} is
               implementation specific.";
          }
          leaf DeviceType {
            type string {
              length "0..256";
            }
            description
              "The value of the UPnP deviceType element in the
               Device Description Document for this {{object}},
               or {{empty}} if this value is not provided by the
               device.";
          }
          leaf FriendlyName {
            type string {
              length "0..128";
            }
            description
              "The value of the UPnP friendlyName element in the
               Device Description Document for this {{object}},
               or {{empty}} if this value is not provided by the
               device.";
          }
          leaf DeviceCategory {
            type string;
            description
              "Each list item is the value of an element in the
               Device Description Document for this {{object}}
               that indicates a device category (e.g.  \"AV_TV\"
               and \"AV_Recorder\"), or the value is {{empty}} if
               no such element is provided by the device.
            
               Note: It is assumed that the
               ''htip:X_DeviceCategory'' Device Description
               Document element is used for HTIP (Home-network
               Topology Identifying Protocol)
               {{bibref|JJ-300.00}} and {{bibref|G.9973}}.
               Standard HTIP device categories are defined in
               {{bibref|JJ-300.01}}.  In this case, the maximum
               length of the list is 127 and of each item is 31,
               and any non-HTIP device categories SHOULD NOT
               conflict with standard HTIP device categories.
            
               Note: {{param}} is different from
               {{param|DeviceType}} and is included here for the
               purpose of HTIP usage.";
          }
          leaf Manufacturer {
            type string {
              length "0..128";
            }
            description
              "The value of the UPnP manufacturer element in the
               Device Description Document for this {{object}},
               or {{empty}} if this value is not provided by the
               device.";
          }
          leaf ManufacturerOUI {
            type string {
              length "0..6";
              pattern "";
              pattern "[0-9A-F]{6}";
            }
            description
              "The value of an element in the Device Description
               Document for this {{object}} that indicates the
               manufacturer OUI if this value is provided by the
               device; or {{empty}} if this value is not provided
               by the device.
            
               {{pattern}}
            
               Note: It is assumed that the
               ''htip:X_ManufacturerOUI'' element is used for
               HTIP (Home-network Topology Identifying Protocol)
               {{bibref|JJ-300.00}} and {{bibref|G.9973}}.";
          }
          leaf ManufacturerURL {
            type string {
              length "0..256";
            }
            description
              "The value of the UPnP manufacturerURL element in the
               Device Description Document for this {{object}},
               or {{empty}} if this value is not provided by the
               device.";
          }
          leaf ModelDescription {
            type string {
              length "0..256";
            }
            description
              "The value of the UPnP modelDescription element in the
               Device Description Document for this {{object}},
               or {{empty}} if this value is not provided by the
               device.";
          }
          leaf ModelName {
            type string {
              length "0..64";
            }
            description
              "The value of the UPnP modelName element in the Device
               Description Document for this {{object}}, or
               {{empty}} if this value is not provided by the
               device.";
          }
          leaf ModelNumber {
            type string {
              length "0..64";
            }
            description
              "The value of the UPnP modelNumber element in the
               Device Description Document for this {{object}},
               or {{empty}} if this value is not provided by the
               device.";
          }
          leaf ModelURL {
            type string {
              length "0..256";
            }
            description
              "The value of the UPnP modelURL element in the Device
               Description Document for this {{object}}, or
               {{empty}} if this value is not provided by the
               device.";
          }
          leaf SerialNumber {
            type string {
              length "0..128";
            }
            description
              "The value of the UPnP serialNumber element in the
               Device Description Document for this {{object}},
               or {{empty}} if this value is not provided by the
               device.";
          }
          leaf UPC {
            type string {
              length "0..12";
            }
            description
              "The value of the UPnP UPC element in the Device
               Description Document for this {{object}}, or
               {{empty}} if this value is not provided by the
               device.";
          }
          leaf PresentationURL {
            type string {
              length "0..256";
            }
            description
              "The value of the UPnP presentationURL element in the
               Device Description Document for this {{object}}
               and MUST be an absolute URL.
            
               The way to obtain an absolute URL from the
               presentationURL element is specified in
               {{bibref|UPnP-DAv1}} and {{bibref|UPnP-DAv11}}.
            
               If the presentationURL is not provided by the
               device then this value MUST be {{empty}}.";
          }
        }

        list ServiceInstance {
          key "ParentDevice ServiceId";
          description
            "This table contains the information from Device
             Description Document retrieved for a discovered UPnP
             service.";
          leaf ParentDevice {
            type string {
              length "0..256";
            }
            description
              "{{reference|a {{object|#.DeviceInstance}} table
               entry}}";
          }
          leaf ServiceId {
            type string {
              length "0..256";
            }
            description
              "The value of the UPnP serviceId element in the Device
               Description Document for this {{object}}, or
               {{empty}} if this value is not provided by the
               service.
            
               If the UPnP serviceId is not provided by the UPnP
               service, this {{object}} MUST be deleted.";
          }
          leaf ServiceDiscovery {
            type string {
              length "0..256";
            }
            description
              "{{reference|a {{object|##.Discovery.Service}} table
               entry}}
            
               This {{param}} value can be {{empty}} because the
               referenced object has been deleted or the CPE was
               unable to retrieve the Description Document due to
               some out-of-band error.  The determination to
               delete this {{object}} or use {{empty}} is
               implementation specific.";
          }
          leaf ServiceType {
            type string {
              length "0..256";
            }
            description
              "The value of the UPnP serviceType element in the
               Device Description Document for this {{object}},
               or {{empty}} if this value is not provided by the
               service.";
          }
          leaf SCPDURL {
            type string;
            description
              "The value of the UPnP SCPDURL element in the Device
               Description Document for this {{object}} and MUST
               be an absolute URL.
            
               The way to obtain an absolute URL from the SCPDURL
               element is specified in {{bibref|UPnP-DAv1}} and
               {{bibref|UPnP-DAv11}}.
            
               If the SCPDURL is not provided by the device then
               this value MUST be {{empty}}.";
          }
          leaf ControlURL {
            type string;
            description
              "The value of the UPnP controlURL element in the
               Device Description Document for this {{object}}
               and MUST be an absolute URL.
            
               The way to obtain an absolute URL from the
               controlURL element is specified in
               {{bibref|UPnP-DAv1}} and {{bibref|UPnP-DAv11}}.
            
               If the controlURL is not provided by the device
               then this value MUST be {{empty}}";
          }
          leaf EventSubURL {
            type string;
            description
              "The value of the UPnP eventSubURL element in the
               Device Description Document for this {{object}}
               and MUST be an absolute URL.
            
               The way to obtain an absolute URL from the
               eventSubURLL element is specified in
               {{bibref|UPnP-DAv1}} and {{bibref|UPnP-DAv11}}.
            
               If the eventSubURL is not provided by the device
               then this value MUST be {{empty}}";
          }
        }
      }
    }

    container ETSIM2M {
      description
        "The {{object}} object represents the management object for
         the Remote Entity Functions (REM) functions defined in
         the M2M Functional Architecture {{bibref|ETSIM2MFA}}.";

      list SCL {
        key "Alias";
        description
          "This object represents an instance of a Service
           Capability Layer (SCL) for a M2M device or gateway.
        
           The {{object}} MAY be maintained by the ACS or by the
           CPE.
        
           When the {{object}} provides the administration of an
           SCL that is represented as a
           {{object|.SoftwareModules.ExecutionUnit}} the
           {{object}} is maintained in the
           {{param|.SoftwareModules.ExecutionUnit.{i}.References}}
           parameter.
        
           Section 5.1.2 of the M2M Functional Architecture
           {{bibref|ETSIM2MFA}} describes the high level event
           flows for SCL registration.
        
           Section 9.3.2.6.2 of the M2M Functional Architecture
           {{bibref|ETSIM2MFA}} describes the
           creation/registration of SCLs.
        
           Section 9.3.2.6.4 of the M2M Functional Architecture
           {{bibref|ETSIM2MFA}} describes the
           update/re-registration of SCLs.
        
           Section 9.3.2.6.5 of the M2M Functional Architecture
           {{bibref|ETSIM2MFA}} describes the
           deletion/deregistration of SCLs.
        
           {{keys}}";
        leaf Enable {
          type boolean;
          default "false";
          description
            "Administratively enables or disables this instance.";
        }
        leaf AnnouncedToSCLList {
          type string;
          description
            "{{list}} The list represents an unordered set of URIs
             {{bibref|RFC3986}}.
          
             A list item is a URI string that represents a SCL to
             which the this {{object}} will announce original
             (local) resources.
          
             The AnnouncedToSCL has an interest in the discovery
             of the local resource.  Section 9.2.1.14 Announced
             Resource of the M2M Functional Architecture
             {{bibref|ETSIM2MFA}} provides a description of this
             behavior of an Announced Resource.
          
             Section 9.3.2.28 of the M2M Functional Architecture
             {{bibref|ETSIM2MFA}} and Section 10.3.2.7 of the M2M
             mIa, dIa and mId Interfaces
             {{bibref|ETSIM2MInterfaces}} describes the process
             of announcing and deannouncing of resources within a
             SCL.";
        }

        container Discovery {
          description
            "This object is represents the administration properties
             used when a NSCL requests discovery of resources
             within this {{object|##.SCL}} instance.
          
             Section 9.3.2.27 of the M2M Functional Architecture
             {{bibref|ETSIM2MFA}} describes the process of
             discovery of resources within a SCL.";
          leaf MaxNumberOfDiscovRecords {
            type uint32;
            description
              "The maximum number of URIs {{bibref|RFC3986}} for
               discovered resources contained in a discovery
               result.
            
               This parameter and the
               {{param|MaxSizeOfDiscovAnswer}} parameter are
               mutually exclusive in that a result can be limited
               due to the bounds of either parameter.
            
               A value of 0 indicates that the SCL does not have
               a limit for this parameter.";
          }
          leaf MaxSizeOfDiscovAnswer {
            type uint32;
            description
              "The maximum size in bytes of the Discovery Answer.
            
               This parameter and the
               {{param|MaxNumberOfDiscovRecords}} parameter are
               mutually exclusive in that a result can be limited
               due to the bounds of either parameter.
            
               A value of 0 indicates that the SCL does not have
               a limit for this parameter.";
          }
        }

        container Reregistration {
          description
            "This object represents the properties and status
             necessary for a SCL to reregister with one or more
             NSCLs.";
          leaf RegTargetNSCLList {
            type string;
            description
              "{{list}} The list represents a priority ordered set
               of URIs {{bibref|RFC3986}}.  The item that is
               first in the list has the highest priority.
            
               A list item is a URI {{bibref|RFC3986}} string
               that represents a NSCL that this {{object|##.SCL}}
               instance can use in order to attempt registration.
            
               When modified the contents of this parameter
               replace the {{param}} received during the
               bootstrap procedure.";
          }
          leaf RegSearchStrings {
            type string;
            description
              "{{list}} The list represents the string tokens used
               as keys when searching for this {{object|##.SCL}}
               instance.
            
               Sections 9.2.3.6.2 and 9.2.3.6.4 of the M2M
               Functional Architecture {{bibref|ETSIM2MFA}}
               describe the usage for this parameter.";
          }
          leaf RegAccessRightID {
            type string;
            description
              "URI {{bibref|RFC3986}} that represents the identifier
               of the access right resource.  The value of this
               parameter is maintained by the NSCL and used by
               the SCL as a default access right identifier for
               re-registration to NSCLs.";
          }
          leaf RegExpirationDuration {
            type int32;
            default "-1";
            description
              "The duration, in {{units}}, that the SCL will use in
               its next re-registration attempt.  Any negative
               value represents an infinite duration.";
          }
          leaf Reregistration {
            type boolean; /* command */
            description
              "{{command}} When set to {{true}}, triggers an
               immediate re-registration action where the SCL
               re-registers with the SCLs in the
               {{param|RegTargetNSCLList}} .";
          }

          container ActionStatus {
            config false;
            description
              "This object represents the status of the
               Reregistration action.";
            leaf Progress {
              type uint32 {
                range "0..100";
              }
              description
                "The progress, in {{units}}, of the Reregistration
                 action.  The progress is measured from 0-100%.
                 A value of 0 indicates that the action has not
                 started.  A value of 100 indicates that the
                 action has completed.";
            }
            leaf FinalStatus {
              type enumeration {
                enum "SUCCESS";
                enum "FAILURE";
              }
              description
                "The completion status of the Reregistration
                 operation.  Enumeration of:
              
                 {{enum}}";
            }
          }
        }

        list SAFPolicySet {
          key "Alias";
          description
            "This object describes the parameters necessary to
             administer the store-and-forward (SAF) handling
             policies applied to requests to access remotely
             hosted resources.
          
             Policies are described by instances of {{object}}.
             Which instances of {{object}} are used by the SCL is
             determined by the {{param|PolicyScope}} parameter.
          
             Section 9.3.1.5 of the M2M Functional Architecture
             {{bibref|ETSIM2MFA}} and Section 10.3.1.2.2 of the
             M2M mIa, dIa and mId Interfaces
             {{bibref|ETSIM2MInterfaces}} describe the behavior
             for SAF processing.
          
             There is at most one {{object}} instance with the
             {{param|PolicyScope}} containing a specific
             application id (APP-ID) URI value within the list.
          
             There is exactly one {{object}} instance with a
             {{param|PolicyScope}} value of \"default\".";
          leaf Enable {
            type boolean;
            default "false";
            description
              "Administratively enables or disables this instance.";
          }
          leaf PolicyScope {
            type string;
            default "";
            description
              "The parameter defines the scope of the policies
               contained in this instance of a
               {{object|#.SAFPolicySet}}.
            
               The parameter value is:
            
               *a list of unordered set of URIs
               {{bibref|RFC3986}} that represents an M2M
               application id (APP-ID)
            
               *the value of \"default\"
            
               *{{empty}}
            
               When this parameter is set to a list of
               application id (APP-ID) URIs {{bibref|RFC3986}},
               the scope indicates that the policies are
               applicable to requests coming from any specific
               application on that list.
            
               When this parameter is set to a string with the
               value \"default\", the scope indicates that the
               policies are the default policies for this
               {{object|##.SCL}} instance.
            
               When this parameter is set to {{empty}}, the value
               represents an unknown {{object|#.SAFPolicySet}}
               and the {{object|#.SAFPolicySet}} is not to be
               used.";
          }

          list ANPPolicy {
            key "ANName";
            description
              "This table contains the SAF-handling policies which
               are controlled by the Access Network Provider(s).
            
               {{keys}}";
            leaf Enable {
              type boolean;
              default "false";
              description
                "Administratively enables or disables this instance.";
            }
            leaf ANName {
              type string;
              default "";
              description
                "This parameter is the name of the access network
                 provider and used to determine for which access
                 network the policies defined in the
                 {{object|#.ANPPolicy}} table will apply.";
            }

            list BlockPeriod {
              key "FailedAttempts";
              description
                "This table contains a list of block periods for a
                 {{object|##.ANPPolicy}}.
              
                 A block period defines how long the device will
                 wait before re-trying to establish connectivity
                 via the access network after the previous
                 attempt has failed.";
              leaf Enable {
                type boolean;
                default "false";
                description
                  "Administratively enables or disables this
                   instance.";
              }
              leaf FailedAttempts {
                type uint32;
                default "0";
                description
                  "Number of consecutively failed access attempts
                   for which the {{param|BlockDuration}} will be
                   used to block the next access attempt.
                
                   The SCL will apply the {{object}} entry with
                   the largest number of consecutive failed
                   attempts that is smaller or equal to the
                   actual number of consecutive failed attempts.";
              }
              leaf BlockDuration {
                type int32;
                default "0";
                description
                  "The duration, in {{units}}, to which to block
                   further access attempts.";
              }
            }

            list RequestCategory {
              key "RCAT";
              description
                "This table contains the Request Category (RCAT)
                 policy items for defining when it is appropriate
                 to use the access network for processing
                 requests.";
              leaf Enable {
                type boolean;
                default "false";
                description
                  "Administratively enables or disables this
                   instance.";
              }
              leaf RCAT {
                type string;
                description
                  "An RCAT is a string that represents a request
                   category used for policy enforcement.";
              }

              list Schedule {
                key "Alias";
                description
                  "This table contains the schedules that define
                   when it is appropriate to use the access
                   network for processing requests for the
                   specified value of the {{param|#.RCAT}}.
                
                   The combination of all instances of the
                   {{object|AbsTimeSpan}} along with the
                   {{param|Schedules}} parameter makes up the
                   complete schedule for this instance of a
                   {{object}}.
                
                   The {{param|Schedules}} parameter defines a
                   recurrence of the schedule.  If instances of
                   {{object|AbsTimeSpan}} exist, these instances
                   places constraints on the schedule recurrence.
                
                   If the value of the {{param|Schedules}}
                   parameter is {{empty}}, at least one enabled
                   instance of {{object|AbsTimeSpan}} MUST exist.
                
                   Processing behavior for the use of RCAT
                   Schedules is defined in section 10.3.1.2.2 of
                   the M2M mIa, dIa and mId Interfaces
                   {{bibref|ETSIM2MInterfaces}} document.";
                leaf Enable {
                  type boolean;
                  default "false";
                  description
                    "Administratively enables or disables this
                     instance.";
                }
                leaf Schedules {
                  type string;
                  default "";
                  description
                    "The list is a set of schedule strings.
                  
                     A schedule string is formatted according to
                     the date and time fields defined CRONTAB
                     input file definition in
                     {{bibref|POSIXBase}}.
                  
                     The {{param}} parameter is used to set the
                     recurrence of the schedule.
                  
                     The timezone used for this parameter is
                     dependent upon the existence of instances of
                     {{object|AbsTimeSpan}} for this {{object}}.
                     If instances of {{object|AbsTimeSpan}}
                     exist, then the timezone of the
                     {{object|AbsTimeSpan}} is used otherwise the
                     UTC timezone is used for this {{param}}
                     parameter.
                  
                     Note the command field is not used in this
                     definition and any whitespace or comma
                     characters within a Schedule string MUST be
                     escaped using percent as defined in
                     {{bibref|TR-106a5|section 3.2.3}}
                  
                     Example of CRONTAB string:
                  
                     *\"* 0-6 * * 1-5\" would mean every minute
                     for the period from 0:00h to 6:00h
                     (inclusive) on any week day (Monday through
                     Friday) and would be represented as
                     \"*%200-6%20*%20*%201-5\"
                  
                     *\"*/15 22-23,0-4 * * 1-5\" would mean every
                     15 minutes for the period from 22:00h to
                     04:00h on any week day (Monday through
                     Friday) and would be represented as
                     \"*/15%2022-23%2C0-4%20*%20*%201-5\"";
                }

                list AbsTimeSpan {
                  key "Alias";
                  description
                    "This object defines an instance of a time span
                     used for determining an RCAT schedule.
                  
                     An instance of the {{object}} represents the
                     time span in which the schedule recurrence
                     defined in {{param|#.Schedules}} is
                     constrained.
                  
                     {{object}} instances with unknown values for
                     the {{param|StartTime}} or {{param|EndTime}}
                     are ignored.
                  
                     All instances of the {{object}} within this
                     {{object|##.Schedule}} MUST utilize the same
                     time zone.";
                  leaf Enable {
                    type boolean;
                    default "false";
                    description
                      "Administratively enables or disables this
                       instance.";
                  }
                  leaf StartTime {
                    type yang:date-and-time;
                    default "0001-01-01T00:00:00Z";
                    description
                      "Date and time that represents the start of
                       the time span.
                    
                       The value 0001-01-01T00:00:00Z represents
                       an unknown value.
                    
                       The device MUST reject requests to set the
                       {{param}} value greater than the
                       {{param|EndTime}} value.";
                  }
                  leaf EndTime {
                    type yang:date-and-time;
                    default "0001-01-01T00:00:00Z";
                    description
                      "Date and time that represents the end of the
                       time span.
                    
                       The value 9999-12-31T23:59:59Z represents
                       an infinite time span from the start time.
                    
                       The value 0001-01-01T00:00:00Z represents
                       an unknown value.
                    
                       The device MUST reject requests to set the
                       {{param}} value less than or equal the
                       {{param|StartTime}} value.";
                  }
                }
              }
            }
          }

          container M2MSPPolicy {
            description
              "This object maintains the SAF handling policies'
               properties that are controlled by the M2M service
               provider for a request.";
            leaf DefaultRCATValue {
              type string;
              default "";
              description
                "The default RCAT value to use for requests to
                 remotely hosted resources during SAF-handling
                 when no RCAT value was specified in the request.";
            }

            list RequestCategory {
              key "RCAT";
              description
                "This object maintains a list of properties to be
                 used for forwarding requests with a specified
                 {{param|RCAT}}.
              
                 Processing behavior for the use of M2M Service
                 Provider policies is defined in section
                 10.3.1.2.2.1 of the M2M mIa, dIa and mId
                 Interfaces {{bibref|ETSIM2MInterfaces}}
                 document.";
              leaf Enable {
                type boolean;
                default "false";
                description
                  "Administratively enables or disables this
                   instance.";
              }
              leaf RCAT {
                type string;
                description
                  "An RCAT is a string that represents a request
                   category used for policy enforcement.";
              }
              leaf TolerableDelay {
                type int32 {
                  range "-1..max";
                }
                default "0";
                description
                  "The tolerable duration, in {{units}}, that a
                   request of the given RCAT category can be
                   pending in SAF handling when a request from an
                   M2M Application does not specify a tolerable
                   delay.
                
                   A value of -1 represents an infinite duration.";
              }
              leaf Thresh {
                type uint32;
                default "0";
                description
                  "The threshold of maximum number of pending
                   requests permitted to be held for a specified
                   RCAT.
                
                   A value of 0 indicates that the request should
                   be transmitted immediately.";
              }
              leaf Mem {
                type string {
                  pattern "([0-9]{1,15}?[BKMGT])";
                  pattern "";
                }
                description
                  "This parameter defines the maximum size of the
                   request queue for pending requests permitted
                   to be held for a specified RCAT.
                
                   The format of the string is an integer with an
                   appended memory unit (B - Bytes, K - 1024
                   Bytes, M - 1048576 Bytes, G -1073741824, T -
                   1099511627776 Bytes).
                
                   When the value is {{empty}} the memory
                   threshold criteria for the associated RCATList
                   will be ignored in SAF handling.
                
                   {{pattern}}";
              }
              leaf RankedANList {
                type string;
                default "";
                description
                  "The list is a prioritized set of Access Networks
                   where the preference of using an Access
                   Network is based on order of the list items
                   with the lowest order list item as the most
                   preferred Access Network.";
              }
            }
          }
        }

        list AreaNwkInstance {
          key "ID";
          config false;
          description
            "The M2M Area Network information provides
             administration capabilities for remote management
             (REM) of M2M Devices (D', d) that are attached to
             this {{object|##.SCL}} instance.
          
             This object provides the administration of the
             properties needed by the SCL to remotely manage M2M
             Devices within a specific type of M2M Area network
             as defined by {{param|AreaNwkType}}.
          
             Multiple instances of {{object}} with the same
             {{param|AreaNwkType}} is permitted.
          
             Section 5.3.5 of the M2M Functional Architecture
             {{bibref|ETSIM2MFA}} describes the REM functionality
             expected of a SCL for an M2M Device.";
          leaf ID {
            type string;
            description
              "URI {{bibref|RFC3986}} that represents the identifier
               of the instance.";
          }
          leaf AreaNwkType {
            type string;
            description
              "Devices (D' and d) that connect to an SCL are said to
               be \"attached devices\" and are organized by M2M
               Area Networks within the {{object|##.SCL}}
               instance.  The {{param}} is an
               implementation-chosen string that indicates the
               type of M2M Area Network.";
          }
          leaf ListOfDevices {
            type string;
            description
              "{{list}} {{reference}}
            
               The list represents the M2M Devices (D', d) that
               are attached to this {{object|##.SCL}} instance
               that are within this {{object}} instance.  The
               list does not contain an instance for this CPE.";
          }

          list Property {
            description
              "This object contains an instance of a property
               extension (name value pair) for this
               {{object|##.AreaNwkInstance}} instance.
            
               For example, if the {{param|#.AreaNwkType}} is
               ZigBee the {{object|##.AreaNwkInstance}} will
               contain ZigBee specific parameters that have not
               been modeled for the M2M Area network.
            
               At a minimum, a property instance MUST exist that
               defines an attribute that describes the IP layer
               address type (e.g., IPv4, IPv6, non-IP) of this
               M2M Area Network.";
            leaf Name {
              type string;
              description
                "The name of the property";
            }
            leaf Value {
              type string;
              description
                "The value of the property.";
            }
          }
        }

        list AreaNwkDeviceInfoInstance {
          description
            "The M2M Area Network Device Information provides the
             administration capability to the SCL for maintenance
             of M2M Devices (D', d) that are attached to this
             {{object|##.SCL}} instance.
          
             While discovery and identification of devices by the
             M2M Gateway or Device (CPE) is implementation
             specific, each device is represented by an instance
             of the {{object|.Hosts.Host}} table.
          
             When the M2M Device is managed by the CWMP endpoint
             of the CPE, the {{object}} is expected to be
             referenced by an instance of one of the following
             tables:
          
             *{{object|.ManagementServer.EmbeddedDevice}}
          
             *{{object|.ManagementServer.VirtualDevice}}
          
             Section 5.3.5 of the M2M Functional Architecture
             {{bibref|ETSIM2MFA}} describes the REM functionality
             expected of a SCL to a M2M Device.
          
             This object instance provides the administration
             properties required by a SCL to remotely manage an
             instance of a M2M Device within a M2M area network.
          
             A M2M Device is associated with an instance of a
             {{object|#.AreaNwkInstance}}.
          
             This table contains parameters and information of
             the M2M Device related to each
             {{object|#.AreaNwkInstance}} instance.
          
             Instances of this table are created and deleted by
             the CPE.  The ACS MAY modify the writeable
             parameters of this object instance but it is
             possible that the value set by the ACS is not
             retained between reboots of the M2M Device.";
          leaf AreaNwkInstance {
            type string;
            config false;
            description
              "{{reference}}";
          }
          leaf Host {
            type string;
            config false;
            description
              "{{list}} {{reference|the {{object|.Hosts.Host}} table
               entry that represents an active or inactive M2M
               Device}}";
          }
          leaf ListOfDeviceNeighbors {
            type string;
            config false;
            description
              "{{list}} {{reference}} References all the
               {{object|.Hosts.Host}} table entries, whether
               active or inactive, that represent the reachable
               neighbors of this M2M Device (D' or d).";
          }
          leaf ListOfDeviceApplications {
            type string;
            config false;
            description
              "The list is an unordered set of URIs
               {{bibref|RFC3986}}.
            
               A list item is an URI string that represents an
               application id (APP-ID) for the M2M D'A
               applications residing on the M2M Device for the
               associated {{object|#.AreaNwkInstance}}.
            
               Table B.58 of the M2M Functional Architecture
               {{bibref|ETSIM2MFA}} describes this parameter.";
          }
          leaf SleepInterval {
            type uint32;
            description
              "The interval, in {{units}}, between sleep periods for
               the device.
            
               A value of 0 represents a device that does not
               sleep.
            
               Note: When this value is modified, the CPE could
               modify the {{param}} for this M2M Device in other
               Area Networks.";
          }
          leaf SleepDuration {
            type uint32;
            description
              "The duration, in {{units}}, of a sleep period.
            
               The value 0 represents an unknown value.
            
               Note: When this value is modified, the CPE could
               modify the {{param}} for this M2M Device in other
               Area Networks.";
          }
          leaf Status {
            type enumeration {
              enum "ASLEEP";
              enum "AWAKE";
            }
            config false;
            description
              "The sleep status of the device.
            
               Enumeration of:
            
               {{enum}}";
          }
          leaf Active {
            type boolean;
            config false;
            description
              "Whether or not this M2M Device is currently attached
               to this {{object|##.SCL}} instance.
            
               The ability to list inactive M2M Devices is
               OPTIONAL.  If the CPE includes inactive M2MDevices
               in this table, {{param}} is set to {{false}} for
               each inactive M2M Device.  The length of time an
               inactive M2M Device remains listed in this table
               is a local matter to the CPE.";
          }

          list Property {
            config false;
            description
              "This object contains an instance of a property
               extension (name value pair) for this
               {{object|##.AreaNwkDeviceInfoInstance}} instance.
            
               For example, if the
               {{param|##.AreaNwkInstance.{i}.AreaNwkType}} value
               is ZigBee, this
               {{object|##.AreaNwkDeviceInfoInstance}} contains
               ZigBee-specific parameters that are not formally
               modeled for this
               {{object|##.AreaNwkDeviceInfoInstance}} instance.";
            leaf Name {
              type string;
              description
                "The name of the property";
            }
            leaf Value {
              type string;
              description
                "The value of the property.";
            }
          }
        }
      }
    }

    container DLNA {
      config false;
      description
        "This object contains all DLNA related objects and
         parameters.";

      container Capabilities {
        description
          "DLNA capabilities.";
        leaf HNDDeviceClass {
          type string;
          description
            "{{list}} Indicates the supported DLNA Home Network
             Device Classes {{bibref|DLNA-NDIG|Table 4-1}}.";
        }
        leaf DeviceCapability {
          type string;
          description
            "{{list}} Indicates the supported DLNA Device
             Capabilities {{bibref|DLNA-NDIG|Table 4-2}}.";
        }
        leaf HIDDeviceClass {
          type string;
          description
            "{{list}} Indicates the supported DLNA Home
             Infrastructure Device Classes
             {{bibref|DLNA-NDIG|Table 4-4}}.";
        }
        leaf ImageClassProfileID {
          type string;
          description
            "{{list}} Indicates the DLNA Image Class Profile IDs
             supported by this device, from Tables 5-2 and 5-3 of
             {{bibref|DLNA-NDIG}}.";
        }
        leaf AudioClassProfileID {
          type string;
          description
            "{{list}} Indicates the DLNA Audio Class Profile IDs
             supported by this device, from Tables 5-4 through
             5-10 of {{bibref|DLNA-NDIG}}.";
        }
        leaf AVClassProfileID {
          type string;
          description
            "{{list}} Indicates the DLNA AV Class Profile IDs
             supported by this device, from Tables 5-11 through
             5-15 of {{bibref|DLNA-NDIG}}.";
        }
        leaf MediaCollectionProfileID {
          type string;
          description
            "{{list}} Indicates the DLNA Media Collection Profile
             IDs supported by this device
             {{bibref|DLNA-NDIG|Table 5-16}}.";
        }
        leaf PrinterClassProfileID {
          type string;
          description
            "{{list}} Indicates the DLNA Printer Class Profile IDs
             supported by this device {{bibref|DLNA-NDIG|Table
             5-17}}.";
        }
      }
    }

    container SelfTestDiagnostics {
      description
        "This diagnostics test is vendor-specific and MAY include
         testing hardware, software, and/or firmware.";
      leaf DiagnosticsState {
        type enumeration {
          enum "None";
          enum "Requested";
          enum "Complete";
          enum "Error_Internal";
          enum "Error_Other";
        }
        description
          "Indicates availability of diagnostic data.  {{enum}}
        
           If the ACS sets the value of this parameter to
           {{enum|Requested}}, the CPE MUST initiate the
           corresponding diagnostic test.  When writing, the only
           allowed value is {{enum|Requested}}.  To ensure the
           use of the proper test parameters (the writable
           parameters in this object), the test parameters MUST
           be set either prior to or at the same time as (in the
           same SetParameterValues) setting the DiagnosticsState
           to Requested.
        
           When requested, the CPE SHOULD wait until after
           completion of the communication session with the ACS
           before starting the diagnostic.
        
           When the test is completed, the value of this
           parameter MUST be either {{enum|Complete}} (if the
           test completed successfully), or one of the Error
           values listed above.
        
           If the value of this parameter is anything other than
           {{enum|Complete}}, the values of the results
           parameters for this test are indeterminate.
        
           When the diagnostic initiated by the ACS is completed
           (successfully or not), the CPE MUST establish a new
           connection to the ACS to allow the ACS to view the
           results, indicating the Event code \"8 DIAGNOSTICS
           COMPLETE\" in the Inform message.
        
           After the diagnostic is complete, the value of all
           result parameters (all read-only parameters in this
           object) MUST be retained by the CPE until either this
           diagnostic is run again, or the CPE reboots.  After a
           reboot, if the CPE has not retained the result
           parameters from the most recent test, it MUST set the
           value of this parameter to {{enum|None}}.
        
           Modifying any of the writable parameters in this
           object except for this one MUST result in the value of
           this parameter being set to {{enum|None}}.
        
           While the test is in progress, modifying any of the
           writable parameters in this object except for this one
           MUST result in the test being terminated and the value
           of this parameter being set to {{enum|None}}.
        
           While the test is in progress, setting this parameter
           to {{enum|Requested}} (and possibly modifying other
           writable parameters in this object) MUST result in the
           test being terminated and then restarted using the
           current values of the test parameters.";
      }
      leaf Results {
        type string {
          length "0..1024";
        }
        config false;
        description
          "Results of self-test (vendor specific).";
      }
    }

    container Firewall {
      description
        "Firewall configuration object.  The {{param|Config}}
         parameter enables and disables the Firewall, and can
         select either a predefined configuration
         ({{enum|High|Config}} or {{enum|Low|Config}}) or an
         explicitly-defined {{enum|Advanced|Config}}
         configuration.
      
         For an {{enum|Advanced|Config}} configuration,
         {{param|AdvancedLevel}} controls the currently active
         Firewall Level, and the Firewall Levels are defined in
         the {{object|Level}}, {{object|Chain}} and
         {{object|Chain.{i}.Rule}} tables.
      
         The Firewall rules modeled by this object operate only
         on the forwarding path.  This means that they affect
         only routed traffic, and do not affect traffic that is
         destined for or generated by the CPE.  Note that any
         {{object|#.NAT}} processing on the ingress packet occurs
         before Firewall rules are applied so, for example, the
         Firewall rules will see the translated destination IP
         address and port in a downstream packet that has passed
         through the NAT.
      
         See {{bibref|TR-181i2a2|Appendix VIII}} for an example
         {{enum|Advanced|Config}} configuration.";
      leaf Enable {
        type boolean;
        description
          "Enables or disables the Firewall.
        
           Firewalls often implement additional Denial of Service
           and other vulnerability protections, such as those
           described in {{bibref|ICSA-Baseline}}.  If a
           {{enum|Stateful|Type}} Firewall is enabled, then it is
           assumed that all implemented stateful protections are
           enabled, unless they are overridden by some other part
           of the data model.";
      }
      leaf Config {
        type enumeration {
          enum "High";
          enum "Low";
          enum "Off";
          enum "Advanced";
        }
        description
          "How this firewall is configured.  {{enum}}
        
           Vendors can extend the enumerated values with vendor
           specific extensions, in which case the rules outlined
           in {{bibref|TR-106a2|Section 3.3}} MUST be adhered to.";
      }
      leaf AdvancedLevel {
        type string;
        description
          "Selects the currently active Firewall Level.
        
           {{param}} only applies when {{param|Config}} is
           {{enum|Advanced|Config}}.";
      }
      leaf Type {
        type enumeration {
          enum "Stateless";
          enum "Stateful";
        }
        config false;
        description
          "Firewall Type.  {{enum}}
        
           A {{enum|Stateless}} Firewall treats each packet
           individually and thus has no concept of sessions.
           Therefore a {{enum|Stateless}} Firewall cannot
           distinguish between unsolicited downstream traffic and
           downstream traffic in response to outbound messages.
           This means that it has to accept all incoming
           downstream traffic.  Furthermore, because a
           {{enum|Stateless}} Firewall treats each packet
           individually, it does not provide any DoS or
           vulnerability protections.
        
           A {{enum|Stateful}} Firewall maintains state about
           previous packets and thus supports sessions.
           Therefore a {{enum|Stateful}} Firewall can distinguish
           between solicited and unsolicited downstream traffic.
           In a {{enum|Stateful}} Firewall, explicitly configured
           rules only apply to unsolicited traffic, and can not
           cause packets received in response to an upstream
           request to be dropped.  Furthermore, because a
           {{enum|Stateful}} Firewall maintains state, it can
           provide DoS and vulnerability protections.
        
           A device that has a {{enum|Stateless}} Firewall
           depends on the NAT to provide protection against
           unsolicited downstream IPv4 traffic.  This is because,
           as noted above, a {{enum|Stateless}} Firewall has to
           be configured to accept all incoming downstream
           traffic.  For IPv6 there is no NAT, so a
           {{enum|Stateless}} Firewall can not provide simple
           security protections against unsolicited downstream
           IPv6 traffic.";
      }
      leaf Version {
        type string {
          length "0..16";
        }
        config false;
        description
          "A string identifying the firewall settings version
           currently used in the CPE, or {{empty}} if the
           firewall settings are not associated with a version.";
      }
      leaf LastChange {
        type yang:date-and-time;
        config false;
        description
          "The time at which the firewall settings most recently
           changed.";
      }

      list Level {
        key "Alias";
        description
          "Firewall Level table.  When an {{enum|Advanced|#.Config}}
           configuration is selected, {{param|#.AdvancedLevel}}
           selects the currently active entry in this table.
           Each {{object}} table entry references the
           {{object|#.Chain}} that contains the rules for this
           level.";
        leaf Name {
          type string {
            length "0..64";
          }
          description
            "Human-readable name associated with this {{object}}
             entry.";
        }
        leaf Description {
          type string {
            length "0..256";
          }
          description
            "Human-readable description associated with this
             {{object}} entry.";
        }
        leaf Order {
          type uint32 {
            range "1..max";
          }
          description
            "Position of the {{object}} entry for user interface
             display; levels can be presented according to an
             increasing or decreasing level of security.
          
             When this value is modified, if the value matches
             that of an existing entry, the {{param}} value for
             the existing entry and all greater-valued {{param}}
             entries is incremented to ensure uniqueness of this
             value.  A deletion causes {{param}} values to be
             compacted.  When a value is changed, incrementing
             occurs before compaction.
          
             The value of {{param}} on creation of a {{object}}
             table entry MUST be one greater than the largest
             current value.";
        }
        leaf Chain {
          type string;
          config false;
          description
            "The Chain containing Firewall Level Rules associated
             with this {{object}} entry.
          
             On creation of a new {{object}} entry, the device
             will automatically create a new {{object|#.Chain}}
             table entry that this {{param}} parameter will
             reference.";
        }
        leaf PortMappingEnabled {
          type boolean;
          default "true";
          description
            "Indicates whether NAT port mapping is enabled or
             disabled when this is the active Level.  For a
             {{enum|Stateless|#.Type}} Firewall this can be set
             to {{false}} to force any port mappings to be
             operationally disabled (for a
             {{enum|Stateful|#.Type}} Firewall this is not
             necessary because the same effect can be achieved
             via Firewall rules).
          
             This parameter affects all the interfaces on which
             NAT is enabled.  It operationally enables or
             disables port mapping functionality and therefore
             does not affect the individual
             {{param|##.NAT.PortMapping.{i}.Enable}} settings.
             Note that the current NAT status and NAT port
             mapping status are indicated by the
             {{param|##.NAT.InterfaceSetting.{i}.Status}}
             parameter.";
        }
        leaf DefaultPolicy {
          type enumeration {
            enum "Drop";
            enum "Accept";
            enum "Reject";
          }
          default "Drop";
          description
            "Default action for packets not matching any of the
             level rules.  {{enum}}";
        }
        leaf DefaultLogPolicy {
          type boolean;
          default "false";
          description
            "Enable or disable logging, in a
             {{object|##.DeviceInfo.VendorLogFile}}, of packets
             not matching any of the level rules.";
        }
      }

      list Chain {
        key "Alias";
        description
          "Firewall Chain table.  Each entry contains an ordered
           list of {{object|Rule}} objects which can themselves
           reference other {{object}} instances.  A hierarchy of
           rules can therefore be created.
        
           A given Firewall Chain's rules are all created by the
           same entity, as indicated by the {{param|Creator}}
           parameter.";
        leaf Enable {
          type boolean;
          default "false";
          description
            "Enables or disables this {{object}} entry.";
        }
        leaf Name {
          type string {
            length "0..64";
          }
          description
            "Human-readable name associated with this {{object}}
             entry.";
        }
        leaf Creator {
          type enumeration {
            enum "Defaults";
            enum "PortMapping";
            enum "WANIPv6FirewallControl";
            enum "ACS";
            enum "UserInterface";
            enum "Other";
          }
          config false;
          default "ACS";
          description
            "Creator of this {{object}} entry and of its
             {{object|Rule}}s.  {{enum}}
          
             Note that this is the entity that originally created
             the {{object}} entry.  The value of this parameter
             does not change if the {{object}} entry or one of
             its rules is subsequently changed by another entity.";
        }

        list Rule {
          key "Alias";
          description
            "Firewall Rule table.  Each entry defines a Firewall
             packet selection rule.  The {{param|Target}}
             parameter defines the action to perform for traffic
             matching this rule: the packet can be dropped,
             accepted, rejected or passed to another
             {{object|#}}.
          
             This table MUST NOT contain dynamic Firewall rules
             associated with {{enum|Stateful|##.Type}} Firewall
             sessions.
          
             All entries are created by the creator of the parent
             {{object|#}}, as indicated by its
             {{param|#.Creator}} parameter.  {{object}} entries
             in a {{object|#}} with a {{param|#.Creator}} of
             {{enum|Defaults|#.Creator}}, {{enum|ACS|#.Creator}},
             {{enum|UserInterface|#.Creator}} or (maybe)
             {{enum|Other|#.Creator}} are referred to as
             ''Static'' {{object}}s.  Whether or not a {{object}}
             in a {{object|#}} with {{param|#.Creator}}
             {{enum|Other|#.Creator}} is regarded as ''Static''
             is a local matter to the CPE.  Some of this object's
             parameter descriptions refer to whether a {{object}}
             is ''Static'' when specifying whether or not the
             parameter value can be modified.
          
             For enabled table entries, if
             {{param|SourceInterface}} is not a valid reference
             and {{param|SourceAllInterfaces}} is {{false}}, or
             if {{param|DestInterface}} is not a valid reference
             and {{param|DestAllInterfaces}} is {{false}}, then
             the table entry is inoperable and the CPE MUST set
             {{param|Status}} to
             {{enum|Error_Misconfigured|Status}}.";
          leaf Enable {
            type boolean;
            default "false";
            description
              "Enables or disables this {{object}} entry.";
          }
          leaf Status {
            type enumeration {
              enum "Disabled";
              enum "Enabled";
              enum "Error_Misconfigured";
              enum "Error";
            }
            config false;
            default "Disabled";
            description
              "The status of this {{object}} entry.  {{enum}}
            
               The {{enum|Error_Misconfigured}} value indicates
               that a necessary configuration value is undefined
               or invalid.
            
               The {{enum|Error}} value MAY be used by the CPE to
               indicate a locally defined error condition.";
          }
          leaf Order {
            type uint32 {
              range "1..max";
            }
            description
              "Position of the {{object}} entry in the order of
               precedence.  A value of ''1'' indicates the first
               entry considered (highest precedence).  For each
               packet, the highest ordered entry that matches the
               rule criteria is applied.  All lower order entries
               are ignored.
            
               When this value is modified, if the value matches
               that of an existing entry, the {{param}} value for
               the existing entry and all lower {{param}} entries
               is incremented (lowered in precedence) to ensure
               uniqueness of this value.  A deletion causes
               {{param}} values to be compacted.  When a value is
               changed, incrementing occurs before compaction.
            
               The value of {{param}} on creation of a {{object}}
               table entry MUST be one greater than the largest
               current value (initially assigned the lowest
               precedence).";
          }
          leaf Description {
            type string {
              length "0..256";
            }
            description
              "Human-readable description associated with this
               {{object}} entry.";
          }
          leaf Target {
            type enumeration {
              enum "Drop";
              enum "Accept";
              enum "Reject";
              enum "Return";
              enum "TargetChain";
            }
            default "Drop";
            description
              "Action to perform for traffic matching this
               {{object}} entry.  {{enum}}
            
               This parameter can only be modified if the
               {{object}} is ''Static'' (as explained in the
               object description).";
          }
          leaf TargetChain {
            type string;
            default "";
            description
              "Specifies the chain to process when {{param|Target}}
               equals {{enum|TargetChain|Target}}.  If there are
               no matching rules in the referenced chain,
               processing continues with the next rule in this
               chain (if any).  In other words,
               {{enum|TargetChain|Target}} behaves like a
               subroutine call.
            
               {{empty}} indicates no {{param}} is specified.
            
               This parameter can only be modified if the
               {{object}} is ''Static'' (as explained in the
               object description).";
          }
          leaf Log {
            type boolean;
            default "false";
            description
              "Enable or disable logging, in a
               {{object|###.DeviceInfo.VendorLogFile}}, of
               packets matching this {{object}}.
            
               If the {{object}} is not ''Static'' (as explained
               in the object description), whether changes to
               this parameter persist across re-boot is a local
               matter to the CPE.";
          }
          leaf CreationDate {
            type yang:date-and-time;
            config false;
            description
              "Date and time when this {{object}} entry was created.";
          }
          leaf ExpiryDate {
            type yang:date-and-time;
            default "9999-12-31T23:59:59Z";
            description
              "The time at which this {{object}} entry will expire,
               or {{null}} if not known.  For an infinite
               lifetime, the parameter value MUST be
               9999-12-31T23:59:59Z.
            
               The only value that MUST be supported is
               9999-12-31T23:59:59Z (i.e.  support for rules that
               expire is OPTIONAL).
            
               When a rule expires, the CPE MUST automatically
               terminate that rule and MUST automatically delete
               the corresponding {{object}} table entry.
            
               This parameter can only be modified if the
               {{object}} is ''Static'' (as explained in the
               object description).";
          }
          leaf SourceInterface {
            type string {
              length "0..256";
            }
            default "";
            description
              "{{object}} criterion.  {{reference}}
            
               This specifies the ingress interface associated
               with the entry.  It MAY be a layer 1, 2 or 3
               interface, however, the types of interfaces for
               which Rules can be instantiated is a local matter
               to the CPE.
            
               This parameter can only be modified if the
               {{object}} is ''Static'' (as explained in the
               object description).";
          }
          leaf SourceInterfaceExclude {
            type boolean;
            default "false";
            description
              "If {{false}}, the rule matches only those packets
               that match the {{param|SourceInterface}} entry, if
               specified.
            
               If {{true}}, the rule matches all packets except
               those that match the {{param|SourceInterface}}
               entry, if specified.
            
               This parameter can only be modified if the
               {{object}} is ''Static'' (as explained in the
               object description).";
          }
          leaf SourceAllInterfaces {
            type boolean;
            default "false";
            description
              "{{object}} criterion.  This specifies that all
               ingress interfaces are associated with the entry.
               If {{true}}, the values of
               {{param|SourceInterface}} and
               {{param|SourceInterfaceExclude}} are ignored since
               all ingress interfaces are indicated.
            
               This parameter can only be modified if the
               {{object}} is ''Static'' (as explained in the
               object description).";
          }
          leaf DestInterface {
            type string {
              length "0..256";
            }
            default "";
            description
              "{{object}} criterion.  {{reference}}
            
               This specifies the egress interface associated
               with the entry.  It MAY be a layer 1, 2 or 3
               interface, however, the types of interfaces for
               which Rules can be instantiated is a local matter
               to the CPE.
            
               This parameter can only be modified if the
               {{object}} is ''Static'' (as explained in the
               object description).";
          }
          leaf DestInterfaceExclude {
            type boolean;
            default "false";
            description
              "If {{false}}, the rule matches only those packets
               that match the {{param|DestInterface}} entry, if
               specified.
            
               If {{true}}, the rule matches all packets except
               those that match the {{param|DestInterface}}
               entry, if specified.
            
               This parameter can only be modified if the
               {{object}} is ''Static'' (as explained in the
               object description).";
          }
          leaf DestAllInterfaces {
            type boolean;
            default "false";
            description
              "{{object}} criterion.  This specifies that all egress
               interfaces are associated with the entry.  If
               {{true}}, the values of {{param|DestInterface}}
               and {{param|DestInterfaceExclude}} are ignored
               since all ingress interfaces are indicated.
            
               This parameter can only be modified if the
               {{object}} is ''Static'' (as explained in the
               object description).";
          }
          leaf IPVersion {
            type int32 {
              range "-1..15";
            }
            default "-1";
            description
              "{{object}} criterion.
            
               IP Protocol Version (e.g.  4 for IPv4 and 6 for
               IPv6).  A value of -1 indicates this criterion is
               not used for matching.
            
               This parameter can only be modified if the
               {{object}} is ''Static'' (as explained in the
               object description).";
          }
          leaf DestIP {
            type types:IPAddress;
            default "";
            description
              "{{object}} criterion.
            
               Destination IP address.  {{empty}} indicates this
               criterion is not used for matching.
            
               Note that Firewall rules are applied after any
               {{object|###.NAT}} processing, so if NAT is
               enabled on the source interface this is always the
               translated address.
            
               This parameter can only be modified if the
               {{object}} is ''Static'' (as explained in the
               object description).";
          }
          leaf DestMask {
            type types:IPPrefix;
            default "";
            description
              "Destination IP address mask, represented as an IP
               routing prefix using CIDR notation [RFC4632].  The
               IP address part MUST be {{empty}} (and, if
               specified, MUST be ignored).";
          }
          leaf DestIPExclude {
            type boolean;
            default "false";
            description
              "If {{false}}, the rule matches only those packets
               that match the (masked) {{param|DestIP}} entry, if
               specified.
            
               If {{true}}, the rule matches all packets except
               those that match the (masked) {{param|DestIP}}
               entry, if specified.
            
               This parameter can only be modified if the
               {{object}} is ''Static'' (as explained in the
               object description).";
          }
          leaf SourceIP {
            type types:IPAddress;
            default "";
            description
              "{{object}} criterion.
            
               Source IP address.  {{empty}} indicates this
               criterion is not used for matching.
            
               This parameter can only be modified if the
               {{object}} is ''Static'' (as explained in the
               object description).";
          }
          leaf SourceMask {
            type types:IPPrefix;
            default "";
            description
              "Source IP address mask, represented as an IP routing
               prefix using CIDR notation [RFC4632].  The IP
               address part MUST be {{empty}} (and, if specified,
               MUST be ignored).";
          }
          leaf SourceIPExclude {
            type boolean;
            default "false";
            description
              "If {{false}}, the rule matches only those packets
               that match the (masked) {{param|SourceIP}} entry,
               if specified.
            
               If {{true}}, the rule matches all packets except
               those that match the (masked) {{param|SourceIP}}
               entry, if specified.
            
               This parameter can only be modified if the
               {{object}} is ''Static'' (as explained in the
               object description).";
          }
          leaf Protocol {
            type int32 {
              range "-1..255";
            }
            default "-1";
            description
              "{{object}} criterion.
            
               Protocol number.  A value of -1 indicates this
               criterion is not used for matching.
            
               This parameter can only be modified if the
               {{object}} is ''Static'' (as explained in the
               object description).";
          }
          leaf ProtocolExclude {
            type boolean;
            default "false";
            description
              "If {{false}}, the rule matches only those packets
               that match the {{param|Protocol}} entry, if
               specified.
            
               If {{true}}, the rule matches all packets except
               those that match the {{param|Protocol}} entry, if
               specified.
            
               This parameter can only be modified if the
               {{object}} is ''Static'' (as explained in the
               object description).";
          }
          leaf DestPort {
            type int32 {
              range "-1..65535";
            }
            default "-1";
            description
              "{{object}} criterion.
            
               Destination port number.  A value of -1 indicates
               this criterion is not used for matching.
            
               Note that Firewall rules are applied after any
               {{object|###.NAT}} processing, so if NAT is
               enabled on the source interface this is always the
               translated port number.
            
               This parameter can only be modified if the
               {{object}} is ''Static'' (as explained in the
               object description).";
          }
          leaf DestPortRangeMax {
            type int32 {
              range "-1..65535";
            }
            default "-1";
            description
              "{{object}} criterion.
            
               If specified, indicates the {{object}} criterion
               is to include the port range from
               {{param|DestPort}} through {{param}} (inclusive).
               If specified, {{param}} MUST be greater than or
               equal to {{param|DestPort}}.
            
               A value of -1 indicates that no port range is
               specified.
            
               Note that Firewall rules are applied after any
               {{object|###.NAT}} processing, so if NAT is
               enabled on the source interface this is always the
               translated port number.
            
               This parameter can only be modified if the
               {{object}} is ''Static'' (as explained in the
               object description).";
          }
          leaf DestPortExclude {
            type boolean;
            default "false";
            description
              "If {{false}}, the rule matches only those packets
               that match the {{param|DestPort}} entry (or port
               range), if specified.
            
               If {{true}}, the rule matches all packets except
               those that match the {{param|DestPort}} entry (or
               port range), if specified.
            
               This parameter can only be modified if the
               {{object}} is ''Static'' (as explained in the
               object description).";
          }
          leaf SourcePort {
            type int32 {
              range "-1..65535";
            }
            default "-1";
            description
              "{{object}} criterion.
            
               Source port number.  A value of -1 indicates this
               criterion is not used for matching.
            
               This parameter can only be modified if the
               {{object}} is ''Static'' (as explained in the
               object description).";
          }
          leaf SourcePortRangeMax {
            type int32 {
              range "-1..65535";
            }
            default "-1";
            description
              "{{object}} criterion.
            
               If specified, indicates the {{object}} criterion
               is to include the port range from
               {{param|SourcePort}} through {{param}}
               (inclusive).  If specified, {{param}} MUST be
               greater than or equal to {{param|SourcePort}}.
            
               A value of -1 indicates that no port range is
               specified.
            
               This parameter can only be modified if the
               {{object}} is ''Static'' (as explained in the
               object description).";
          }
          leaf SourcePortExclude {
            type boolean;
            default "false";
            description
              "If {{false}}, the rule matches only those packets
               that match the {{param|SourcePort}} entry (or port
               range), if specified.
            
               If {{true}}, the rule matches all packets except
               those that match the {{param|SourcePort}} entry
               (or port range), if specified.
            
               This parameter can only be modified if the
               {{object}} is ''Static'' (as explained in the
               object description).";
          }
          leaf DSCP {
            type int32 {
              range "-1..63";
            }
            default "-1";
            description
              "{{object}} criterion.
            
               DiffServ codepoint (defined in
               {{bibref|RFC2474}}).
            
               If set to a Class Selector Codepoint (defined in
               {{bibref|RFC2474}}), all DSCP values that match
               the first 3 bits will be considered a valid match.
            
               A value of -1 indicates this criterion is not used
               for matching.
            
               This parameter can only be modified if the
               {{object}} is ''Static'' (as explained in the
               object description).";
          }
          leaf DSCPExclude {
            type boolean;
            default "false";
            description
              "If {{false}}, the rule matches only those packets
               that match the {{param|DSCP}} entry, if specified.
            
               If {{true}}, the rule matchess all packets except
               those that match the {{param|DSCP}} entry, if
               specified.
            
               This parameter can only be modified if the
               {{object}} is ''Static'' (as explained in the
               object description).";
          }
        }
      }
    }

    container PeriodicStatistics {
      description
        "This object configures collection of periodic statistics
         for the device.
      
         Periodic statistics are measured over a sample interval
         (which can be aligned with absolute time) and are made
         available to the ACS as a comma-separated list of the
         most recent <n> samples.
      
         This object provides a single set of global settings
         that affect the entire device unless overridden locally.";
      leaf MinSampleInterval {
        type uint32;
        config false;
        description
          "Minimum sample interval in {{units}} that the CPE is able
           to support.
        
           A value of 0 indicates no specific minimum sample
           interval.";
      }
      leaf MaxReportSamples {
        type uint32;
        config false;
        description
          "Maximum number of samples of each statistic that the CPE
           is able to store and report.
        
           A value of 0 indicates no specific maximum number of
           samples.";
      }

      list SampleSet {
        key "Name";
        description
          "Periodic statistics sample set table.  Each sample set
           has its own sample interval etc.";
        leaf Enable {
          type boolean;
          default "false";
          description
            "Enables or disables collection of periodic statistics
             for this sample set.
          
             When collection of periodic statistics is enabled,
             any stored samples are discarded, and the first
             sample interval begins immediately.";
        }
        leaf Status {
          type enumeration {
            enum "Disabled";
            enum "Enabled";
            enum "Trigger";
          }
          config false;
          default "Disabled";
          description
            "Indicates availability of Sample statistics.  {{enum}}
          
             The {{enum|Trigger}} value is only used for
             triggering the ACS to fetch the collected data and
             can only be used when {{param|FetchSamples}} is in
             the range [1:{{param|ReportSamples}}].
          
             The transition from {{enum|Enabled}} to
             {{enum|Trigger}} to {{enum|Enabled}} MUST be
             instantaneous and so will result in only a single
             value change for notification purposes.";
        }
        leaf Name {
          type string {
            length "0..128";
          }
          default "";
          description
            "The name of this sample set, which uniquely
             distinguishes each sample set.";
        }
        leaf SampleInterval {
          type uint32 {
            range "1..max";
          }
          default "3600";
          description
            "The sample interval in {{units}}.  Each statistic is
             measured over this sample interval.
          
             The CPE MAY reject a request to set {{param}} to
             less than
             {{param|.PeriodicStatistics.MinSampleInterval}}.
          
             Sample intervals MUST begin every {{param}}
             {{units}}, with no delay between samples.
          
             If {{param}} is changed while collection of periodic
             statistics is enabled, any stored samples are
             discarded, and the first sample interval begins
             immediately.
          
             For example, if {{param|ReportSamples}} is 24 and
             {{param}} is 3600 (an hour), the CPE can store up to
             a day's worth of samples for each statistic.";
        }
        leaf ReportSamples {
          type uint32 {
            range "1..max";
          }
          default "24";
          description
            "The number of samples that the CPE will store and
             report for each statistic.
          
             The CPE MUST permit {{param}} to be set to at least
             {{param|.PeriodicStatistics.MaxReportSamples}}.
          
             If {{param}} is changed while collection of periodic
             statistics is enabled, the CPE will truncate or
             extend its statistics buffers as appropriate, but
             statistics collection MUST NOT otherwise be
             affected.
          
             For example, if {{param}} is 24 and
             {{param|SampleInterval}} is 3600 (an hour), the CPE
             can store up to a day's worth of samples for each
             statistic.";
        }
        leaf TimeReference {
          type yang:date-and-time;
          default "0001-01-01T00:00:00Z";
          description
            "An absolute time reference in UTC to determine when
             sample intervals will complete.  Each sample
             interval MUST complete at this reference time plus
             or minus an integer multiple of
             {{param|SampleInterval}}.
          
             {{param}} is used only to set the \"phase\" of the
             sample and fetch intervals.  The actual value of
             {{param}} can be arbitrarily far into the past or
             future.
          
             This time reference also determines when the
             {{param|Status}} {{enum|Enabled|Status}} to
             {{enum|Trigger|Status}} to {{enum|Enabled|Status}}
             transitions that are controlled by
             {{param|FetchSamples}} will occur.  If collection of
             periodic statistics is enabled and
             {{param|FetchSamples}} is in the range
             [1:{{param|ReportSamples}}] then each such
             {{param|Status}} transition MUST occur at this
             reference time plus or minus an integer multiple of
             {{param|FetchSamples}} * {{param|SampleInterval}}
             (the fetch interval).
          
             If {{param}} is changed while collection of periodic
             statistics is enabled, any stored samples are
             discarded, and the first sample interval begins
             immediately.
          
             The Unknown Time value defined in
             {{bibref|TR-106a2}} indicates that no particular
             time reference is specified.  That is, the CPE MAY
             locally choose the time reference, and is required
             only to adhere to the specified sample and fetch
             intervals.
          
             If absolute time is not available to the CPE, its
             sample and fetch interval behavior MUST be the same
             as if the {{param}} parameter was set to the Unknown
             Time value.
          
             For example, if {{param|SampleInterval}} is 3600 (an
             hour) and if {{param}} is set to UTC midnight on
             some day (in the past, present, or future) then
             sample intervals will complete on each UTC hour
             (00:00, 01:00, 02:00 etc).
          
             If, in addition, {{param|FetchSamples}} is 24, then
             the fetch interval is 86400 (a day) and
             {{param|Status}} {{enum|Enabled|Status}} to
             {{enum|Trigger|Status}} to {{enum|Enabled|Status}}
             transitions will occur every day at UTC midnight.
          
             Note that, if {{param}} is set to a time other than
             the Unknown Time, the first sample interval (which
             has to begin immediately) will almost certainly be
             shorter than {{param|SampleInterval}}).  This is why
             {{param}} is defined in terms of when sample
             intervals complete rather than start.";
        }
        leaf FetchSamples {
          type uint32;
          default "0";
          description
            "The number of sample intervals to be collected before
             transitioning {{param|Status}} from
             {{enum|Enabled|Status}} to {{enum|Trigger|Status}}
             to {{enum|Enabled|Status}}.
          
             If this SampleSet is enabled and {{param}} is in the
             range [1:{{param|ReportSamples}}] then
             {{param|Status}} MUST transition from
             {{enum|Enabled|Status}} to {{enum|Trigger|Status}}
             to {{enum|Enabled|Status}} on completion of every
             {{param}} sample intervals.  Otherwise, the
             transition MUST NOT occur.
          
             For example, if {{param|ReportSamples}} is 25 and
             {{param}} is 24, then the CPE will store 25 values
             for each monitored parameter and the above
             {{param|Status}} transition will occur as the CPE
             stores each 24th of 25 sample intervals, which means
             that the ACS could delay for up to two sample
             intervals before reading the stored values and would
             still not miss any samples (see also
             {{param|ForceSample}}).
          
             To disable this trigger mechanism and still collect
             sampled statistics, {{param}} can be set to either 0
             or a value greater than {{param|ReportSamples}}.";
        }
        leaf ForceSample {
          type boolean;
          default "false";
          description
            "When set to {{true}}, forces statistics for the current
             sample to be calculated and updated in the data
             model.  Setting it to {{false}} has no effect.
             {{hidden}}
          
             If this is the first time that {{param}} has been
             set to {{true}} during the current sample interval,
             this MUST cause a new value to be added to each of
             the periodic statistics comma-separated list
             parameters, and the {{param|ReportEndTime}} and all
             {{param|SampleSeconds}} parameters MUST be updated
             accordingly.
          
             If this is not the first time that {{param}} has
             been set to {{true}} during the current sample
             interval, then the new values that were added as
             described in the previous paragraph, and the
             {{param|ReportEndTime}} and all
             {{param|SampleSeconds}} parameters, MUST be updated
             accordingly.
          
             Note that {{param}} just provides a \"sneak
             preview\" of the current sample.  It does not create
             a new sample and it does not interfere with the
             sample interval schedule.
          
             At the end of each sample interval, if {{param}} was
             set to {{true}} during the sample interval then the
             new values that were added as described above, and
             the {{param|ReportEndTime}} and all
             {{param|SampleSeconds}} parameters, will be updated
             accordingly.  In other words, the partial sample
             data that was created when {{param}} was set to
             {{true}} will be updated one last time at the end of
             the sample interval.";
        }
        leaf ReportStartTime {
          type yang:date-and-time;
          config false;
          default "";
          description
            "The absolute time at which the sample interval for the
             first stored sample (for each statistic) started.";
        }
        leaf ReportEndTime {
          type yang:date-and-time;
          config false;
          default "";
          description
            "The absolute time at which the sample interval for the
             last stored sample (for each statistic) ended.
          
             If {{param|ForceSample}} has been used to force
             statistics for the current sample to be calculated
             and updated in the data model, then {{param}} MUST
             be updated to reflect the actual time over which
             stored data was collected.";
        }
        leaf SampleSeconds {
          type uint32;
          config false;
          default "";
          description
            "{{list}} Each entry indicates the number of {{units}}
             during which data was collected during the sample
             interval.
          
             Individual {{param}} values can be less than
             {{param|SampleInterval}}, for several reasons,
             including:
          
             : {{param|TimeReference}} has been set to a time
             other than the Unknown Time and the current sample
             interval started part of the way through a scheduled
             sample interval.
          
             : {{param|ForceSample}} has been used to force
             statistics for the current sample to be calculated
             and updated in the data model.";
        }

        list Parameter {
          key "Reference";
          description
            "Periodic statistics parameter table for this sample
             set.  This table contains entries for parameters
             whose values are to be sampled.
          
             Note that the comma-separated lists in this object
             (SampleSeconds, SuspectData and Values) only ever
             change (a) when first enabled, (b) when ForceSample
             is set to true (a \"sneak preview\" of the current
             sample), or (c) at the end of the sample interval.";
          leaf Enable {
            type boolean;
            default "false";
            description
              "Enables or disables this object instance.";
          }
          leaf Reference {
            type string {
              length "0..256";
            }
            default "";
            description
              "{{reference}} This is the parameter being monitored
               by the Periodic Statistics mechanism.";
          }
          leaf SampleMode {
            type enumeration {
              enum "Current";
              enum "Change";
            }
            default "Current";
            description
              "Controls how this parameter's value is sampled.
               {{enum}}
            
               Parameters of non-numeric types can only support
               {{enum|Current}}.  The value of the {{param}} MUST
               be ignored for such parameters.";
          }
          leaf CalculationMode {
            type enumeration {
              enum "Latest";
              enum "Minimum";
              enum "Maximum";
              enum "Average";
            }
            default "Latest";
            description
              "Controls how this parameter's statistic is calculated
               from the sampled value(s).  {{enum}}
            
               Parameters of non-numeric types can only support
               {{enum|Latest}}.  The value of the {{param}} MUST
               be ignored for such parameters.
            
               {{param|SampleMode}} MUST be applied before
               {{param}}, i.e.  the inputs to the calculation
               will have already accounted for
               {{param|SampleMode}}.";
          }
          leaf LowThreshold {
            type int32;
            default "0";
            description
              "The low threshold value that controls the calculation
               of {{param|Failures}}.
            
               A value equal to {{param|HighThreshold}} disables
               the threshold/failure mechanism.
            
               Parameters of non-numeric types cannot support the
               threshold/failure mechanism.  The value of this
               parameter MUST be ignored for such parameters.";
          }
          leaf HighThreshold {
            type int32;
            default "0";
            description
              "The high threshold value that controls the
               calculation of {{param|Failures}}.
            
               A value equal to {{param|LowThreshold}} disables
               the threshold/failure mechanism.
            
               Parameters of non-numeric types cannot support the
               threshold/failure mechanism.  The value of this
               parameter MUST be ignored for such parameters.";
          }
          leaf SampleSeconds {
            type uint32;
            config false;
            default "";
            description
              "{{list}} Each entry indicates the number of {{units}}
               during which data was collected for this parameter
               during the sample interval.
            
               Individual {{param}} values can be less than
               {{param|.PeriodicStatistics.SampleSet.{i}.SampleInterval}},
               for several reasons, including:
            
               : Any of the reasons for which
               {{param|.PeriodicStatistics.SampleSet.{i}.SampleSeconds}}
               values might be less than
               {{param|.PeriodicStatistics.SampleSet.{i}.SampleInterval}}.
            
               : The parameter doesn't exist, or was created or
               deleted during a sample interval.";
          }
          leaf SuspectData {
            type uint32 {
              range "min..1";
            }
            config false;
            default "";
            description
              "{{list}} Each entry is 0 if the sampled value is
               believed to be valid, or 1 if an event that might
               affect the validity of the sampled value occurred
               during the sample interval.
            
               For example, if the parameter value were to be
               reset during the sample interval then it would be
               appropriate to set {{param}} to 1.";
          }
          leaf Values {
            type string;
            config false;
            default "";
            description
              "{{list}} Each entry indicates the value of the
               referenced parameter, as determined by
               {{param|SampleMode}}, during the sample interval.
            
               The statistics values in this comma-separated
               lists MUST be in time order, with the oldest one
               first and the most recent one last.
            
               If the {{param|SampleMode}} parameter is not
               present, or is inappropriate for the referenced
               parameter, the statistics values MUST be collected
               in Current mode.";
          }
          leaf Failures {
            type uint32;
            config false;
            default "0";
            description
              "Counts the number of times (since this object
               instance was last enabled) that a newly-calculated
               sample value (accounting for {{param|SampleMode}})
               transitioned from the \"in range\" state to the
               \"out of range\" state, or between the \"out of
               range (low)\" and \"out of range (high)\" states.
               The states are defined as follows:
            
               * \"in range\" : current value is greater than
               {{param|LowThreshold}} and less than
               {{param|HighThreshold}}.
            
               * \"out of range\" : current value is less than or
               equal to {{param|LowThreshold}}, or greater than
               or equal to {{param|HighThreshold}}.
            
               * \"out of range (low)\" : current value is less
               than or equal to {{param|LowThreshold}}.
            
               * \"out of range (high)\" : current value is
               greater than or equal to {{param|HighThreshold}}.
            
               Note that, if {{param|LowThreshold}} and
               {{param|HighThreshold}} are both the same, the
               threshold/failure mechanism is disabled, so the
               value of this parameter will not increment.
            
               This parameter can be incremented at any time
               during a sample interval, and might be incremented
               more than once during a single sample interval.
               For this reason, the CPE SHOULD place a locally
               specified limit on the frequency at which it will
               notify the ACS of such changes, as described in
               {{bibref|TR-069a2|Section 3.2.1}}.
            
               Parameters of non-numeric types cannot support the
               threshold/failure mechanism.  The value of this
               parameter MUST be ignored for such parameters.";
          }
        }
      }
    }

    container SoftwareModules {
      description
        "Top level object for dynamically managed software
         applications.";

      list ExecEnv {
        key "Alias";
        description
          "The Execution Environments that are available on the
           device, along with their properties and configurable
           settings.";
        leaf Enable {
          type boolean;
          description
            "Indicates whether or not this {{object}} is enabled.
          
             Disabling an enabled Execution Environment stops it,
             while enabling a disabled Execution Environment
             starts it.
          
             When an Execution Environment is disabled,
             Deployment Units installed to that Execution
             Environment will be unaffected, but any Execution
             Units currently running on that Execution
             Environment will automatically transition to
             {{enum|Idle|#.ExecutionUnit.{i}.Status}}.
          
             If a ChangeDUState is attempted on a
             {{object|#.DeploymentUnit}} that is to be applied
             against a disabled {{object}}, that ChangeDUState
             operation fails and the associated
             DUStateChangeComplete RPC will contain a FaultStruct
             for that operation.
          
             If a SetParameterValues is attempted against the
             {{param|#.ExecutionUnit.{i}.RequestedState}} for an
             {{object|#.ExecutionUnit}} that is associated with a
             disabled {{object}} a CWMP Fault will be issued in
             response.
          
             Disabling an Execution Environment could place the
             device in a non-manageable state.  For example, if
             the operating system itself was modeled as an
             {{object}} and the ACS disabled it, the CWMP
             management agent might be terminated leaving the
             device unmanageable.";
        }
        leaf Status {
          type enumeration {
            enum "Up";
            enum "Error";
            enum "Disabled";
          }
          config false;
          description
            "Indicates the status of this {{object}}.";
        }
        leaf Reset {
          type boolean; /* command */
          description
            "Setting this parameter to {{true}} causes this
             {{object}} to revert back to the state it was in
             when the device last issued a \"0 BOOTSTRAP\" Inform
             event.  The following requirements dictate what MUST
             happen for the reset to be complete:
          
             # All Deployment Units that were installed after the
             last \"0 BOOTSTRAP\" Inform event MUST be removed
          
             # All persistent storage, configuration files, and
             log files that were associated with the removed
             Deployment Units MUST be removed
          
             # Any Deployment Unit that is still installed
             against the Execution Environment MUST be restored
             to the version present when the last \"0 BOOTSTRAP\"
             Inform event was issued
          
             # Any Deployment Unit that was present when the last
             \"0 BOOTSTRAP\" Inform event was issued, but was
             subsequently uninstalled and is now not present,
             MUST be installed with the version that was present
             when the last \"0 BOOTSTRAP\" Inform event was
             issued
          
             # The Execution Environment MUST be restored to the
             version and configuration present when the last \"0
             BOOTSTRAP\" Inform event was issued
          
             # The Execution Environment MUST be restarted after
             all other restoration requirements have been met";
        }
        leaf Name {
          type string {
            length "0..32";
          }
          config false;
          description
            "A Name provided by the CPE that adequately
             distinguishes this {{object}} from all other
             {{object}} instances.";
        }
        leaf Type {
          type string {
            length "0..64";
          }
          config false;
          description
            "Indicates the complete type and specification version
             of this {{object}}.";
        }
        leaf InitialRunLevel {
          type uint32 {
            range "min..65535";
          }
          description
            "The run level that this {{object}} will be in upon
             startup (whether that is caused by a CPE Boot or the
             Execution Environment starting).
          
             Run levels dictate which Execution Units will be
             started.  Execution Units will be started if
             {{param|CurrentRunLevel}} is greater than or equal
             to {{param|#.ExecutionUnit.{i}.RunLevel}} and
             {{param|#.ExecutionUnit.{i}.AutoStart}} is {{true}}.
          
             If the value of {{param|CurrentRunLevel}} is -1,
             then the value of this parameter is irrelevant when
             read and setting its value has no impact on the Run
             Level of this {{object}}.";
        }
        leaf RequestedRunLevel {
          type int32 { /* command */
            range "-1..65535";
          }
          description
            "Provides a mechanism to remotely manipulate the run
             level of this {{object}}, meaning that altering this
             parameter's value will change the value of the
             {{param|CurrentRunLevel}}.
          
             Run levels dictate which Execution Units will be
             started.  Execution Units will be started if
             {{param|CurrentRunLevel}} is greater than or equal
             to {{param|#.ExecutionUnit.{i}.RunLevel}} and
             {{param|#.ExecutionUnit.{i}.AutoStart}} is {{true}}.
          
             Setting this value when {{param|CurrentRunLevel}} is
             -1 has no impact to the Run Level of this
             {{object}}.";
        }
        leaf CurrentRunLevel {
          type int32 {
            range "-1..65535";
          }
          config false;
          description
            "The run level that this {{object}} is currently
             operating in.  This value is altered by changing the
             {{param|RequestedRunLevel}} parameter.
          
             Upon startup (whether that is caused by a CPE Boot
             or the Execution Environment starting) {{param}}
             will be equal to {{param|InitialRunLevel}}, unless
             Run Levels are not supported by this {{object}} in
             which case {{param}} will be -1.
          
             Run levels dictate which Execution Units will be
             started.  Execution Units will be started if
             {{param}} is greater than or equal to
             {{param|#.ExecutionUnit.{i}.RunLevel}} and
             {{param|#.ExecutionUnit.{i}.AutoStart}} is {{true}}.
          
             If {{param}} is -1 then Run Levels are not supported
             by this {{object}} and setting
             {{param|InitialRunLevel}} or
             {{param|RequestedRunLevel}} will not impact the Run
             Level of this {{object}}.";
        }
        leaf InitialExecutionUnitRunLevel {
          type int32 {
            range "-1..65535";
          }
          description
            "Indicates the initial value on creation for
             {{param|#.ExecutionUnit.{i}.RunLevel}} for all
             Execution Unit instances associated with this
             {{object}}.
          
             If the value of {{param|CurrentRunLevel}} is -1,
             then the value of this parameter is irrelevant when
             read and setting its value has no impact on the Run
             Level of any Execution Unit.";
        }
        leaf Vendor {
          type string {
            length "0..128";
          }
          config false;
          description
            "The vendor that produced this {{object}}.";
        }
        leaf Version {
          type string {
            length "0..32";
          }
          config false;
          description
            "The Version of this {{object}} as specified by the
             Vendor that implemented this {{object}}, not the
             version of the specification.";
        }
        leaf ParentExecEnv {
          type string;
          config false;
          description
            "Represents the parent {{object}} of this {{object}}.
          
             If this value is {{empty}} then this is the Primary
             Execution Environment.";
        }
        leaf AllocatedDiskSpace {
          type int32 {
            range "-1..max";
          }
          config false;
          description
            "The amount of disk space measured in {{units}}
             allocated to this {{object}}.  A value of -1 MUST be
             used for {{object}} instances where this parameter
             is not applicable.";
        }
        leaf AvailableDiskSpace {
          type int32 {
            range "-1..max";
          }
          config false;
          description
            "The amount of disk space measured in {{units}}
             currently available to this {{object}}.  This value
             changes as the {{object|#.ExecutionUnit}} instances
             associated with this {{object}} consumes disk space.
             A value of -1 MUST be used for {{object}} instances
             where this parameter is not applicable.";
        }
        leaf AllocatedMemory {
          type int32 {
            range "-1..max";
          }
          config false;
          description
            "The amount of physical RAM measured in {{units}}
             allocated to this {{object}}.  A value of -1 MUST be
             used for {{object}} instances where this parameter
             is not applicable.";
        }
        leaf AvailableMemory {
          type int32 {
            range "-1..max";
          }
          config false;
          description
            "The amount of physical RAM measured in {{units}}
             currently available to this {{object}}.  This value
             changes as the {{object|#.ExecutionUnit}} instances
             associated with this {{object}} are started/stopped
             and consume the physical RAM.  A value of -1 MUST be
             used for {{object}} instances where this parameter
             is not applicable.";
        }
        leaf ActiveExecutionUnits {
          type string;
          config false;
          description
            "Represents the {{object|#.ExecutionUnit}} instances
             currently running on this {{object}}.  This
             parameter only contains {{object|#.ExecutionUnit}}
             instances that currently have a
             {{param|#.ExecutionUnit.{i}.Status}} of
             {{enum|Active|#.ExecutionUnit.{i}.Status}}.";
        }
        leaf ProcessorRefList {
          type string;
          config false;
          description
            "Represents the processors that this {{object}} has
             available to it.";
        }
      }

      list DeploymentUnit {
        key "UUID Version ExecutionEnvRef";
        config false;
        description
          "This table serves as the Deployment Unit inventory and
           contains status information about each Deployment
           Unit.
        
           A new instance of this table gets created during the
           installation of a Software Module.";
        leaf UUID {
          type string {
            length "0..36";
          }
          description
            "A Universally Unique Identifier either provided by the
             ACS, or generated by the CPE, at the time of
             Deployment Unit Installation.  The format of this
             value is defined by {{bibref|RFC4122}} Version 3
             (Name-Based) and {{bibref|TR-069a3|Annex H}}.
          
             This value MUST NOT be altered when the {{object}}
             is updated.";
        }
        leaf DUID {
          type string {
            length "0..64";
          }
          description
            "Deployment Unit Identifier chosen by the targeted
             {{object|#.ExecEnv}}.  The format of this value is
             Execution Environment specific.";
        }
        leaf Name {
          type string {
            length "0..64";
          }
          description
            "Indicates the Name of this {{object}}, which is chosen
             by the author of the Deployment Unit.
          
             The value of this parameter is used in the
             generation of the {{param|UUID}} based on the rules
             defined in {{bibref|TR-069a3|Annex H}}.";
        }
        leaf Status {
          type enumeration {
            enum "Installing";
            enum "Installed";
            enum "Updating";
            enum "Uninstalling";
            enum "Uninstalled";
          }
          description
            "Indicates the status of this {{object}}.";
        }
        leaf Resolved {
          type boolean;
          description
            "Indicates whether or not this {{object}} has resolved
             all of its dependencies.";
        }
        leaf URL {
          type string {
            length "0..1024";
          }
          description
            "Contains the URL used by the most recent ChangeDUState
             RPC to either Install or Update this {{object}}.";
        }
        leaf Description {
          type string {
            length "0..256";
          }
          description
            "Textual description of this {{object}}.  The format of
             this value is Execution Environment specific.";
        }
        leaf Vendor {
          type string {
            length "0..128";
          }
          description
            "The author of this {{object}} formatted as a domain
             name.
          
             The value of this parameter is used in the
             generation of the {{param|UUID}} based on the rules
             defined in {{bibref|TR-069a3|Annex H}}.";
        }
        leaf Version {
          type string {
            length "0..32";
          }
          description
            "Version of this {{object}}.  The format of this value
             is Execution Environment specific.";
        }
        leaf VendorLogList {
          type string;
          description
            "Represents the vendor log files that have come into
             existence because of this {{object}}.  This does not
             include any vendor log files that have come into
             existence because of {{object|#.ExecutionUnit}}
             instances that are contained within this {{object}}.
          
             When this {{object}} is uninstalled the vendor log
             files referenced here SHOULD be removed from the
             CPE.
          
             Not all {{object}} instances will actually have a
             corresponding vendor log file, in which case the
             value of this parameter will be {{empty}}.";
        }
        leaf VendorConfigList {
          type string;
          description
            "Represents the vendor config files that have come into
             existence because of this {{object}}.  This does not
             include any vendor config files that have come into
             existence because of {{object|#.ExecutionUnit}}
             instances that are contained within this {{object}}.
          
             When this {{object}} is uninstalled the vendor
             config files referenced here SHOULD be removed from
             the CPE.
          
             Not all {{object}} instances will actually have a
             corresponding vendor config file, in which case the
             value of this parameter will be {{empty}}.";
        }
        leaf ExecutionUnitList {
          type string;
          description
            "Represents the {{object|#.ExecutionUnit}} instances
             that are associated with this {{object}} instance.";
        }
        leaf ExecutionEnvRef {
          type string;
          description
            "Represents the {{object|#.ExecEnv}} instance where this
             {{object}} instance is installed.";
        }
      }

      list ExecutionUnit {
        key "EUID";
        description
          "This table serves as the Execution Unit inventory and
           contains both status information about each Execution
           Unit as well as configurable parameters for each
           Execution Unit.
        
           Each {{object|#.DeploymentUnit}} that is installed can
           have zero or more Execution Units.
        
           Once a Deployment Unit is installed it populates this
           table with its contained Execution Units.
        
           When the Deployment Unit (that caused this {{object}}
           to come into existence) is updated, this instance MAY
           be removed and new instances MAY come into existence.
           While the Deployment Unit (that caused this {{object}}
           to come into existence) is being updated, all
           {{object}} instances associated with the Deployment
           Unit will be stopped until the update is complete at
           which time they will be restored to the state that
           they were in before the update started.
        
           When the Deployment Unit (that caused this {{object}}
           to come into existence) is uninstalled, this instance
           is removed.
        
           Each {{object}} MAY also contain a set of vendor
           specific parameters displaying status and maintaining
           configuration that reside under the
           {{object|Extensions}} object.";
        leaf EUID {
          type string {
            length "0..64";
          }
          config false;
          description
            "Execution Unit Identifier chosen by the
             {{object|#.ExecEnv}} during installation of the
             associated {{object|#.DeploymentUnit}}.
          
             The format of this value is Execution Environment
             specific, but it MUST be unique across
             {{object|#.ExecEnv}} instances.  Thus, it is
             recommended that this be a combination of the
             {{param|#.ExecEnv.{i}.Name}} and an Execution
             Environment local unique value.";
        }
        leaf Name {
          type string {
            length "0..32";
          }
          config false;
          description
            "The name of this {{object}} as it pertains to its
             associated {{object|#.DeploymentUnit}}, which SHOULD
             be unique across all {{object}} instances contained
             within its associated {{object|#.DeploymentUnit}}.";
        }
        leaf ExecEnvLabel {
          type string {
            length "0..64";
          }
          config false;
          description
            "The name of this {{object}} as provided by the
             {{object|#.ExecEnv}}, which SHOULD be unique across
             all {{object}} instances contained within a specific
             {{object|#.ExecEnv}}.";
        }
        leaf Status {
          type enumeration {
            enum "Idle";
            enum "Starting";
            enum "Active";
            enum "Stopping";
          }
          config false;
          description
            "Indicates the status of this {{object}}.";
        }
        leaf RequestedState {
          type enumeration { /* command */
            enum "Idle";
            enum "Active";
          }
          description
            "Indicates the state transition that the ACS is
             requesting for this {{object}}.  {{enum}}
          
             If this {{object}} is associated with an Execution
             Environment that is disabled and an attempt is made
             to alter this value, then a CWMP Fault MUST be
             generated.";
        }
        leaf ExecutionFaultCode {
          type enumeration {
            enum "NoFault";
            enum "FailureOnStart";
            enum "FailureOnAutoStart";
            enum "FailureOnStop";
            enum "FailureWhileActive";
            enum "DependencyFailure";
            enum "UnStartable";
          }
          config false;
          description
            "If while running or transitioning between states this
             {{object}} identifies a fault this parameter
             embodies the problem.  The value of {{enum|NoFault}}
             MUST be used when everything is working as intended.
             {{enum}}
          
             For fault codes not included in this list, the
             vendor MAY include vendor-specific values, which
             MUST use the format defined in
             {{bibref|TR-106a4|Section 3.3}}.";
        }
        leaf ExecutionFaultMessage {
          type string {
            length "0..256";
          }
          config false;
          description
            "If while running or transitioning between states this
             {{object}} identifies a fault this parameter
             provides a more detailed explanation of the problem.
          
             If {{param|ExecutionFaultCode}} has the value of
             {{enum|NoFault|ExecutionFaultCode}} then the value
             of this parameter MUST {{empty}} and ignored by the
             ACS.";
        }
        leaf AutoStart {
          type boolean;
          description
            "If {{true}} and the {{param|RunLevel}} verification is
             also met, then this {{object}} will be automatically
             started by the device after its {{object|#.ExecEnv}}
             is either rebooted or restarted.
          
             If {{false}} this {{object}} will not be started
             after its {{object|#.ExecEnv}} is either rebooted or
             restarted until it is explicitly commanded to do so
             by either the ACS or another Execution Unit.";
        }
        leaf RunLevel {
          type uint32 {
            range "min..65535";
          }
          description
            "Determines when this {{object}} will be started.
          
             If {{param|AutoStart}} is {{true}} and
             {{param|#.ExecEnv.{i}.CurrentRunLevel}} is greater
             than or equal to {{param}}, then this {{object}}
             will be started.
          
             If the value of
             {{param|#.ExecEnv.{i}.CurrentRunLevel}} is -1, then
             the associated {{object|#.ExecEnv.}} doesn't support
             Run Levels, thus the value of this parameter is
             irrelevant when read and setting its value has no
             impact to the Run Level of this {{object}}.";
        }
        leaf Vendor {
          type string {
            length "0..128";
          }
          config false;
          description
            "Vendor of this {{object}}.";
        }
        leaf Version {
          type string {
            length "0..32";
          }
          config false;
          description
            "Version of the {{object}}.  The format of this value is
             Execution Environment specific.";
        }
        leaf Description {
          type string {
            length "0..256";
          }
          config false;
          description
            "Textual description of this {{object}}.  The format of
             this value is Execution Environment specific.";
        }
        leaf DiskSpaceInUse {
          type int32 {
            range "-1..max";
          }
          config false;
          description
            "The amount of disk space measured in {{units}}
             currently being used by this {{object}}.  A value of
             -1 MUST be used for {{object}} instances where this
             parameter is not applicable.";
        }
        leaf MemoryInUse {
          type int32 {
            range "-1..max";
          }
          config false;
          description
            "The amount of physical RAM measured in {{units}}
             currently being used by this {{object}}.  A value of
             -1 MUST be used for {{object}} instances where this
             parameter is not applicable.";
        }
        leaf References {
          type string;
          config false;
          description
            "Represents the instances of multi-instanced objects
             that are directly controlled by, and have come into
             existence because of, this {{object}}.  See
             {{bibref|TR-157a3|Appendix II.3.2}} for more
             description and some examples.
          
             NOTE: All other objects and parameters (i.e.  not
             multi-instanced objects) that this {{object}} has
             caused to come into existence can be discovered via
             the {{object|.DeviceInfo.SupportedDataModel.{i}.}}
             table.";
        }
        leaf AssociatedProcessList {
          type string;
          config false;
          description
            "Represents the system processes that are active in the
             system because of this {{object}}.
          
             If {{param|Status}} is not {{enum|Active|Status}} it
             is expected that this list will be {{empty}}.  Some
             {{object}} instances MIGHT NOT have any system
             processes irrespective of the value of
             {{param|Status}}.";
        }
        leaf VendorLogList {
          type string;
          config false;
          description
            "Represents the vendor log files that have come into
             existence because of this {{object}}.
          
             When the {{object|#.DeploymentUnit}} (that caused
             this {{object}} to come into existence) is
             uninstalled the vendor log files referenced here
             SHOULD be removed from the CPE.
          
             Not all {{object}} instances will actually have a
             corresponding vendor log file, in which case the
             value of this parameter will be {{empty}}.";
        }
        leaf VendorConfigList {
          type string;
          config false;
          description
            "Represents the vendor config files that have come into
             existence because of this {{object}}.
          
             When the {{object|#.DeploymentUnit}} (that caused
             this {{object}} to come into existence) is
             uninstalled the vendor config files referenced here
             SHOULD be removed from the CPE.
          
             Not all {{object}} instances will actually have a
             corresponding vendor config file, in which case the
             value of this parameter will be {{empty}}.";
        }
        leaf SupportedDataModelList {
          type string;
          config false;
          description
            "Represents the CWMP-DT schema instances that have been
             introduced to this device because of the existence
             of this {{object}}.";
        }
        leaf ExecutionEnvRef {
          type string;
          config false;
          description
            "Represents the {{object|#.ExecEnv}} that this
             {{object}} is associated with.";
        }

        container Extensions {
          config false;
          description
            "This object proposes a general location for vendor
             extensions specific to this Execution Unit, which
             allows multiple Execution Units to expose parameters
             without the concern of conflicting parameter names.
             These vendor extensions are related to displaying
             status and maintaining configuration for this
             Execution Unit.
          
             It is also possible for the Execution Unit to expose
             status and configuration parameters within Service
             objects or as embedded objects and parameters
             directly within the root data model, in which case
             the combination of {{param|#.References}} and
             {{param|#.SupportedDataModelList}} will be used to
             determine their locations.
          
             See {{bibref|TR-157a3|Appendix II.3.2}} for more
             description and some examples.";
        }
      }
    }

    container FaultMgmt {
      description
        "This object contains parameters relating to Fault/Alarm
         Management.";
      leaf MaxCurrentAlarmEntries {
        type uint32;
        config false;
        description
          "The maximum number of entries allowed in the
           {{object|.FaultMgmt.CurrentAlarm.{i}.}} table.";
      }

      list SupportedAlarm {
        key "EventType ProbableCause SpecificProblem PerceivedSeverity";
        description
          "Supported Alarm Entries which can be raised by the
           device.
        
           The instance numbers for this table SHOULD be
           maintained across firmware upgrades of the device.";
        leaf EventType {
          type string {
            length "0..64";
          }
          config false;
          description
            "Indicates the type of event.";
        }
        leaf ProbableCause {
          type string {
            length "0..64";
          }
          config false;
          description
            "Qualifies the alarm and provides further information
             than {{param|EventType}}.";
        }
        leaf SpecificProblem {
          type string {
            length "0..128";
          }
          config false;
          description
            "Provides further qualification on the alarm beyond
             {{param|EventType}} and {{param|ProbableCause}}.
          
             This is vendor defined and will be {{empty}} if the
             device doesn't support unique indexing of the table
             using {{param}}.
          
             The string can be set to \"*\" to indicate the
             default case if only a subset of {{param}} are to be
             contained within the table.";
        }
        leaf PerceivedSeverity {
          type enumeration {
            enum "";
            enum "*";
            enum "Cleared";
            enum "Critical";
            enum "Major";
            enum "Minor";
            enum "Warning";
            enum "Indeterminate";
          }
          config false;
          description
            "Indicates the relative level of urgency for operator
             attention, see {{bibref|ITU-X.733}}.  {{enum}}
          
             This will be {{empty}} if the device doesn't support
             unique indexing of the table using {{param}}.
          
             The string can be set to \"*\" to indicate the
             default case if only a subset of {{param}} are to be
             contained within the table.";
        }
        leaf ReportingMechanism {
          type enumeration {
            enum "0 Expedited";
            enum "1 Queued";
            enum "2 Logged";
            enum "3 Disabled";
          }
          description
            "Indicates the reporting mechanism setting of the alarm.
             {{enum}}";
        }
      }

      list CurrentAlarm {
        key "AlarmIdentifier";
        config false;
        description
          "Contains all currently active alarms (whose
           {{param|.FaultMgmt.SupportedAlarm.{i}.PerceivedSeverity}}
           is not
           {{enum|Cleared|.FaultMgmt.SupportedAlarm.{i}.PerceivedSeverity}}).
        
           Newly raised alarms result in a new entry in this
           table being added, any changes to the alarm as a
           result of an update event are updated in the existing
           table entry, and a clear event raised against an alarm
           results in the alarm being removed from this table.
        
           If maximum entries as indicated by
           {{param|.FaultMgmt.MaxCurrentAlarmEntries}} is
           reached, the next event overrides the object with the
           oldest {{param|AlarmChangedTime}}.
        
           When a new alarm replaces an existing alarm, then all
           parameter values for that instance are considered as
           changed for the purposes of value change notifications
           to the ACS (even if their new values are identical to
           those of the prior alarm).";
        leaf AlarmIdentifier {
          type string {
            length "0..64";
          }
          description
            "Identifies one Alarm Entry in the Alarm List.  This
             value MUST be uniquely allocated by the device to
             the alarm instance during the lifetime of the
             individual alarm.";
        }
        leaf AlarmRaisedTime {
          type yang:date-and-time;
          description
            "Indicates the date and time when the alarm was first
             raised by the device.";
        }
        leaf AlarmChangedTime {
          type yang:date-and-time;
          description
            "Indicates the date and time when the alarm was last
             changed by the device.";
        }
        leaf ManagedObjectInstance {
          type string {
            length "0..512";
          }
          description
            "Specifies the instance of the Informational Object
             Class in which the alarm occurred by carrying the
             Distinguished Name (DN) of this object instance.
             The format of the DN is specific to the application
             that is using this {{object}}.";
        }
        leaf EventType {
          type string {
            length "0..64";
          }
          description
            "Indicates the type of event.";
        }
        leaf ProbableCause {
          type string {
            length "0..64";
          }
          description
            "Qualifies the alarm and provides further information
             than {{param|EventType}}.";
        }
        leaf SpecificProblem {
          type string {
            length "0..128";
          }
          description
            "Provides further qualification on the alarm beyond
             {{param|EventType}} and {{param|ProbableCause}}.
          
             This is vendor defined and will be {{empty}} if the
             device doesn't support inclusion of this
             information.";
        }
        leaf PerceivedSeverity {
          type enumeration {
            enum "Critical";
            enum "Major";
            enum "Minor";
            enum "Warning";
            enum "Indeterminate";
          }
          description
            "Indicates the relative level of urgency for operator
             attention, see {{bibref|ITU-X.733}}.  {{enum}}";
        }
        leaf AdditionalText {
          type string {
            length "0..256";
          }
          description
            "This provides a textual string which is vendor defined.
          
             This will be {{empty}} if the device doesn't support
             inclusion of this information.";
        }
        leaf AdditionalInformation {
          type string {
            length "0..256";
          }
          description
            "This contains additional information about the alarm
             and is vendor defined.";
        }
      }

      list HistoryEvent {
        key "EventTime AlarmIdentifier";
        config false;
        description
          "Alarm events added or updated in
           {{object|.FaultMgmt.CurrentAlarm.{i}.}} are
           simultaneously entered into the this table.  This
           table also contains alarm clearing events.
        
           Active alarms at the time of a power failure or reboot
           might not get an alarm clearing event.
        
           This object has a fixed number of entries with
           instance numbers from 1 to
           {{param|.FaultMgmt.HistoryEventNumberOfEntries}}.
        
           If maximum instance number
           {{param|.FaultMgmt.HistoryEventNumberOfEntries}} is
           reached, the next event overrides the object with
           instance number 1.  Subsequent entries override
           objects at sequentially increasing instance numbers.
           This logic provides for automatic \"rolling\" of
           records.";
        leaf EventTime {
          type yang:date-and-time;
          description
            "Indicates the date and time when the alarm event
             occurs.";
        }
        leaf AlarmIdentifier {
          type string {
            length "0..64";
          }
          description
            "Identifies one Alarm Entry in the Alarm List.  This
             value MUST be uniquely allocated by the device to
             the alarm instance during the lifetime of the
             individual alarm.";
        }
        leaf NotificationType {
          type enumeration {
            enum "NewAlarm";
            enum "ChangedAlarm";
            enum "ClearedAlarm";
          }
          description
            "Indicates the reason for the specific alarm
             notification event.  {{enum}}";
        }
        leaf ManagedObjectInstance {
          type string {
            length "0..512";
          }
          description
            "Specifies the instance of the Informational Object
             Class in which the alarm occurred by carrying the
             Distinguished Name (DN) of this object instance.
             The format of the DN is specific to the application
             that is using this {{object}}.";
        }
        leaf EventType {
          type string {
            length "0..64";
          }
          description
            "Indicates the type of event.";
        }
        leaf ProbableCause {
          type string {
            length "0..64";
          }
          description
            "Qualifies the alarm and provides further information
             than {{param|EventType}}.";
        }
        leaf SpecificProblem {
          type string {
            length "0..128";
          }
          description
            "Provides further qualification on the alarm beyond
             {{param|EventType}} and {{param|ProbableCause}}.
          
             This is vendor defined and will be {{empty}} if the
             device doesn't support inclusion of this
             information.";
        }
        leaf PerceivedSeverity {
          type enumeration {
            enum "Cleared";
            enum "Critical";
            enum "Major";
            enum "Minor";
            enum "Warning";
            enum "Indeterminate";
          }
          description
            "Indicates the relative level of urgency for operator
             attention, see {{bibref|ITU-X.733}}.  {{enum}}";
        }
        leaf AdditionalText {
          type string {
            length "0..256";
          }
          description
            "This provides a textual string which is vendor defined.
          
             This will be {{empty}} if the device doesn't support
             inclusion of this information.";
        }
        leaf AdditionalInformation {
          type string {
            length "0..256";
          }
          description
            "This contains additional information about the alarm
             and is vendor defined.";
        }
      }

      list ExpeditedEvent {
        key "AlarmIdentifier";
        config false;
        description
          "Alarm events added or updated in
           {{object|.FaultMgmt.CurrentAlarm.{i}.}} are
           simultaneously entered into the this table if their
           corresponding entry in
           {{object|.FaultMgmt.SupportedAlarm.{i}.}} has
           {{param|.FaultMgmt.SupportedAlarm.{i}.ReportingMechanism}}
           set to {{enum|0
           Expedited|.FaultMgmt.SupportedAlarm.{i}.ReportingMechanism}}.
           This table also contains alarm clearing events.
        
           This object has a fixed number of entries with
           instance numbers from 1 to
           {{param|.FaultMgmt.ExpeditedEventNumberOfEntries}}.
        
           Initially the table starts with all instances having
           {{param|EventTime}} set to the Unknown Time value, as
           defined in {{bibref|TR-106a4}}.
        
           If maximum instance number
           {{param|.FaultMgmt.ExpeditedEventNumberOfEntries}} is
           reached, the next event overrides the object with
           instance number 1.  Subsequent entries override
           objects at sequentially increasing instance numbers.
           This logic provides for automatic \"rolling\" of
           records.
        
           When a new alarm replaces an existing alarm, then all
           parameter values for that instance are considered as
           changed for the purposes of value change notifications
           to the ACS (even if their new values are identical to
           those of the prior alarm).";
        leaf EventTime {
          type yang:date-and-time;
          description
            "Indicates the date and time when the alarm event
             occurs.
          
             For an unpopulated entry, the value is the Unknown
             Time as defined in {{bibref|TR-106a4}}.";
        }
        leaf AlarmIdentifier {
          type string {
            length "0..64";
          }
          description
            "Identifies one Alarm Entry in the Alarm List.  This
             value MUST be uniquely allocated by the device to
             the alarm instance during the lifetime of the
             individual alarm.
          
             For an unpopulated entry, the value is {{empty}}.";
        }
        leaf NotificationType {
          type enumeration {
            enum "NewAlarm";
            enum "ChangedAlarm";
            enum "ClearedAlarm";
          }
          description
            "Indicates the reason for the specific alarm
             notification event.  {{enum}}";
        }
        leaf ManagedObjectInstance {
          type string {
            length "0..512";
          }
          description
            "Specifies the instance of the Informational Object
             Class in which the alarm occurred by carrying the
             Distinguished Name (DN) of this object instance.
             The format of the DN is specific to the application
             that is using this {{object}}.";
        }
        leaf EventType {
          type string {
            length "0..64";
          }
          description
            "Indicates the type of event.";
        }
        leaf ProbableCause {
          type string {
            length "0..64";
          }
          description
            "Qualifies the alarm and provides further information
             than {{param|EventType}}.";
        }
        leaf SpecificProblem {
          type string {
            length "0..128";
          }
          description
            "Provides further qualification on the alarm beyond
             {{param|EventType}} and {{param|ProbableCause}}.
          
             This is vendor defined and will be {{empty}} if the
             device doesn't support inclusion of this
             information.";
        }
        leaf PerceivedSeverity {
          type enumeration {
            enum "Cleared";
            enum "Critical";
            enum "Major";
            enum "Minor";
            enum "Warning";
            enum "Indeterminate";
          }
          description
            "Indicates the relative level of urgency for operator
             attention, see {{bibref|ITU-X.733}}.  {{enum}}";
        }
        leaf AdditionalText {
          type string {
            length "0..256";
          }
          description
            "This provides a textual string which is vendor defined.
          
             This will be {{empty}} if the device doesn't support
             inclusion of this information.";
        }
        leaf AdditionalInformation {
          type string {
            length "0..256";
          }
          description
            "This contains additional information about the alarm
             and is vendor defined.";
        }
      }

      list QueuedEvent {
        key "AlarmIdentifier";
        config false;
        description
          "Alarm events added or updated in
           {{object|.FaultMgmt.CurrentAlarm.{i}.}} are
           simultaneously entered into the this table if their
           corresponding entry in
           {{object|.FaultMgmt.SupportedAlarm.{i}.}} has
           {{param|.FaultMgmt.SupportedAlarm.{i}.ReportingMechanism}}
           set to {{enum|1
           Queued|.FaultMgmt.SupportedAlarm.{i}.ReportingMechanism}}.
           This table also contains alarm clearing events.
        
           This object has a fixed number of entries with
           instance numbers from 1 to
           {{param|.FaultMgmt.QueuedEventNumberOfEntries}}.
        
           Initially the table starts with all instances having
           {{param|EventTime}} set to the Unknown Time value, as
           defined in {{bibref|TR-106a4}}.
        
           If maximum instance number
           {{param|.FaultMgmt.QueuedEventNumberOfEntries}} is
           reached, the next event overrides the object with
           instance number 1.  Subsequent entries override
           objects at sequentially increasing instance numbers.
           This logic provides for automatic \"rolling\" of
           records.
        
           When a new alarm replaces an existing alarm, then all
           parameter values for that instance are considered as
           changed for the purposes of value change notifications
           to the ACS (even if their new values are identical to
           those of the prior alarm).";
        leaf EventTime {
          type yang:date-and-time;
          description
            "Indicates the date and time when the alarm event
             occurs.
          
             For an unpopulated entry, the value is the Unknown
             Time as defined in {{bibref|TR-106a4}}.";
        }
        leaf AlarmIdentifier {
          type string {
            length "0..64";
          }
          description
            "Identifies one Alarm Entry in the Alarm List.  This
             value MUST be uniquely allocated by the device to
             the alarm instance during the lifetime of the
             individual alarm.
          
             For an unpopulated entry, the value is {{empty}}.";
        }
        leaf NotificationType {
          type enumeration {
            enum "NewAlarm";
            enum "ChangedAlarm";
            enum "ClearedAlarm";
          }
          description
            "Indicates the reason for the specific alarm
             notification event.  {{enum}}";
        }
        leaf ManagedObjectInstance {
          type string {
            length "0..512";
          }
          description
            "Specifies the instance of the Informational Object
             Class in which the alarm occurred by carrying the
             Distinguished Name (DN) of this object instance.
             The format of the DN is specific to the application
             that is using this {{object}}.";
        }
        leaf EventType {
          type string {
            length "0..64";
          }
          description
            "Indicates the type of event.";
        }
        leaf ProbableCause {
          type string {
            length "0..64";
          }
          description
            "Qualifies the alarm and provides further information
             than {{param|EventType}}.";
        }
        leaf SpecificProblem {
          type string {
            length "0..128";
          }
          description
            "Provides further qualification on the alarm beyond
             {{param|EventType}} and {{param|ProbableCause}}.
          
             This is vendor defined and will be {{empty}} if the
             device doesn't support inclusion of this
             information.";
        }
        leaf PerceivedSeverity {
          type enumeration {
            enum "Cleared";
            enum "Critical";
            enum "Major";
            enum "Minor";
            enum "Warning";
            enum "Indeterminate";
          }
          description
            "Indicates the relative level of urgency for operator
             attention, see {{bibref|ITU-X.733}}.  {{enum}}";
        }
        leaf AdditionalText {
          type string {
            length "0..256";
          }
          description
            "This provides a textual string which is vendor defined.
          
             This will be {{empty}} if the device doesn't support
             inclusion of this information.";
        }
        leaf AdditionalInformation {
          type string {
            length "0..256";
          }
          description
            "This contains additional information about the alarm
             and is vendor defined.";
        }
      }
    }

    container Security {
      description
        "This object contains general information related to
         managing security features on the device.";

      list Certificate {
        key "SerialNumber Issuer";
        description
          "This table provides information about all types of public
           key-based credentials, such as X.509 certificates, see
           {{bibref|RFC5280}}.";
        leaf Enable {
          type boolean;
          description
            "Enables or disables this certificate.";
        }
        leaf LastModif {
          type yang:date-and-time;
          config false;
          description
            "The last modification time of this certificate.";
        }
        leaf SerialNumber {
          type string {
            length "0..64";
          }
          config false;
          description
            "The Serial Number field in an X.509 certificate, see
             {{bibref|RFC5280}}.";
        }
        leaf Issuer {
          type string {
            length "0..256";
          }
          config false;
          description
            "The Issuer field in an X.509 certificate, see
             {{bibref|RFC5280}}; i.e.  the Distinguished Name
             (DN) of the entity who has signed the certificate.";
        }
        leaf NotBefore {
          type yang:date-and-time;
          config false;
          description
            "The beginning of the certificate validity period; i.e.
             the Not Before field in an X.509 certificate, see
             {{bibref|RFC5280}}.";
        }
        leaf NotAfter {
          type yang:date-and-time;
          config false;
          description
            "The end of the certificate validity period; i.e., the
             Not After field in an X.509 certificate, see
             {{bibref|RFC5280}}.";
        }
        leaf Subject {
          type string {
            length "0..256";
          }
          config false;
          description
            "The Distinguished Name (DN) of the entity associated
             with the Public Key; i.e., the Subject field in an
             X.509 certificate, see {{bibref|RFC5280}}.";
        }
        leaf SubjectAlt {
          type string;
          config false;
          description
            "{{list}} Each item is a DNS Name.
          
             The Subject Alternative Names extension field in an
             X.509 certificate, see {{bibref|RFC5280}}.";
        }
        leaf SignatureAlgorithm {
          type string {
            length "0..256";
          }
          config false;
          description
            "The algorithm used in signing the certificate; i.e.
             the Signature Algorithm field in an X.509
             certificate, see {{bibref|RFC5280}}.";
        }
      }
    }

    container FAP {
      description
        "This object is the container for all Femto related
         component objects, to prevent pollution of the so-called
         global namespace of the BBF with FAP specific objects.";

      container GPS {
        description
          "This object contains the parameters relating to the GPS
           scan.";
        leaf ScanOnBoot {
          type boolean;
          default "true";
          description
            "Enables or disables GPS scans during the device start
             up.";
        }
        leaf ScanPeriodically {
          type boolean;
          default "false";
          description
            "Enables or disables periodic GPS scans.";
        }
        leaf PeriodicInterval {
          type uint32;
          description
            "When {{param|ScanPeriodically}} is {{true}}, this value
             indicates the interval in {{units}} which GPS scan
             is performed.";
        }
        leaf PeriodicTime {
          type yang:date-and-time;
          description
            "An absolute time reference in UTC to determine when the
             CPE will initiate the periodic GPS scan.  Each GPS
             scan MUST occur at (or as soon as possible after)
             this reference time plus or minus an integer
             multiple of the {{param|PeriodicInterval}}.
          
             {{param}} is used only to set the \"phase\" of the
             GPS scan.  The actual value of {{param}} can be
             arbitrarily far into the past or future.
          
             For example, if {{param|PeriodicInterval}} is 86400
             (a day) and if {{param}} is set to UTC midnight on
             some day (in the past, present, or future) then
             periodic GPS scans will occur every day at UTC
             midnight.  These MUST begin on the very next
             midnight, even if {{param}} refers to a day in the
             future.
          
             The Unknown Time value defined in
             {{bibref|TR-106a4|Section 3.2}} indicates that no
             particular time reference is specified.  That is,
             the CPE MAY locally choose the time reference, and
             needs only to adhere to the specified
             PeriodicInformInterval.
          
             If absolute time is not available to the CPE, its
             periodic GPS scan behavior MUST be the same as if
             {{param}} parameter was set to the Unknown Time
             value.";
        }
        leaf ContinuousGPS {
          type boolean;
          description
            "Whether or not the device SHOULD maintain a continuous
             GPS lock (e.g.  as a frequency stability source).";
        }
        leaf ScanTimeout {
          type uint32;
          description
            "Specifies the time-out value in {{units}} since the
             scan started after which the scan will time out.  A
             timed out scan is to be reported as
             {{enum|Error_TIMEOUT|ScanStatus}} with
             {{param|ErrorDetails}} indicating \"Timed out\"";
        }
        leaf ScanStatus {
          type enumeration {
            enum "Indeterminate";
            enum "InProgress";
            enum "Success";
            enum "Error";
            enum "Error_TIMEOUT";
          }
          config false;
          description
            "Indicates the current status of this scan.";
        }
        leaf ErrorDetails {
          type string {
            length "0..256";
          }
          config false;
          description
            "Provides more detail when the {{param|ScanStatus}} is
             either {{enum|Error|ScanStatus}} or
             {{enum|Error_TIMEOUT|ScanStatus}}.";
        }
        leaf LastScanTime {
          type yang:date-and-time;
          config false;
          description
            "The date and time when the last GPS scan completed.";
        }
        leaf LastSuccessfulScanTime {
          type yang:date-and-time;
          config false;
          description
            "Specifies the date and time, when the GPS scan last
             completed successfully.
          
             This value is retained across reboot and is only
             reset after another scan completes successfully or
             {{param|GPSReset}} is set to {{true}}.
          
             The values for {{param|LockedLatitude}},
             {{param|LockedLongitude}} and
             {{param|NumberOfSatellites}} correspond to this
             time.  If a scan has never succeeded before, the
             value will be the Unknown Time value, as defined in
             {{bibref|TR-106a4|Section 3.2}}.";
        }
        leaf LockedLatitude {
          type int32 {
            range "-90000000..90000000";
          }
          config false;
          description
            "This parameter specifies the latitude of the device's
             position in degrees, multiplied by 1 million.  The
             positive value signifies the direction, north of the
             equator.  The negative value signifies the
             direction, south of the equator.
          
             Range is from: 90d00.00' South (-90,000,000) to
             90d00.00' North (90,000,000).
          
             Example: A latitude of 13d19.43' N would be
             represented as 13,323,833, derived as
             (13*1,000,000)+((19.43*1,000,000)/60).  Latitude of
             50d00.00' S would be represented as value
             -50,000,000.
          
             This value is retained across reboots and is only
             reset after another scan completes successfully or
             {{param|GPSReset}} is set to {{true}}.  If a scan
             has never succeeded before, the value 0 is reported.";
        }
        leaf LockedLongitude {
          type int32 {
            range "-180000000..180000000";
          }
          config false;
          description
            "This parameter specifies the longitude of the device's
             position in degrees, multiplied by 1 million.  The
             positive value signifies the direction, east of the
             prime meridian.  The negative value signifies the
             direction, west of the prime meridian.
          
             Range is from: 180d00.00' West (-180,000,000) to
             180d00.00' East (180,000,000).
          
             Example: A longitude of 13d19.43' E would be
             represented as 13,323,833, derived as
             (13*1,000,000)+((19.43*1,000,000)/60).  A longitude
             of 50d00.00' W would be represented as value
             -50,000,000.
          
             This value is retained across reboots and is only
             reset after another scan completes successfully or
             {{param|GPSReset}} is set to {{true}}.  If a scan
             has never succeeded before, the value 0 is reported.";
        }
        leaf NumberOfSatellites {
          type uint32;
          config false;
          description
            "The number of satellites that were locked during the
             test execution.  The greater the number of
             satellites the better the precision of the results.
          
             This value is retained across reboots and is only
             reset after another scan completes successfully or
             {{param|GPSReset}} is set to {{true}}.  If a scan
             has never succeeded before, the value 0 is reported.";
        }
        leaf GPSReset {
          type boolean; /* command */
          description
            "Setting this to {{true}} will cause a reset on the GPS
             Hardware.  Setting this to {{false}} has no effect.";
        }

        container ContinuousGPSStatus {
          description
            "When {{param|#.ContinuousGPS}} is {{true}}, the
             parameters in this object contain the GPS status as
             it is continuously monitored.
          
             When {{param|#.ContinuousGPS}} is {{false}}, the
             parameters in this object are not being updated and
             their values are not accurate.";
          leaf CurrentFix {
            type boolean;
            config false;
            description
              "The value is {{true}} if the location fix is
               currently valid (i.e.  GPS receiver is currently
               tracking satellite signals), otherwise it is
               {{false}}.  After a reboot the value is {{false}}
               until the GPS receivers has a valid current
               position.";
          }
          leaf GotFix {
            type boolean;
            config false;
            description
              "The value is {{true}} if {{param|CurrentFix}} has
               transitioned to {{true}} at least once since
               {{param|#.ContinuousGPS}} was enabled, otherwise
               it is {{false}}.  After a reboot the value is
               {{false}} until {{param|CurrentFix}} has
               transitioned to {{true}} again.
            
               The GPS coordinates ({{param|Latitude}},
               {{param|Longitude}}, and {{param|Elevation}}) are
               not valid until {{param}} has a value of {{true}}.";
          }
          leaf TimingGood {
            type boolean;
            config false;
            description
              "The value is {{true}} if the timing synchronization
               is good, otherwise it is {{false}}.  After a
               reboot the value is {{false}} until the timing is
               synchronized again.";
          }
          leaf Latitude {
            type int32 {
              range "-90000000..90000000";
            }
            config false;
            description
              "This parameter represents the most recent latitude
               reading for the device's position in degrees,
               multiplied by 1 million.  The positive value
               signifies the direction, north of the equator.
               The negative value signifies the direction, south
               of the equator.
            
               Range is from: 90 deg 00.00' South (-90,000,000)
               to 90 deg 00.00' North (90,000,000).
            
               Example: A latitude of 13 deg 19.43' N would be
               represented as 13,323,833, derived as
               (13*1,000,000)+((19.43*1,000,000)/60).  Latitude
               of 50 deg 00.00' S would be represented as value
               -50,000,000.
            
               {{param}} is not valid until {{param|GotFix}} is
               {{true}}.
            
               If the parameter has never been set before, the
               value 0 is reported.  The value SHOULD be
               maintained over a reboot.";
          }
          leaf Longitude {
            type int32 {
              range "-180000000..180000000";
            }
            config false;
            description
              "This parameter represents the most recent longitude
               reading for the device's position in degrees,
               multiplied by 1 million.  The positive value
               signifies the direction, east of the prime
               meridian.  The negative value signifies the
               direction, west of the prime meridian.
            
               Range is from: 180d00.00' West (-180,000,000) to
               180d00.00' East (180,000,000).
            
               Example: A longitude of 13d19.43' E would be
               represented as 13,323,833, derived as
               (13*1,000,000)+((19.43*1,000,000)/60).  A
               longitude of 50d00.00' W would be represented as
               value -50,000,000.
            
               {{param}} is not valid until {{param|GotFix}} is
               {{true}}.
            
               If the parameter has never been set before, the
               value 0 is reported.  The value SHOULD be
               maintained over a reboot.";
          }
          leaf Elevation {
            type int32 {
              range "-5000000..25000000";
            }
            config false;
            description
              "This parameter represents the most recent elevation
               reading for the device's position in {{units}},
               relative to the WGS84 ellipsoid.  The positive
               value signifies the direction, above sea level.
               The negative value signifies the direction, below
               sea level.
            
               Range is from: 5,000.000 meters below sea level
               (-5,000,000) to 25,000.000 meters above sea level
               (25,000,000).
            
               {{param}} is not valid until {{param|GotFix}} is
               {{true}}.
            
               If the parameter has never been set before, the
               value 0 is reported.  The value SHOULD be
               maintained over a reboot.";
          }
          leaf LastFixTime {
            type yang:date-and-time;
            config false;
            description
              "Represents the date and time when the last GPS Fix
               was acquired.
            
               The Unknown Time value defined in
               {{bibref|TR-106a4|Section 3.2}} is used when
               {{param|GotFix}} is {{false}}.  This applies too
               after a reboot of the device until a valid
               location is determined and {{param|GotFix}}
               transsitions to {{true}}.";
          }
          leaf LastFixDuration {
            type uint32;
            config false;
            description
              "Number of {{units}} of continuous GPS fix time.
               After a reboot this value is reset to 0.";
          }
          leaf FirstFixTimeout {
            type int32 {
              range "-1..max";
            }
            description
              "Number of {{units}} to wait for first GPS fix before
               declaring a GPS fault.
            
               A value of -1 means that there is no timeout and
               no fault logging.";
          }
          leaf SatellitesTracked {
            type uint32;
            config false;
            description
              "The number of satellites the receiver is tracking.";
          }
          leaf SatelliteTrackingInterval {
            type uint32 {
              range "60..3600";
            }
            description
              "The interval in {{units}} at which the GPS tracking
               information gets reported.";
          }
          leaf ReceiverStatus {
            type string {
              length "0..256";
            }
            config false;
            description
              "The output of the GPS receiver's status.";
          }
          leaf LocationType {
            type enumeration {
              enum "Real";
              enum "Reference";
            }
            config false;
            description
              "Indicates whether the {{param|Latitude}},
               {{param|Longitude}}, and {{param|Elevation}}
               values are determined via a GPS Fix (where the
               value of this parameter would be {{enum|Real}}) or
               via some other means (where the value of this
               parameter would be {{enum|Reference}}).";
          }
          leaf LockTimeOutDuration {
            type uint32 {
              range "120..86400";
            }
            description
              "The timer duration, in {{units}}, for which the
               device waits for GPS to acquire lock.";
          }
        }

        container AGPSServerConfig {
          description
            "This object contains parameters for the configuration
             of the Assisted Global Positioning System (A-GPS)
             server.  See also {{bibref|3GPP-TS.25.171|Section
             3.2}}";
          leaf Enable {
            type boolean;
            description
              "Enables or disables the {{object}} entry.";
          }
          leaf ServerURL {
            type string {
              length "0..256";
            }
            description
              "A-GPS server host name or IP address.";
          }
          leaf ServerPort {
            type uint32 {
              range "min..65535";
            }
            description
              "The port to use when communicating to the A-GPS
               Server.";
          }
          leaf Username {
            type string {
              length "0..64";
            }
            description
              "Username to be used by the device to authenticate
               with the A-GPS server.  This string is set to
               {{empty}} if no authentication is used.";
          }
          leaf Password {
            type string {
              length "0..64";
            }
            description
              "Password to be used by the device to authenticate
               with the A-GPS server.  This string is set to
               {{empty}} if no authentication is used.";
          }
          leaf ReferenceLatitude {
            type int32 {
              range "-90000000..90000000";
            }
            description
              "This parameter specifies the reference latitude for
               an A-GPS request position in degrees, multiplied
               by 1 million.  The positive value signifies the
               direction, north of the equator.  The negative
               value signifies the direction, south of the
               equator.
            
               Range is from: 90d00.00' South (-90,000,000) to
               90d00.00' North (90,000,000).
            
               Example: A latitude of 13d19.43' N would be
               represented as 13,323,833, derived as
               (13*1,000,000)+((19.43*1,000,000)/60).  Latitude
               of 50d00.00' S would be represented as value
               -50,000,000.";
          }
          leaf ReferenceLongitude {
            type int32 {
              range "-180000000..180000000";
            }
            description
              "This parameter specifies the reference longitude for
               an A-GPS request position in degrees, multiplied
               by 1 million.  The positive value signifies the
               direction, east of the prime meridian.  The
               negative value signifies the direction, west of
               the prime meridian.
            
               Range is from: 180d00.00' West (-180,000,000) to
               180d00.00' East (180,000,000).
            
               Example: A longitude of 13d19.43' E would be
               represented as 13,323,833, derived as
               (13*1,000,000)+((19.43*1,000,000)/60).  A
               longitude of 50d00'00'' W would be represented as
               value -50,000,000.";
          }
          leaf ServerInUse {
            type boolean;
            config false;
            description
              "The value is {{true}} if the device has successfully
               contacted and received A-GPS info from the A-GPS
               server, otherwise the value is {{false}}.
            
               After a reboot the value is {{false}} until the
               server could be contacted again.";
          }
        }
      }

      container PerfMgmt {
        description
          "This object contains parameters relating to Performance
           Management in a Femto-related environment.";

        list Config {
          key "URL PeriodicUploadInterval PeriodicUploadTime";
          description
            "This object contains parameters relating to File
             Management configuration for uploading of
             Performance Files to a designated File Server.  Each
             table entry can be referenced by zero or more
             radio-specific objects contained in the FAPService
             instances.  The periodic upload will upload data for
             all of the radio-specific objects that reference it.";
          leaf Enable {
            type boolean;
            description
              "Enables or disables this entry.  If this entry is
               disabled then its periodic uploads are not
               performed.";
          }
          leaf URL {
            type string {
              length "0..256";
            }
            description
              "URL specifying the destination file location.  HTTP
               and HTTPS transports MUST be supported.  Other
               transports MAY be supported.
            
               This argument specifies only the destination file
               location, and does not indicate in any way the
               name or location of the local file to be uploaded.";
          }
          leaf Username {
            type string {
              length "0..256";
            }
            description
              "Username to be used by the device to authenticate
               with the file server.  This string is set to
               {{empty}} if no authentication is used.";
          }
          leaf Password {
            type string {
              length "0..256";
            }
            description
              "Password to be used by the device to authenticate
               with the file server.  This string is set to
               {{empty}} if no authentication is used.";
          }
          leaf PeriodicUploadInterval {
            type uint32 {
              range "1..max";
            }
            description
              "The duration in {{units}} of the interval for which
               the device MUST create a Performance File and
               attempt to upload the file to {{param|URL}} if
               {{param|Enable}} is {{true}}.";
          }
          leaf PeriodicUploadTime {
            type yang:date-and-time;
            description
              "An absolute time reference in UTC to determine when
               the device will initiate the periodic file upload.
               Each file upload MUST occur at this reference time
               plus or minus an integer multiple of the
               {{param|PeriodicUploadInterval}}.
            
               {{param}} is used only to set the \"phase\" of the
               periodic uploads.  The actual value of {{param}}
               can be arbitrarily far into the past or future.
            
               For example, if {{param|PeriodicUploadInterval}}
               is 86400 (a day) and if {{param}} is set to UTC
               midnight on some day (in the past, present, or
               future) then periodic file uploads will occur
               every day at UTC midnight.  These MUST begin on
               the very next midnight, even if {{param}} refers
               to a day in the future.
            
               The Unknown Time value as defined in
               {{bibref|TR-106a4|Section 3.2}} indicates that no
               particular time reference is specified.  That is,
               the device MAY locally choose the time reference,
               and is REQUIRED only to adhere to the specified
               {{param|PeriodicUploadInterval}}.
            
               If absolute time is not available to the device,
               its periodic file upload behavior MUST be the same
               as if the {{param}} parameter was set to the
               Unknown Time value.";
          }
        }
      }

      container ApplicationPlatform {
        description
          "This object defines the data model for the following
           Femtozone APIs.
        
           * Femto Awareness
        
           * SMS
        
           * MMS
        
           * Terminal Location
        
           Femto Awareness, SMS, MMS, and Terminal Location APIs
           are defined in the Release 1 API Specifications of the
           Service SIG in the Femto Forum (non public document).
        
           {{bibref|TR-262|appendix I}} provides the \"Theory of
           Operation\" for the usage of this object.";
        leaf Version {
          type string {
            length "0..64";
          }
          config false;
          description
            "Version of Femto Application Platform running on this
             device";
        }
        leaf Enable {
          type boolean;
          description
            "Enable or disable the Femto ApplicationPlatform";
        }
        leaf Status {
          type enumeration {
            enum "Disabled";
            enum "Enabled";
            enum "Reset";
            enum "Initializing";
          }
          config false;
          description
            "Current state of the Femto Application Platform.";
        }
        leaf MaxNumberOfApplications {
          type uint32;
          config false;
          description
            "Determines how many Femtozone Applications can be
             supported by the Femto Application Platform
             simultaneously.";
        }
        leaf CurrentNumberofApplications {
          type uint32;
          config false;
          description
            "Specifies how many Femtozone Applications are currently
             communicating with the Femto Application Platform.";
        }

        container Capabilities {
          config false;
          description
            "This object contains parameters related to the
             capabilities of the Femtozone Application Platform
             and the Femtozone APIs.";
          leaf PresenceApplicationSupport {
            type boolean;
            description
              "Specifies whether the Femto Application Platform
               supports Presence-Based Femtozone Applications";
          }
          leaf FemtoAwarenessAPISupport {
            type boolean;
            description
              "Specifies whether the Femto Awareness API is
               supported on this device.";
          }
          leaf SMSAPISupport {
            type boolean;
            description
              "Specifies whether the SMS API is supported on this
               device.";
          }
          leaf SubscribeToNotificationsOfSMSSentToApplicationSupport {
            type boolean;
            description
              "Specifies whether the
               SubscribeToNotificationsOfSMSSentToApplication
               functionality is supported by the FAP SMS API.";
          }
          leaf QuerySMSDeliveryStatusSupport {
            type boolean;
            description
              "Specifies whether the QuerySMSDeliveryStatus
               functionality is supported by the FAP SMS API.";
          }
          leaf MMSAPISupport {
            type boolean;
            description
              "Specifies whether the MMS API is supported on this
               device.";
          }
          leaf QueryMMSDeliveryStatusSupport {
            type boolean;
            description
              "Specifies whether the QueryMMSDeliveryStatus
               functionality is supported by the FAP MMS API.";
          }
          leaf SubscribeToNotificationsOfMMSSentToApplicationSupport {
            type boolean;
            description
              "Specifies whether the
               SubscribeToNotificationsOfMMSSentToApplication
               functionality is supported by the FAP MMS API.";
          }
          leaf TerminalLocationAPISupport {
            type boolean;
            description
              "Specifies whether the Terminal Location API is
               supported on this device.";
          }
          leaf AuthenticationMethodsSupported {
            type enumeration {
              enum "Basic";
              enum "Digest";
              enum "DigitalSignature";
            }
            description
              "Specifies the supported methods that 3rd Party
               Applications can use to authenticate with the
               Femto Application Platform at initialization.
               Comma separated list of strings.";
          }
          leaf AccessLevelsSupported {
            type enumeration {
              enum "Guest";
              enum "Standard";
              enum "Restricted";
              enum "Administrator";
              enum "Debug";
            }
            description
              "Specifies the supported access levels that 3rd Party
               Applications can request when authenticating with
               the Femto Application Platform at initialization.
               This access level is with respect to resources
               within the Femto Application Platform only (not to
               be confused with Access Mode parameter in
               .FAPService.{i}.AccessMgmt).";
          }
          leaf SendSMSTargetAddressType {
            type enumeration {
              enum "TelUri";
              enum "AnonymousReference";
              enum "All";
            }
            description
              "Specifies the supported types of addresses SMSs can
               be sent to.";
          }
          leaf SendMMSTargetAddressType {
            type enumeration {
              enum "TelUri";
              enum "AnonymousReference";
              enum "All";
            }
            description
              "Specifies the supported types of addresses MMSs can
               be sent to.";
          }
        }

        container Control {
          description
            "This object contains parameters related to the
             operation of the Femtozone APIs.";
          leaf AuthenticationMethod {
            type string {
              length "0..256";
            }
            description
              "Specifies how 3rd Party Applications have to
               authenticate against Femto APIs in order to use
               it.  {{reference}}
            
               '''''Note:''''' The credentials are not part of
               the data model and have to be supplied externally.";
          }
          leaf TunnelInst {
            type string {
              length "0..256";
            }
            description
              "This is the reference to the IPsec tunnel instance to
               be used by the Application Platform traffic.
            
               If InternetGatewayDevice:1 {{bibref|TR-098}} or
               Device:1 {{bibref|TR-181i1}}) is used as root data
               model the {{param}} MUST point to a row in the
               ''.FAP.Tunnel.IKESA.{i}.'' table.
            
               If the root data model used is Device:2
               {{bibref|TR-181i2}} than the {{param}} MUST point
               to an tunnel instance defined in this data model.
            
               If the referenced object is deleted, the parameter
               value MUST be set to an empty string.";
          }

          container FemtoAwareness {
            description
              "This object contains parameters related to the Femto
               Awareness API.";
            leaf APIEnable {
              type boolean;
              description
                "Enable or disable FemtoAwareness API exposure on
                 FAP";
            }
            leaf QueueEnable {
              type boolean;
              description
                "Enable or disable Request queueing for the API";
            }
            leaf Queueing  {
              type enumeration {
                enum "FiFo";
                enum "Priority";
              }
              description
                "Determines how FAP handles simultaneous requests
                 from different Applications to Femto Awareness
                 API.";
            }
            leaf MaxAPIUsersNumber {
              type uint32 {
                range "0..255";
              }
              description
                "Determines the Max Number of different Applications
                 that can send Requests to Femto Awareness API.";
            }
            leaf FemtozoneID {
              type string {
                length "0..256";
              }
              description
                "Specifies Identifier of the Femtozone.";
            }
            leaf NotificationsUserIdentifierMSISDN {
              type boolean;
              description
                "Specifies whether the Mobile Station International
                 Subscriber Directory Number (MSISDN) has to be
                 used as UserIdentifier in Femto Awareness
                 Notifications.  A value of {{true}} means that
                 the MSISDN is send as user identifier, a value
                 of {{false}} means that an anonymous reference
                 is used.";
            }
            leaf SubscribeToNotificationsResponseCallbackData {
              type boolean;
              description
                "Specifies whether the OPTIONAL Argument \"Callback
                 Data\" has to be used in Responses to Requests
                 to \"Subscribe To Femto Awareness
                 Notifications\".";
            }
            leaf QueryFemtocellResponseTimezone {
              type boolean;
              description
                "Specifies whether the OPTIONAL Argument
                 \"Timezone\" has to be used in Responses to
                 Requests to \"Query Femtocell Status\".";
            }
          }

          container SMS {
            description
              "This object contains parameters related to the SMS
               API.";
            leaf APIEnable {
              type boolean;
              description
                "Enable or disable SMS API exposure on FAP";
            }
            leaf QueueEnable {
              type boolean;
              description
                "Enable or disable Request queueing for the API";
            }
            leaf Queueing  {
              type enumeration {
                enum "FiFo";
                enum "Priority";
              }
              description
                "Determines how FAP handles simultaneous requests
                 from different Applications to SMS API.";
            }
            leaf MaxAPIUsersNumber {
              type uint32 {
                range "0..255";
              }
              description
                "Determines the Max Number of different Applications
                 that can send Requests to SMS API.";
            }
            leaf MinSendSMSTimeInterval {
              type uint32 {
                range "0..3599";
              }
              description
                "Determines the Minimum Time Interval in {{units}}
                 between two consecutive Send SMS Requests by the
                 same Application.";
            }
            leaf EnableQuerySMSDeliveryStatus {
              type boolean;
              description
                "Enable or disable \"QuerySMSDeliveryStatus\"
                 Operation on SMS API.  When disabled,
                 QuerySMSDeliveryStatus Requests to SMS API are
                 ignored.";
            }
            leaf EnableSubscribeToNotificationsOfMessageSentToApplication {
              type boolean;
              description
                "Enable or disable
                 \"SubscribeToNotificationsOfMessageSentToApplication\"
                 Operation on SMS API.  When disabled,
                 SubscribeTo
                 NotificationsOfMessageSentToApplication Requests
                 to SMS API are ignored.";
            }
          }

          container MMS {
            description
              "This object contains parameters related to the MMS
               API.";
            leaf APIEnable {
              type boolean;
              description
                "Enable or disable MMS API exposure on FAP";
            }
            leaf QueueEnable {
              type boolean;
              description
                "Enable or disable Request queueing for the API";
            }
            leaf Queueing  {
              type enumeration {
                enum "FiFo";
                enum "Priority";
              }
              description
                "Determines how FAP handles simultaneous requests
                 from different Applications to MMS API.";
            }
            leaf MaxAPIUsersNumber {
              type uint32 {
                range "0..255";
              }
              description
                "Determines the Max Number of different Applications
                 that can send Requests to MMS API.";
            }
            leaf MinSendMMSTimeInterval {
              type uint32 {
                range "0..3599";
              }
              description
                "Determines the Minimum Time Interval in {{units}}
                 between two consecutive Send MMS Requests by the
                 same Application.";
            }
            leaf EnableQueryMMSDeliveryStatus {
              type boolean;
              description
                "Enable or disable \"QuerySMSDeliveryStatus\"
                 Operation on MMS API.  When disabled,
                 QuerySMSDeliveryStatus Requests to MMS API are
                 ignored.";
            }
            leaf EnableSubscribeToNotificationsOfMessageSentToApplication {
              type boolean;
              description
                "Enable or disable \"SubscribeTo
                 NotificationsOfMessageSentToApplication\"
                 Operation on MMS API.  When disabled,
                 SubscribeTo
                 NotificationsOfMessageSentToApplication Requests
                 to MMS API are ignored.";
            }
          }

          container TerminalLocation {
            description
              "This object contains parameters related to the
               TerminalLocation API.";
            leaf APIEnable {
              type boolean;
              description
                "Enable or disable TerminalLocation API exposure on
                 FAP";
            }
            leaf QueueEnable {
              type boolean;
              description
                "Enable or disable Request queueing for the API";
            }
            leaf Queueing  {
              type enumeration {
                enum "FiFo";
                enum "Priority";
              }
              description
                "Determines how FAP handles simultaneous requests
                 from different Applications to TerminalLocation
                 API.";
            }
            leaf MaxAPIUsersNumber {
              type uint32 {
                range "0..255";
              }
              description
                "Determines the Max Number of different Applications
                 that can send Requests to TerminalLocation API.";
            }
            leaf QueryMobileLocationResponseAddress {
              type enumeration {
                enum "TelUri";
                enum "AnonymousReference";
              }
              description
                "Specifies Terminal Address Format to be used in
                 QueryMobileLocation Responses.";
            }
            leaf QueryMobileLocationResponseLongitudeLatitude {
              type boolean;
              description
                "Include or exclude FAP Longitude and Latitude
                 arguments in Responses to QueryMobileLocation
                 Requests.";
            }
            leaf QueryMobileLocationResponseAltitude {
              type boolean;
              description
                "Include or exclude FAP Altitude argument in
                 Responses to QueryMobileLocation Requests .";
            }
            leaf QueryMobileLocationResponseTimestamp {
              type uint32 {
                range "0..86399";
              }
              description
                "Specifies Response Timestamp in {{units}}.";
            }
          }
        }

        container Monitoring {
          description
            "This object contains parameters related to the
             monitoring of the Femtozone Application Platform and
             the Femtozone APIs.";
          leaf Enable {
            type boolean;
            description
              "Enables and disables this entry.";
          }
          leaf MonitoringInterval {
            type uint32;
            description
              "Specifies the interval in {{units}} used to collect
               the monitoring measurements.";
          }
          leaf AuthenticationRequestsReceived {
            type uint32;
            config false;
            description
              "Specifies the total number of authentication requests
               received by the Femto Application Platform.  The
               counter will be reset whenever the device reboots
               or the {{param|Enable}} parameter is set to
               {{true}}.";
          }
          leaf AuthenticationRequestsRejected {
            type uint32;
            config false;
            description
              "Specifies the number of authentication requests
               received by the Femto Application Platform that
               were rejected.  The counter will be reset whenever
               the device reboots or the {{param|Enable}}
               parameter is set to {{true}}.";
          }

          container FemtoAwareness {
            config false;
            description
              "This object contains parameters related to the
               Monitoring of the FemtoAwareness API.";
            leaf APIAvailable {
              type boolean;
              description
                "Specifies whether the FemtoAwareness API is
                 currently available on this device (the API
                 could be disabled or could have exhausted its
                 resources)";
            }
            leaf APIUsers {
              type uint32 {
                range "0..255";
              }
              description
                "Specifies the current number of Applications using
                 the Femto Awareness API.";
            }
            leaf QueueState {
              type enumeration {
                enum "Disabled";
                enum "Ready";
                enum "Flushed";
              }
              description
                "Specifies the state of the Femto Awareness API
                 Queue.";
            }
            leaf QueueNum {
              type uint32 {
                range "0..255";
              }
              description
                "Specifies the current number of requests waiting in
                 the Femto Awareness API Queue.";
            }
            leaf QueueReceived {
              type uint32;
              description
                "Specifies the number of requests in the Femto
                 Awareness API Queue that have been received.
                 The counter will be reset whenever the device
                 reboots or the {{param|#.Enable}} parameter is
                 set to {{true}}.";
            }
            leaf QueueDiscarded {
              type uint32;
              description
                "Specifies the number of requests in the Femto
                 Awareness API Queue that have been discarded.
                 The counter will be reset whenever the device
                 reboots or the {{param|#.Enable}} parameter is
                 set to {{true}}.";
            }
          }

          container SMS {
            config false;
            description
              "This object contains parameters related to the
               Monitoring of the SMS API.";
            leaf APIAvailable {
              type boolean;
              description
                "Specifies whether the SMS API is currently
                 available on this device (the API could be
                 disabled or could have exhausted its
                 resources)..";
            }
            leaf APIUsers {
              type uint32 {
                range "0..255";
              }
              description
                "Specifies the current number of Applications using
                 the SMS API.";
            }
            leaf QueueState {
              type enumeration {
                enum "Disabled";
                enum "Ready";
                enum "Flushed";
              }
              description
                "Specifies the state of the SMS API Queue.";
            }
            leaf QueueNum {
              type uint32 {
                range "0..255";
              }
              description
                "Specifies the current number of requests waiting in
                 the SMS API Queue.";
            }
            leaf QueueReceived {
              type uint32;
              description
                "Specifies the number of requests in the SMS API
                 Queue that have been received.  The counter will
                 be reset whenever the device reboots or the
                 {{param|#.Enable}} parameter is set to {{true}}.";
            }
            leaf QueueDiscarded {
              type uint32;
              description
                "Specifies the number of requests in the SMS API
                 Queue that have been discarded.  The counter
                 will be reset whenever the device reboots or the
                 {{param|#.Enable}} parameter is set to {{true}}.";
            }
          }

          container MMS {
            config false;
            description
              "This object contains parameters related to the
               Monitoring of the MMS API.";
            leaf APIAvailable {
              type boolean;
              description
                "Specifies whether the MMS API is currently
                 available on this device (the API could be
                 disabled or could have exhausted its
                 resources)..";
            }
            leaf APIUsers {
              type uint32 {
                range "0..255";
              }
              description
                "Specifies the current number of Applications using
                 the MMS API.";
            }
            leaf QueueState {
              type enumeration {
                enum "Disabled";
                enum "Ready";
                enum "Flushed";
              }
              description
                "Specifies the state of the MMS API Queue.";
            }
            leaf QueueNum {
              type uint32 {
                range "0..255";
              }
              description
                "Specifies the current number of requests waiting in
                 the MMS API Queue.";
            }
            leaf QueueReceived {
              type uint32;
              description
                "Specifies the number of requests in the MMS API
                 Queue that have been received.  The counter will
                 be reset whenever the device reboots or the
                 {{param|#.Enable}} parameter is set to {{true}}.";
            }
            leaf QueueDiscarded {
              type uint32;
              description
                "Specifies the number of requests in the MMS API
                 Queue that have been discarded.  The counter
                 will be reset whenever the device reboots or the
                 {{param|#.Enable}} parameter is set to {{true}}.";
            }
          }

          container TerminalLocation {
            config false;
            description
              "This object contains parameters related to the
               Monitoring of the TerminalLocation API.";
            leaf APIAvailable {
              type boolean;
              description
                "Specifies whether the TerminalLocation API is
                 currently available on this device (the API
                 could be disabled or could have exhausted its
                 resources)..";
            }
            leaf APIUsers {
              type uint32 {
                range "0..255";
              }
              description
                "Specifies the current number of Applications using
                 the Terminal Location API.";
            }
            leaf QueueState {
              type enumeration {
                enum "Disabled";
                enum "Ready";
                enum "Flushed";
              }
              description
                "Specifies the state of the Terminal Location API
                 Queue.";
            }
            leaf QueueNum {
              type uint32 {
                range "0..255";
              }
              description
                "Specifies the current number of requests waiting in
                 the Terminal Location API Queue.";
            }
            leaf QueueReceived {
              type uint32;
              description
                "Specifies the number of requests in the Terminal
                 Location API Queue that have been received.  The
                 counter will be reset whenever the device
                 reboots or the {{param|#.Enable}} parameter is
                 set to {{true}}.";
            }
            leaf QueueDiscarded {
              type uint32;
              description
                "Specifies the number of requests in the Terminal
                 Location API Queue that have been discarded.
                 The counter will be reset whenever the device
                 reboots or the {{param|#.Enable}} parameter is
                 set to {{true}}.";
            }
          }
        }
      }
    }

    container BulkData {
      description
        "Bulk Data utilizes various solutions (e.g., IPDR, HTTP) to
         collect data from devices and transfer the data to a
         collection server.
      
         The IPDR solution is based on a service specification
         described in {{bibref|TR-232}}.
      
         The HTTP solution is based on transfer mechanisms
         described in {{bibref|TR-157a5}}.
      
         The Bulk Data Collection Profiles are measured over a
         reporting interval (which can be aligned with absolute
         time) and are made available to the collection server.
      
         This object provides bulk data collection capabilities
         and global collection settings that affect the entire
         device.";
      leaf Enable {
        type boolean;
        description
          "Enables or disables all collection profiles.
        
           If {{false}}, bulk data will not be collected or
           reported.";
      }
      leaf Status {
        type enumeration {
          enum "Enabled";
          enum "Disabled";
          enum "Error";
        }
        config false;
        description
          "Indicates the status of the Bulk Data Collection
           mechanism.";
      }
      leaf MinReportingInterval {
        type uint32;
        config false;
        description
          "Minimum reporting interval in {{units}} that the CPE is
           capable of supporting.
        
           A value of 0 indicates no minimum reporting interval.";
      }
      leaf Protocols {
        type enumeration {
          enum "Streaming";
          enum "File";
          enum "HTTP";
        }
        config false;
        description
          "Represents the IPDR and transport protocols that this
           device is capable of supporting.";
      }
      leaf EncodingTypes {
        type enumeration {
          enum "XML";
          enum "XDR";
          enum "CSV";
          enum "JSON";
        }
        config false;
        description
          "Represents the Encoding Types for the protocols that this
           device is capable of supporting.";
      }
      leaf ParameterWildCardSupported {
        type boolean;
        config false;
        description
          "When {{true}}, the Device supports the use of wildcards
           to determine the parameters that are reported using a
           Profile.";
      }
      leaf MaxNumberOfProfiles {
        type int32 {
          range "-1..max";
        }
        config false;
        description
          "The maximum number of profiles that can exist at any
           given time.  Specifically, the maximum number of
           {{object|Profile.{i}.}} instances that the ACS can
           create.
        
           If the value of this parameter is -1, then it means
           that the CPE doesn't have a limit to the number of
           profiles that can exist.";
      }
      leaf MaxNumberOfParameterReferences {
        type int32 {
          range "-1..max";
        }
        config false;
        description
          "The maximum number of parameters that can be referenced
           via the bulk data collection mechanism.  Specifically,
           the maximum number of parameters that can be
           referenced via
           {{param|Profile.{i}.Parameter.{i}.Reference}} across
           all Profile and Parameter instances (including the
           expansion of partial paths within the Reference
           parameter).
        
           If the value of this parameter is -1, then it means
           that the CPE doesn't have a limit to the number of
           parameter that can be referenced via the bulk data
           collection mechanism.";
      }

      list Profile {
        key "Alias";
        description
          "A set of Bulk Data Collection profiles.
        
           Each profile represents a bulk data report, including
           its own timing configuration, communications
           configuration, and set of parameters.  This allows the
           ACS to configure multiple reports to be generated at
           different times for different sets of data.";
        leaf Enable {
          type boolean;
          default "false";
          description
            "Enables or disables this specific bulk data profile.
          
             If {{false}}, this profile will not be collected or
             reported.";
        }
        leaf Protocol {
          type string;
          description
            "The Bulk Data Protocol being used for this collection
             profile.";
        }
        leaf EncodingType {
          type string;
          description
            "The Bulk Data encoding type being used for this
             collection profile.";
        }
        leaf NumberOfRetainedFailedReports {
          type int32 {
            range "-1..max";
          }
          default "0";
          description
            "The number of reports to be retained and be transmitted
             within the current reporting interval defined by the
             {{param|ReportingInterval}} parameter.
          
             If the value of the {{param|EncodingType}} parameter
             is modified any outstanding failed reports are
             deleted.
          
             If the CPE cannot retain the number of failed
             reports from previous reporting intervals while
             transmitting the report of the current reporting
             interval, then the oldest failed reports are deleted
             until the CPE is able to transmit the report from
             the current reporting interval.
          
             A value of 0 indicates that failed reports are not
             to be retained for transmission in the next
             reporting interval.
          
             A value of -1 indicates that the CPE will retain as
             many failed reports as possible,";
        }
        leaf ReportingInterval {
          type uint32 {
            range "1..max";
          }
          default "86400";
          description
            "The reporting interval in {{units}}.  Each report is
             generated based on this interval and
             {{param|TimeReference}}.
          
             The CPE MAY reject a request to set {{param}} to
             less than {{param|#.MinReportingInterval}}.
          
             Reporting intervals MUST begin every {{param}}
             {{units}}.
          
             If {{param}} is changed while collection is enabled,
             the first reporting interval begins immediately.
          
             For example, if {{param}} is 86400 (a day) and if
             {{param|TimeReference}} is set to UTC midnight on
             some day (in the past, present, or future) then the
             CPE will generate (and transmit, if the
             {{param|Protocol}} parameter is set to
             {{enum|Streaming|#.Protocols}}) its report at
             midnight every 24 hours.";
        }
        leaf TimeReference {
          type yang:date-and-time;
          default "0001-01-01T00:00:00Z";
          description
            "An absolute time reference in UTC to determine when
             will be transmitted.  Each reporting interval MUST
             complete at this reference time plus or minus an
             integer multiple of {{param|ReportingInterval}},
             unless unable to due to higher prioritized
             operations.
          
             {{param}} is used only to set the \"phase\" of the
             reporting intervals.  The actual value of {{param}}
             can be arbitrarily far into the past or future.
          
             If {{param}} is changed while collection of bulk
             data is enabled, the first reporting interval begins
             immediately.
          
             The Unknown Time value as defined in
             {{bibref|TR-106a2}} indicates that no particular
             time reference is specified.  That is, the CPE MAY
             locally choose the time reference, and is required
             only to adhere to the specified reporting intervals.
          
             If absolute time is not available to the CPE, its
             reporting interval behavior MUST be the same as if
             the {{param}} parameter was set to the Unknown Time
             value.
          
             For example, if {{param|ReportingInterval}} is 86400
             (a day) and if {{param}} is set to UTC midnight on
             some day (in the past, present, or future) then the
             CPE will generate (and transmit, if in a \"ITPush\"
             mode) its report at midnight every 24 hours.
          
             Note that, if {{param}} is set to a time other than
             the Unknown Time, the first reporting interval
             (which has to begin immediately) will almost
             certainly be shorter than
             {{param|ReportingInterval}}).  This is why {{param}}
             is defined in terms of when reporting intervals
             complete rather than start.";
        }
        leaf StreamingHost {
          type string {
            length "0..256";
          }
          description
            "This is the host name or IP Address of the IPDR
             Collector to be used by the CPE to stream bulk data
             records if this collection profile is configured for
             the IPDR Streaming Protocol {{bibref|IPDR-SP}} (the
             {{param|Protocol}} parameter has a value of
             {{enum|Streaming|#.Protocols}}).";
        }
        leaf StreamingPort {
          type uint32 {
            range "0..65535";
          }
          default "4737";
          description
            "This is the port number of the IPDR Collector to be
             used by the CPE to stream bulk data records if this
             collection profile is configured for the IPDR
             Streaming Protocol {{bibref|IPDR-SP}} (the
             {{param|Protocol}} parameter has a value of
             {{enum|Streaming|#.Protocols}}).";
        }
        leaf StreamingSessionID {
          type uint32 {
            range "48..57 | 65..90";
          }
          description
            "This is the unique identification of an IPDR Session to
             be used when this collection profile is configured
             for the IPDR Streaming Protocol {{bibref|IPDR-SP}}
             (the {{param|Protocol}} parameter has a value of
             {{enum|Streaming|#.Protocols}}).
          
             An ACS MUST NOT configure multiple IPDR Streaming
             Protocol collection profiles with the same
             {{param}}.  Doing so MUST cause the CPE to fail the
             SetParameterValues.
          
             Within the IPDR Streaming Protocol specification the
             Session ID has a type of a single 'char', but we are
             restricting the range even further (ASCII values of
             '0' - '9' and 'A' - 'Z'.";
        }
        leaf FileTransferURL {
          type string {
            length "0..256";
          }
          description
            "This is the URL within the CPE that is used by an IPDR
             Collector to retrieve the IPDRDocs when this
             collection profile is configured for the IPDR File
             Transfer Protocol {{bibref|IPDR-FTP}} (the
             {{param|Protocol}} parameter has a value of
             {{enum|File|#.Protocols}}).";
        }
        leaf FileTransferUsername {
          type string {
            length "0..64";
          }
          description
            "Username used for authentication of the
             {{param|FileTransferURL}}.
          
             This is the {{param}} that the IPDR Collector uses
             to access the CPE when this collection profile is
             configured for the IPDR File Transfer Protocol
             {{bibref|IPDR-FTP}} (the {{param|Protocol}}
             parameter has a value of {{enum|File|#.Protocols}}).";
        }
        leaf FileTransferPassword {
          type string {
            length "0..64";
          }
          description
            "Password used for authentication of the
             {{param|FileTransferURL}}.
          
             This is the {{param}} that the IPDR Collector uses
             to access the CPE when this collection profile is
             configured for the IPDR File Transfer Protocol
             {{bibref|IPDR-FTP}} (the {{param|Protocol}}
             parameter has a value of {{enum|File|#.Protocols}}).";
        }
        leaf ControlFileFormat {
          type string {
            length "0..128";
          }
          description
            "If this collection profile is configured for the IPDR
             File Transfer Protocol {{bibref|IPDR-FTP}} (the
             {{param|Protocol}} parameter has a value of
             {{enum|File|#.Protocols}}) then the control file
             names will be of the following format:
          
             :
             <ControlFilePrefix>_<ControlFilePolicy>.<ControlFileSuffix>
          
             Where the following rules apply:
          
             * ControlFilePrefix MUST NOT contain an underscore
             '_' or any other character not suitable for a file
             name.
          
             * ControlFilePolicy MUST contain one or more 'N'
             characters, where the number of 'N' characters
             denotes the number of digits in the sequence number,
             including leading zeros as necessary to match the
             number of 'N' characters.
          
             * ControlFileSuffix is a file extension.
          
             For example, BulkData_NNNN.log where \"BulkData\"
             would be the prefix, \"NNNN\" would be the policy,
             and \"log\" would be the suffix.  Files adhering to
             this file format would look like: BulkData_0000.log,
             BulkData_0001.log, etc.";
        }

        list Parameter {
          description
            "Bulk data parameter table.
          
             Each entry in this table represents a parameter (or
             set of parameters if a partial path is provided) to
             be collected and reported.";
          leaf Reference {
            type string {
              length "0..256";
            }
            default "";
            description
              "Represents the parameter(s) that are part of this
               Bulk Data collection profile.  The value MUST be a
               path name of a parameter or an object instance.
            
               When the {{param|##.ParameterWildCardSupported}}
               parameter has a value of {{true}}, patterns for
               object instances identifiers are permitted with
               wildcards (an \"*\" character) in place of Object
               Instance Identifiers; any attempt to set the value
               otherwise MUST be rejected by the CPE.
            
               In the case where a partial parameter path is
               specified sub-objects of the resolved pattern and
               contained parameters will be part of the bulk data
               collected and reported.  If the path name refers
               to an object then it MUST end with a '.'.";
          }
          leaf Name {
            type string {
              length "0..64";
            }
            description
              "Name of the parameter in the report body.
            
               If the value of this parameter is an {{empty}},
               then the value of the name of the parameter uses
               the name of the parameter in the
               {{param|Reference}} parameter.
            
               The content of this value is only valid when the
               Reference parameter is a fully qualified parameter
               name.  The use of this parameter is not valid when
               the {{param|Reference}} parameter uses wildcards
               or a partial parameter path.";
          }
        }

        container CSVEncoding {
          description
            "This object defines the properties to be used when
             encoding the data using CSV encoding.";
          leaf FieldSeparator {
            type string;
            default ",";
            description
              "HTML encoded field separator to use when encoding CSV
               file.  Default value is the HTML encoded comma
               character.";
          }
          leaf RowSeparator {
            type string;
            default "CRLF";
            description
              "HTML encoded row separator to use when encoding CSV
               file.  Default value is the HTML encoded carriage
               return line feed characters (CRLF).";
          }
          leaf EscapeCharacter {
            type string;
            description
              "HTML encoded escapte separator to use when encoding
               CSV file.  Default value is the HTML encoded
               double quote character.";
          }
          leaf ReportFormat {
            type enumeration {
              enum "ParameterPerRow";
              enum "ParameterPerColumn";
              enum "SchemaDefined";
            }
            description
              "This parameter describes the formatting used for
               reports defined by this profile as described in
               {{bibref|TR-157a5}}.";
          }
          leaf ReportSchema {
            type string {
              length "0..1024";
            }
            default "";
            description
              "When the value of the {{param|ReportFormat}}
               parameter is {{enum|SchemaDefined|ReportFormat}},
               then the value of this parameter represents the
               URI ({{bibref|RFC3986}}) that defines the schema
               used to interpret the content of the report and
               {{empty}} indicates that the content of the report
               is implementation specific.";
          }
          leaf RowTimestamp {
            type enumeration {
              enum "Unix-Epoch";
              enum "ISO-8601";
              enum "None";
            }
            description
              "The timestamp of when the data is collected to be
               inserted into the row.";
          }
        }

        container JSONEncoding {
          description
            "This object defines the properties to be used when
             encoding the data using JSON encoding.";
          leaf ReportFormat {
            type enumeration {
              enum "ObjectHierarchy";
              enum "NameValuePair";
              enum "SchemaDefined";
            }
            description
              "This parameter describes the formatting used for the
               report as described in {{bibref|TR-157a5}}.";
          }
          leaf ReportSchema {
            type string {
              length "0..1024";
            }
            default "";
            description
              "When the value of the {{param|ReportFormat}}
               parameter is {{enum|SchemaDefined|ReportFormat}},
               then the value of this parameter represents the
               URI ({{bibref|RFC3986}}) that defines the schema
               used to interpret the content of the report and
               {{empty}} indicates that the content of the report
               is implementation specific.";
          }
          leaf ReportTimestamp {
            type enumeration {
              enum "Unix-Epoch";
              enum "ISO-8601";
              enum "None";
            }
            description
              "The timestamp of when the data is collected to be
               inserted as a JSON Object named \"CollectionTime\"
               as described in {{bibref|TR-157a5}}.";
          }
        }

        container HTTP {
          description
            "This object defines the properties to be used when
             transporting bulk data using the HTTP/S protocol.
             This object is used when the {{param|#.Protocol}}
             parameter has a value of {{enum|HTTP|##.Protocols}}.";
          leaf URL {
            type string {
              length "0..1024";
            }
            description
              "The URL, as defined in {{bibref|RFC3986}}, for the
               collection server to receive the Bulk Data
               transmitted by the CPE.";
          }
          leaf Username {
            type string {
              length "0..256";
            }
            description
              "Username used to authenticate the CPE when making a
               connection to the collection server.";
          }
          leaf Password {
            type string {
              length "0..256";
            }
            description
              "Password used to authenticate the CPE when making a
               connection to the collection server.";
          }
          leaf CompressionSupported {
            type enumeration {
              enum "GZIP";
              enum "Compress";
              enum "Deflate";
            }
            config false;
            description
              "Indicates the HTTP Compression mechanism(s) supported
               by this CPE for the purposes of transfering bulk
               data.
            
               Vendors can extend the enumerated values with
               vendor specific extensions, in which case the
               rules outlined in {{bibref|TR-106a7|Section 3.3}}
               MUST be adhered to.";
          }
          leaf Compression {
            type string;
            description
              "The value of this parameter represents the HTTP
               Compression mechanism to be used by the CPE when
               transferring data to the collection server.";
          }
          leaf TransferCodingSupported {
            type enumeration {
              enum "Chunked";
            }
            config false;
            description
              "Indicates the HTTP transfer-coding mechanism(s)
               supported by this CPE for the purposes of
               transfering bulk data.
            
               Vendors can extend the enumerated values with
               vendor specific extensions, in which case the
               rules outlined in {{bibref|TR-106a7|Section 3.3}}
               MUST be adhered to.";
          }
          leaf TransferCoding {
            type string;
            default "Chunked";
            description
              "The value of this parameter represents the HTTP
               transfer-coding mechanism to be used by the CPE
               when transferring data to the collection server.";
          }
          leaf MethodSupported {
            type enumeration {
              enum "Post";
              enum "Put";
            }
            config false;
            description
              "Indicates the HTTP method(s) supported by this CPE
               for the purposes of transfering bulk data.
            
               Vendors can extend the enumerated values with
               vendor specific extensions, in which case the
               rules outlined in {{bibref|TR-106a7|Section 3.3}}
               MUST be adhered to.";
          }
          leaf Method {
            type string;
            default "Post";
            description
              "The value of this parameter represents the HTTP
               method to be used by the CPE when transferring
               data to the collection server.";
          }
          leaf UseDateHeader {
            type boolean;
            default "true";
            description
              "When {{true}}, the CPE encodes the HTTP Date Header
               {{bibref|RFC2616|Section 14.18}} in the HTTP
               client request.";
          }
          leaf RetryEnable {
            type boolean;
            default "false";
            description
              "When {{true}}, the CPE retries unsuccessful attempts
               to transfer data.";
          }
          leaf RetryMinimumWaitInterval {
            type uint32 {
              range "1..65535";
            }
            default "5";
            description
              "Configures the data transfer retry wait interval, in
               seconds, as specified in {{bibref|TR-157|Appendix
               I}}.
            
               The device MUST use a random value between
               {{param}} and ({{param}} *
               {{param|RetryIntervalMultiplier}} / 1000) as the
               first retry wait interval.  Other values in the
               retry pattern MUST be calculated using this value
               as a starting point.";
          }
          leaf RetryIntervalMultiplier {
            type uint32 {
              range "1000..65535";
            }
            default "2000";
            description
              "Configures the retry interval multiplier as specified
               in {{bibref|TR-157|Appendix I}}.
            
               This value is expressed in units of 0.001.  Hence
               the values of the multiplier range between 1.000
               and 65.535.
            
               The device MUST use a random value between
               {{param|RetryMinimumWaitInterval}} and
               ({{param|RetryMinimumWaitInterval}} * {{param}} /
               1000) as the first retry wait interval.  Other
               values in the retry pattern MUST be calculated
               using this value as a starting point.";
          }

          list RequestURIParameter {
            description
              "This object represents an instance of a parameter to
               be used in the report header used as part of the
               HTTP Request-URI transmitted by the CPE to the
               collection server using the Request-URI.
            
               For example, the HTTP request from the CPE will
               look like this:
            
               POST https://bdc.acme.com/csv1?oui=X&sn=Y&pc=Z";
            leaf Name {
              type string {
                length "0..64";
              }
              description
                "Name of the Request-URI parameter.
              
                 If the value of this parameter is an {{empty}},
                 then the value of the name of the header
                 parameter uses the name of the parameter in the
                 {{param|Reference}} parameter.";
            }
            leaf Reference {
              type string {
                length "0..256";
              }
              default "";
              description
                "{{reference|the Request-URI parameter}}";
            }
          }
        }
      }
    }

    container XMPP {
      description
        "The {{object}} represents the XMPP capabilities of the
         device as described in {{bibref|TR-069a5|Appendix III}}.";

      list Connection {
        key "Username Domain Resource";
        description
          "The {{object}} represents a XMPP connection between the
           device and a server.  The {{param|Username}},
           {{param|Domain}} and {{param|Resource}} comprise the
           full identity (JabberID) of this {{object}} for this
           device.";
        leaf Enable {
          type boolean;
          default "false";
          description
            "Enables or disables this {{object}}.
          
             This parameter is based on ''ifAdminStatus'' from
             {{bibref|RFC2863}}.";
        }
        leaf Username {
          type string {
            length "0..256";
          }
          description
            "The proposed local-part of the Jabber ID of this
             {{object}}, and the value to be used to authenticate
             this {{object}} when making a connection to the
             Server using the procedure outlined in
             {{bibref|RFC6120|Section 6}}.";
        }
        leaf Password {
          type string {
            length "0..256";
          }
          description
            "Password used to authenticate this {{object}} when
             making a connection to the {{object|Server}} using
             the procedure outlined in {{bibref|RFC6120|Section
             6}}.
          
             Note that on a factory reset of the CPE, the value
             of this parameter might be reset to its factory
             value.  If an ACS modifies the value of this
             parameter, it SHOULD be prepared to accommodate the
             situation that the original value is restored as the
             result of a factory reset.";
        }
        leaf Domain {
          type string {
            length "0..64";
          }
          description
            "The proposed domain-part of the Jabber ID of this
             {{object}}.";
        }
        leaf Resource {
          type string {
            length "0..64";
          }
          description
            "The proposed resource-part of the Jabber ID of this
             {{object}}.";
        }
        leaf JabberID {
          type string;
          config false;
          description
            "The complete Jabber ID as determined by the first-hop
             XMPP server at time of connection establishment.
             This Jabber ID will usually be the standard
             concatentation of the local-part (Username),
             domain-part (Domain), and resource-part (Resource)
             as defined in {{bibref|RFC6120|Section 2.1}}
             (local-part@domain-part/resource-part), but since
             the Jabber ID is owned by the first-hop XMPP Server
             there are cases where the value will be different.";
        }
        leaf Status {
          type enumeration {
            enum "Enabled";
            enum "Disabled";
            enum "Unknown";
            enum "Dormant";
            enum "Connecting";
            enum "ServerNotPresent";
            enum "Error_Misconfigured";
            enum "Error_AuthenticationFailure";
            enum "Error";
          }
          config false;
          description
            "The current operational state of this {{object}} (see
             {{bibref|TR-181i2|Section 4.2.2}}).  {{enum}}
          
             When {{param|Enable}} is {{false}} then {{param}}
             SHOULD normally be {{enum|Disabled}} or
             {{enum|Error}} if there is a fault condition on the
             interface).
          
             When {{param|Enable}} is changed to {{true}} then
             {{param}} SHOULD change to {{enum|Enabled}} if and
             only if the interface is able to transmit and
             receive PDUs; it SHOULD change to {{enum|Dormant}}
             if and only if the interface is operable but is
             waiting for external actions before it can transmit
             and receive network traffic (and subsequently change
             to {{enum|Enabled}} if still operable when the
             expected actions have completed); it SHOULD change
             to {{enum|Unknown}} if the state of the interface
             can not be determined for some reason.";
        }
        leaf LastChangeDate {
          type yang:date-and-time;
          config false;
          description
            "The date and time at which this {{object}} entered into
             its current operational state.";
        }
        leaf ServerConnectAlgorithm {
          type enumeration {
            enum "DNS-SRV";
            enum "ServerTable";
          }
          default "DNS-SRV";
          description
            "The algorithm the {{object}} uses when connecting with
             the associated lists of servers.  {{enum}}";
        }
        leaf KeepAliveInterval {
          type int64 {
            range "-1..max";
          }
          default "-1";
          description
            "The number of {{units}} that keep alive events as
             specified in {{bibref|RFC6120|Section 4.6.1}} are
             sent by this {{object}}.
          
             A value of 0 disables the keep alive functionality.
             A value of -1 indicates that the keep alive interval
             is a vendor specific implementation.
          
             {{bibref|RFC6120|Section 4.6.4}} recommends not
             checking more frequently than every 5 minutes (or
             300 {{units}}).";
        }
        leaf ServerConnectAttempts {
          type uint32;
          default "16";
          description
            "The number of times that this {{object}} attempts to
             connect to a given IP address before moving on to
             the current server's next IP address, or to the next
             server if the current server has no more IP
             addresses.
          
             If {{param}}, {{param|ServerRetryInitialInterval}},
             {{param|ServerRetryIntervalMultiplier}} and
             {{param|ServerRetryMaxInterval}} all have their
             default values, the maximum reconnection wait
             intervals, in ''minutes'', will be ''{1, 2, 4, 8,
             16, 32, 64, 128, 256, 512, 512, 512, 512, 512,
             512}''.  After the initial attempt there are 15
             further attempts, making a total of 16.  The maximum
             reconnection wait interval is reached on the 10th
             retry, i.e.  the 11th attempt.
          
             NOTE: If this {{object}} fails to connect to any of
             the servers' IP addresses, fallback behavior SHOULD
             be as specified in {{bibref|RFC6120|Section 3.2}}.
          
             NOTE: If the value of this parameter is 0, server
             connection and reconnection behavior is
             implementation-dependent.";
        }
        leaf ServerRetryInitialInterval {
          type uint32 {
            range "1..65535";
          }
          default "60";
          description
            "The maximum first reconnection wait interval, in
             {{units}}, as specified in {{bibref|TR-069a5|Annex K
             XMPP Connection Request}}.
          
             The Device MUST use a random value between ''0'' and
             {{param}} as the first reconnection wait interval.
          
             NOTE: If the value of the
             {{param|ServerConnectAttempts}} parameter is 0, the
             value of this parameter is ignored.";
        }
        leaf ServerRetryIntervalMultiplier {
          type uint32 {
            range "1000..65535";
          }
          default "2000";
          description
            "The reconnection interval multiplier as specified in
             {{bibref|TR-069a5|Annex K XMPP Connection Request}}.
             This value is expressed in units of 0.001.  Hence
             the values of the multiplier range between 1.000 and
             65.535.
          
             For the ''n''th reconnection wait interval, the
             Device MUST use a random value, in ''seconds'',
             between ''0'' and
             {{param|ServerRetryInitialInterval}} * ({{param}} /
             1000) ** (''n'' - ''1'').
          
             NOTE: If the value of the
             {{param|ServerConnectAttempts}} parameter is 0, the
             value of this parameter is ignored.";
        }
        leaf ServerRetryMaxInterval {
          type uint32 {
            range "1..max";
          }
          default "30720";
          description
            "The maximum reconnection wait interval, in {{units}}.
          
             If the ''n''th reconnection wait interval calculated
             from {{param|ServerRetryInitialInterval}} and
             {{param|ServerRetryIntervalMultiplier}} exceeds the
             value of this parameter, then the Device MUST use
             the value of this parameter as the next reconnection
             wait interval.
          
             NOTE: If the value of the
             {{param|ServerConnectAttempts}} parameter is 0, the
             value of this parameter is ignored.";
        }
        leaf UseTLS {
          type boolean;
          default "false";
          description
            "This parameter allows an ACS to configure whether or
             not this XMPP Connection is required to use TLS
             independent of whether or not the XMPP Server that
             is being connected to is configured for TLS
             \"mandatory-to-negotiate\".
          
             If the value of {{param}} is {{true}} then the CPE
             will initiate TLS negotiation if not required to by
             the XMPP Server.
          
             If the value of {{param}} is {{false}} then the CPE
             will not initiate TLS negotiation if not required to
             by the XMPP Server.";
        }
        leaf TLSEstablished {
          type boolean;
          config false;
          description
            "This parameter represents the TLS state of this XMPP
             Connection.
          
             If this XMPP Connection is established and is
             secured by TLS then the value of this parameter is
             {{true}}.
          
             If this XMPP Connection is either not established or
             established but not secured by TLS then the value of
             this parameter is {{false}}.";
        }

        list Server {
          key "ServerAddress Port";
          description
            "The {{object}} represents an XMPP server to be used for
             a {{object|##.Connection}}.
          
             This table is only relevant when
             {{param|##.Connection.{i}.ServerConnectAlgorithm}}
             is set to
             {{enum|ServerTable|##.Connection.{i}.ServerConnectAlgorithm}}.
             If
             {{param|##.Connection.{i}.ServerConnectAlgorithm}}
             is set to
             {{enum|DNS-SRV|##.Connection.{i}.ServerConnectAlgorithm}}
             then any instances of this table are ignored by this
             {{object|##.Connection}}.";
          leaf Enable {
            type boolean;
            default "false";
            description
              "Enables or disables this {{object}}.
            
               This parameter is based on ''ifAdminStatus'' from
               {{bibref|RFC2863}}.";
          }
          leaf Priority {
            type uint32 {
              range "0..65535";
            }
            description
              "The priority of this {{object}} that is used by the
               {{object|##.Connection}} when determining the
               {{object}} to connect.  The
               {{object|##.Connection}} MUST contact the
               {{object}} with the lowest-numbered priority that
               the {{object|##.Connection}} can reach as defined
               in {{bibref|RFC2782}}.  The selection of
               {{object}}s with the same {{param}} value utilizes
               the {{param|Weight}} parameter to determine which
               {{object}} is selected by the
               {{object|##.Connection}}.";
          }
          leaf Weight {
            type int64 {
              range "-1..65535";
            }
            description
              "This parameter specifies a relative weight for
               entries with the same {{param|Priority}}.  The
               mechanism is defined in {{bibref|RFC2782}}.  A
               value of -1 indicates that the implementation of
               this parameter is specific to the Vendor.";
          }
          leaf ServerAddress {
            type string {
              length "0..256";
            }
            description
              "Fully Qualified Domain Name (FQDN) or IP address of
               the XMPP server for this {{object|##.Connection}}.
            
               If the value of this Parameter is a FQDN that
               resolves to multiple addresses then each address
               SHOULD be attemtped (in an implemnetation-specific
               order) until a connection can be made or all
               addresses are exhausted, in which case the next
               {{object}} instance (based on {{param|Priority}}
               and {{param|Weight}}) SHOULD be used.";
          }
          leaf Port {
            type uint32 {
              range "0..65535";
            }
            default "5222";
            description
              "Port number of the XMPP server for this
               {{object|##.Connection}}.";
          }
        }

        container Stats {
          config false;
          description
            "XMPP Connection statistics information for this
             resource.";
          leaf ReceivedMessages {
            type uint32;
            default "0";
            description
              "The number of XMPP stanzas (iq, presence, or message)
               that have been received on this
               {{object|##.Connection}}.";
          }
          leaf TransmittedMessages {
            type uint32;
            default "0";
            description
              "The number of XMPP stanzas (iq, presence, or message)
               that have been transmitted by this
               {{object|##.Connection}}.";
          }
          leaf ReceivedErrorMessages {
            type uint32;
            default "0";
            description
              "The number of XMPP stanzas (iq, presence, or message)
               that have been received on this
               {{object|##.Connection}} where the type attribute
               had a value of \"error\".";
          }
          leaf TransmittedErrorMessages {
            type uint32;
            default "0";
            description
              "The number of XMPP stanzas (iq, presence, or message)
               that have been transmitted by this
               {{object|##.Connection}} where the type attribute
               had a value of \"error\".";
          }
        }
      }
    }

    container IEEE1905 {
      description
        "This object represents the management functions for the
         1905 capabilities as defined in {{bibref|IEEE1905.1a}}.";
      leaf Version {
        type enumeration {
          enum "1905.1";
          enum "1905.1a";
        }
        config false;
        description
          "1905 profile version number of the AL as would be sent in
           a Higher Layer response message as defined in
           {{bibref|IEEE1905.1a|Table 6-37: 1905 profile version
           TLV}}.";
      }

      container AL {
        description
          "This object represents the management functions for the
           1905 Abstraction Layer as defined in
           {{bibref|IEEE1905.1a|Section 4.4 Abstraction Layer}}.";
        leaf IEEE1905Id {
          type types:MACAddress;
          config false;
          description
            "1905 AL MAC Address.";
        }
        leaf Status {
          type enumeration {
            enum "Disabled";
            enum "Enabled";
            enum "Error_Misconfigured";
            enum "Up";
            enum "Down";
            enum "Unknown";
            enum "Dormant";
            enum "NotPresent";
            enum "LowerLayerDown";
            enum "Error";
          }
          config false;
          description
            "The current operational state of the 1905 Abstraction
             Layer.  {{enum}}
          
             The {{enum|Error_Misconfigured}} value indicates
             that a necessary configuration value is undefined or
             invalid.
          
             The {{enum|Error}} value MAY be used by the CPE to
             indicate a locally defined error condition.";
        }
        leaf LastChange {
          type uint32;
          config false;
          description
            "This parameter is NOT RECOMMENDED to be used because
             IEEE1905 is not an interface.  The accumulated time
             in {{units}} since the 1905 Abstraction Layer
             entered its current operational state.";
        }
        leaf LowerLayers {
          type string;
          config false;
          description
            "This parameter is NOT RECOMMENDED to be used because
             IEEE1905 is not an interface.  {{list}}
             {{reference}} See {{bibref|TR-181i2|Section 4.2.1}}.";
        }
        leaf RegistrarFreqBand {
          type enumeration {
            enum "802.11 2.4 GHz";
            enum "802.11 5 GHz";
            enum "802.11 60 GHz";
          }
          config false;
          description
            "{{list}} See {{bibref|IEEE1905.1a|Table 6-25:
             SupportedFreqBand TLV}}.  {{enum}}";
        }

        list Interface {
          key "InterfaceId";
          description
            "The 1905 interface table (described in
             {{bibref|IEEE1905.1a|sub-clause 5 Abstraction Layer
             Management}}).";
          leaf InterfaceId {
            type types:MACAddress;
            config false;
            description
              "MAC Address of this interface.  This is the value of
               the intfAddress parameter defined in
               {{bibref|IEEE1905.1a|Table 5-2: intfDescriptor
               elements}}";
          }
          leaf Status {
            type enumeration {
              enum "Up";
              enum "Down";
              enum "Unknown";
              enum "Dormant";
              enum "NotPresent";
              enum "LowerLayerDown";
              enum "Error";
            }
            config false;
            description
              "This parameter is NOT RECOMMENDED to be used because
               it is not a parameter defined in a 1905 ALME
               primitive or protocol TLV.  The current
               operational state of the interface (see
               {{bibref|TR-181i2|Section 4.2.2}}).  {{enum}}
            
               It SHOULD change to {{enum|Up}} if and only if the
               interface is able to transmit and receive network
               traffic; it SHOULD normally be {{enum|Down}} when
               the interface cannot transmit and receive network
               traffic; it SHOULD change to {{enum|Dormant}} if
               and only if the interface is operable but is
               waiting for external actions before it can
               transmit and receive network traffic (and
               subsequently change to {{enum|Up}} if still
               operable when the expected actions have
               completed); it SHOULD change to
               {{enum|LowerLayerDown}} if and only if the
               interface is prevented from entering the
               {{enum|Up}} state because one or more of the
               interfaces beneath it is down; it SHOULD remain in
               the {{enum|Error}} state if there is an error or
               other fault condition detected on the interface;
               it SHOULD remain in the {{enum|NotPresent}} state
               if the interface has missing (typically hardware)
               components; it SHOULD change to {{enum|Unknown}}
               if the state of the interface can not be
               determined for some reason.
            
               This parameter is based on ''ifOperStatus'' from
               {{bibref|RFC2863}}.";
          }
          leaf LastChange {
            type uint32;
            config false;
            description
              "This parameter is NOT RECOMMENDED to be used because
               it is not a parameter defined in a 1905 ALME
               primitive or protocol TLV.  The accumulated time
               in {{units}} since the interface entered its
               current operational state.";
          }
          leaf LowerLayers {
            type string;
            config false;
            description
              "This parameter is NOT RECOMMENDED to be used because
               it is not a parameter defined in a 1905 ALME
               primitive or protocol TLV.  {{list}}
               {{reference|an interface object that is stacked
               immediately below this interface object}} See
               {{bibref|TR-181i2|Section 4.2.1}}.";
          }
          leaf InterfaceStackReference {
            type string {
              length "0..256";
            }
            config false;
            description
              "Path name of an interface object described by this
               1905 {{object}}.  Referenced interface object MUST
               have a MACAddress and the InterfaceId MUST be the
               same as the interface object MACAddress.";
          }
          leaf MediaType {
            type enumeration {
              enum "IEEE 802.3u";
              enum "IEEE 802.3ab";
              enum "IEEE 802.11b";
              enum "IEEE 802.11g";
              enum "IEEE 802.11a";
              enum "IEEE 802.11n 2.4";
              enum "IEEE 802.11n 5.0";
              enum "IEEE 802.11ac";
              enum "IEEE 802.11ad";
              enum "IEEE 802.11af";
              enum "IEEE 1901 Wavelet";
              enum "IEEE 1901 FFT";
              enum "MoCAv1.1";
              enum "Generic PHY";
            }
            config false;
            description
              "Media type of this {{object}}.  This is derived from
               the value of the intfType parameter defined in
               {{bibref|IEEE1905.1a|Tables 5.2: intfDescriptor
               elements}}.  {{enum}}";
          }
          leaf GenericPhyOUI {
            type string {
              length "6";
              pattern "[0-9A-F]{6}";
            }
            config false;
            description
              "OUI of the Generic Phy networking technology of the
               local interface that would be included in a
               Generic Phy Device Information Type TLV defined in
               {{bibref|IEEE1905.1a|Tables 6-29: Generic Phy
               Device Information type TLV}}.";
          }
          leaf GenericPhyVariant {
            type yang:hex-string {
              length "1";
            }
            config false;
            description
              "Variant Index of the Generic Phy networking
               technology of the local interface that would be
               included in a Generic Phy Device Information Type
               TLV defined in {{bibref|IEEE1905.1a|Tables 6-29:
               Generic Phy Device Information type TLV}}.";
          }
          leaf GenericPhyURL {
            type string {
              length "0..1024";
            }
            config false;
            description
              "URL to Generic Phy XML Description of the Generic Phy
               networking technology of the local interface that
               would be included in a Generic Phy Device
               Information Type TLV defined in
               {{bibref|IEEE1905.1a|Table 6-29: Generic Phy
               device information type TLV}}.";
          }
          leaf SetIntfPowerStateEnabled {
            type boolean;
            description
              "Enables or disables the Abstraction Layer's ability
               to set the power state for the interface.  Boolean
               can be {{true}} for \"enabled\" and {{false}} for
               \"disabled\".";
          }
          leaf PowerState {
            type enumeration {
              enum "On";
              enum "Power_Save";
              enum "Off";
              enum "Unsupported";
            }
            description
              "The Power State of this {{object}}.  This is derived
               from the value of the powerState parameter as
               defined in {{bibref|IEEE1905.1a|Tables 5.3:
               ALME-SET-INTF-PWR-STATE.request parameters and
               Table 5.7: ALME-GET-INTF-PWR-STATE.response
               parameters}}.  {{enum}}";
          }

          list VendorProperties {
            config false;
            description
              "This object defines the vendor specific properties
               (vendorSpecificInfo field) of this
               {{object|##.Interface}} as defined in
               {{bibref|IEEE1905.1a|Table 5-2: intfDescriptor
               elements}}.";
            leaf OUI {
              type string {
                length "6";
                pattern "[0-9A-F]{6}";
              }
              description
                "Organizationally unique identifier of a
                 manufacturer of this {{object|##.Interface}}.
                 Represented as a six hexadecimal-digit value
                 using all upper-case letters and including any
                 leading zeros according to
                 {{bibref|IEEE1905.1a|Table 5-20:
                 VendorSpecificInfo information element}}.
                 {{pattern}}";
            }
            leaf Information {
              type yang:hex-string {
                length "0..65535";
              }
              description
                "A hexbinary string used to to provide vendor
                 specific information about this
                 {{object|##.Interface}}.  This is the value of
                 the vendorSpecificInfo parameter defined in
                 {{bibref|IEEE1905.1a|Table 5-20:
                 VendorSpecificInfo information element}}.";
            }
          }

          list Link {
            key "InterfaceId IEEE1905Id";
            config false;
            description
              "This object defines the 1905 neighbors and link
               properties.";
            leaf InterfaceId {
              type types:MACAddress;
              description
                "MAC Address of the interface of the Neighbor for
                 this {{object}}.  This value comes from the
                 neighbor’s Topology discovery message as defined
                 in {{bibref|IEEE1905.1a|Table 6-9: MAC address
                 typeTLV}}.";
            }
            leaf IEEE1905Id {
              type types:MACAddress;
              description
                "MAC Address of the 1905 AL entity of the Neighbor
                 device on this {{object}}.  This value comes
                 from the neighbor’s Topology discovery message
                 as defined in {{bibref|IEEE1905.1a|Table 6-8: AL
                 MAC address type TLV}}.";
            }
            leaf MediaType {
              type enumeration {
                enum "IEEE 802.3u";
                enum "IEEE 802.3ab";
                enum "IEEE 802.11b";
                enum "IEEE 802.11g";
                enum "IEEE 802.11a";
                enum "IEEE 802.11n 2.4";
                enum "IEEE 802.11n 5.0";
                enum "IEEE 802.11ac";
                enum "IEEE 802.11ad";
                enum "IEEE 802.11af";
                enum "IEEE 1901 Wavelet";
                enum "IEEE 1901 FFT";
                enum "MoCAv1.1";
                enum "Generic PHY";
              }
              description
                "Media type of this {{object}}.  This value is
                 derived from the neighbor’s Topology response
                 message 1905 device information type TLV Media
                 Type field as defined in
                 {{bibref|IEEE1905.1a|Table 6-12: Media type}}.
                 {{enum}}";
            }
            leaf GenericPhyOUI {
              type string {
                length "6";
                pattern "[0-9A-F]{6}";
              }
              description
                "OUI of the Generic Phy networking technology of the
                 interface of the Neighbor for this
                 {{object|#.Link}}.  This value is from a Generic
                 Phy response message field as defined in
                 {{bibref|IEEE1905.1a|Tables 6-29: Generic Phy
                 Device Information type TLV}}.";
            }
            leaf GenericPhyVariant {
              type yang:hex-string {
                length "1";
              }
              description
                "Variant Index of the Generic Phy networking
                 technology of the interface of the Neighbor for
                 this {{object|#.Link}}.  This value is from a
                 Generic Phy response message variant index field
                 as defined in {{bibref|IEEE1905.1a|Tables 6-29:
                 Generic Phy Device Information type TLV}}.";
            }
            leaf GenericPhyURL {
              type string {
                length "0..1024";
              }
              description
                "URL to Generic Phy XML Description of the Generic
                 Phy networking technology of the interface of
                 the Neighbor for this {{object|#.Link}}.  This
                 value is from a Generic Phy response message URL
                 to Generic Phy field as defined in
                 {{bibref|IEEE1905.1a|Table 6-29: Generic Phy
                 device information type TLV}}.";
            }

            container Metric {
              description
                "This object represents the metrics for this
                 {{object|##.Link}} as defined in
                 {{bibref|IEEE1905.1a|Tables 6-18: 1905
                 transmitter link metrics and Table 6-20: 1905
                 receiver link metrics}}.";
              leaf IEEE802dot1Bridge {
                type boolean;
                description
                  "Indicates whether or not the 1905 link includes
                   one or more IEEE 802.1 bridges.  If {{false}},
                   the 1905 link does not include an IEEE 802.1
                   bridge.  If {{true}}, the 1905 link does
                   include one or more IEEE 802.1 bridges.";
              }
              leaf PacketErrors {
                type types:StatsCounter32;
                description
                  "Estimated number of lost {{units}} on the
                   transmit side of the link
                   {{bibref|IEEE1905.1a|Table 6-18: 1905
                   transmitter link metrics}} during a
                   measurement period.";
              }
              leaf PacketErrorsReceived {
                type types:StatsCounter32;
                description
                  "Estimated number of lost {{units}} on the receive
                   side of the link {{bibref|IEEE1905.1a|Table
                   6-20: 1905 receiver link metrics}} during a
                   measurement period.";
              }
              leaf TransmittedPackets {
                type types:StatsCounter32;
                description
                  "Estimated number of {{units}} sent to the
                   Neighbor on this {{object|##.Link}}, in the
                   same measurement period used to estimate
                   {{param|PacketErrors}}.";
              }
              leaf PacketsReceived {
                type types:StatsCounter32;
                description
                  "Estimated number of {{units}} received from this
                   Neighbor on this {{object|##.Link}}
                   {{bibref|IEEE1905.1a|Table 6-20: 1905 receiver
                   link metrics}}, in the same measurement period
                   used to estimate {{param|PacketErrors}}.";
              }
              leaf MACThroughputCapacity {
                type uint32;
                description
                  "The maximum MAC throughput in {{units}} between
                   this {{object|###.Interface}} and the Neighbor
                   on this {{object|##.Link}} that is estimated
                   at this {{object|###.Interface}}.";
              }
              leaf LinkAvailability {
                type uint32 {
                  range "0..100";
                }
                description
                  "The estimated average {{units}} of time that the
                   {{object|##.Link}} is available for data
                   transmissions.";
              }
              leaf PHYRate {
                type uint32;
                description
                  "The Physical Layer (PHY) rate in {{units}}
                   between this {{object|###.Interface}} and the
                   Neighbor on this {{object|##.Link}} that is
                   estimated at this {{object|###.Interface}}.";
              }
              leaf RSSI {
                type uint32 {
                  range "0..255";
                }
                description
                  "The estimated Received Signal Strength Indicator
                   (RSSI) ratio in {{units}} between this
                   {{object|###.Interface}} and the Neighbor on
                   this {{object|##.Link}} that is estimated at
                   the receive side of this
                   {{object|###.Interface}}.";
              }
            }
          }
        }

        container ForwardingTable {
          description
            "This object represents the rules to forward PDUs
             between interfaces within the 1905 Abstraction
             Layer.";
          leaf SetForwardingEnabled {
            type boolean;
            description
              "Abstraction Layer ability to set, modify, and remove
               {{object|ForwardingRule}} entries for interfaces.
               Boolean can be {{true}} for \"enabled\" and
               {{false}} for \"disabled\".";
          }

          list ForwardingRule {
            description
              "The 1905 fowarding rule for the
               ALME-SET-FWD-RULE.request and
               ALME-GET-FWD-RULES.response with classification
               criteria as defined in {{bibref|IEEE1905.1a|Table
               5-9: ClassificationSet elements}}.";
            leaf InterfaceList {
              type string {
                length "0..256";
              }
              default "";
              description
                "The list of interfaces to which a frame satisfying
                 the following classification criteria should be
                 forwarded (intfAddressList parameter as defined
                 in {{bibref|IEEE1905.1a|Table 5-8:
                 ALME-SET-FWD-RULE.request parameters and Table
                 5-12: fwdRuleList elements}}).  {{list}} Each
                 list item MUST be the path name of an object,
                 which MUST be a row of an
                 {{object|##.Interface}} object.  If the
                 referenced item is deleted, the corresponding
                 item MUST be removed from the list.
                 {{noreference}}";
            }
            leaf MACDestinationAddress {
              type types:MACAddress;
              description
                "Classification criterion.
              
                 The destination MAC address.";
            }
            leaf MACDestinationAddressFlag {
              type boolean;
              default "false";
              description
                "If {{false}}, the classification criterion
                 {{param|MACDestinationAddress}} is ignored.  If
                 {{true}}, the classification criterion
                 {{param|MACDestinationAddress}} is used.";
            }
            leaf MACSourceAddress {
              type types:MACAddress;
              description
                "Classification criterion.
              
                 The source MAC address.";
            }
            leaf MACSourceAddressFlag {
              type boolean;
              default "false";
              description
                "If {{false}}, the classification criterion
                 {{param|MACSourceAddress}} is ignored.  If
                 {{true}}, the classification criterion
                 {{param|MACSourceAddress}} is used.";
            }
            leaf EtherType {
              type uint32;
              description
                "Classification criterion.
              
                 Ether Type Field in a frame.";
            }
            leaf EtherTypeFlag {
              type boolean;
              default "false";
              description
                "If {{false}}, the classification criterion
                 {{param|EtherType}} is ignored.  If {{true}},
                 the classification {{param|EtherType}} is used.";
            }
            leaf Vid {
              type uint32 {
                range "0..4095";
              }
              description
                "Classification criterion.
              
                 IEEE 802.1Q VLAN ID in a frame.";
            }
            leaf VidFlag {
              type boolean;
              default "false";
              description
                "If {{false}}, the classification criterion
                 {{param|Vid}} is ignored.  If {{true}}, the
                 classification {{param|Vid}} is used.";
            }
            leaf PCP {
              type uint32 {
                range "0..7";
              }
              description
                "Classification criterion.
              
                 IEEE 802.1Q Priority Code Point field.";
            }
            leaf PCPFlag {
              type boolean;
              default "false";
              description
                "If {{false}}, the classification criterion
                 {{param|PCP}} is ignored.  If {{true}}, the
                 classification {{param|PCP}} is used.";
            }
          }
        }

        container NetworkTopology {
          description
            "This object represents the 1905 Network Topology
             capabilities of this device.";
          leaf Enable {
            type boolean;
            description
              "Enables or disables the 1905 Network Topology
               reporting (via TR-069).  When {{true}}, the device
               clears and (re)populates the
               {{object|IEEE1905Device}} and {{object|ChangeLog}}
               tables.  When {{false}}, the contents of the
               {{object|IEEE1905Device}} and {{object|ChangeLog}}
               tables have no meaning.";
          }
          leaf Status {
            type enumeration {
              enum "Incomplete";
              enum "Available";
              enum "Error_Misconfigured";
            }
            config false;
            description
              "When {{param|Enable}} is set to {{true}}, this
               parameter indicates the transient phase of the
               discovery of the {{object}}.
            
               {{enum}}";
          }
          leaf MaxChangeLogEntries {
            type uint32 {
              range "1..max";
            }
            description
              "The maximum number of entries allowed in the
               {{object|ChangeLog}} table.";
          }
          leaf LastChange {
            type string {
              length "0..256";
            }
            config false;
            description
              "{{reference}} If the {{object|ChangeLog}} is modified
               the parameter is modified to reflect the last
               entry added to the {{object|ChangeLog}}.";
          }

          list ChangeLog {
            config false;
            description
              "This object represents log entries for changes in the
               1905 Network Topology.  The Change Log is a First
               In First Out queue where the oldest entries
               (defined by values of the {{param|TimeStamp}}
               parameter) are deleted once the log is full.";
            leaf TimeStamp {
              type yang:date-and-time;
              description
                "Date and Time at which the entry was added to the
                 {{object}} table.";
            }
            leaf EventType {
              type enumeration {
                enum "NewNeighbor";
                enum "LostNeighbor";
              }
              description
                "Type of event for this entry.  {{enum}}";
            }
            leaf ReporterDeviceId {
              type types:MACAddress;
              description
                "1905 AL MAC Address of device which reported the
                 change.";
            }
            leaf ReporterInterfaceId {
              type types:MACAddress;
              description
                "MAC Address of the interface of the reporting
                 device on which the change has been detected.";
            }
            leaf NeighborType {
              type enumeration {
                enum "IEEE1905";
                enum "Non-IEEE1905";
              }
              description
                "Type of Neighbor for this event.  {{enum}}";
            }
            leaf NeighborId {
              type types:MACAddress;
              description
                "MAC Address of the Neighbor of this event.  If the
                 value of the {{param|EventType}} parameter is
                 {{enum|NewNeighbor|EventType}}, then the value
                 of this parameter represents the MAC Address of
                 the new Neighbor that joined the network; if the
                 value of the {{param|EventType}} parameter is
                 {{enum|LostNeighbor|EventType}}, then the value
                 of this parameter represents the MAC Address of
                 the Neighbor that left the network.
              
                 If value of the {{param|NeighborType}} parameter
                 is {{enum|IEEE1905|NeighborType}}, then the
                 value of this parameter is the 1905 AL MAC
                 Address of the Neighbor.";
            }
          }

          list IEEE1905Device {
            key "IEEE1905Id";
            config false;
            description
              "This object represents an instance of discovered 1905
               Devices in the network (received Topology
               discovery message as defined in
               {{bibref|IEEE1905.1a|Clause 6.3.1}}).";
            leaf IEEE1905Id {
              type types:MACAddress;
              description
                "1905 AL MAC Address.";
            }
            leaf Version {
              type enumeration {
                enum "1905.1";
                enum "1905.1a";
              }
              description
                "1905 profile version number in Higher Layer
                 Response message as defined in
                 {{bibref|IEEE1905.1a|Table 6-37: 1905 profile
                 version TLV}}.";
            }
            leaf RegistrarFreqBand {
              type enumeration {
                enum "802.11 2.4 GHz";
                enum "802.11 5 GHz";
                enum "802.11 60 GHz";
              }
              description
                "{{list}} of frequency bands identified as supported
                 for a registrar role in an AP-autoconfiguration
                 response message as defined in
                 {{bibref|IEEE1905.1a|Table 6-25:
                 SupportedFreqBand TLV}} {{enum}}.";
            }
            leaf FriendlyName {
              type string {
                length "0..128";
              }
              description
                "Friendly Name String received in Higher Layer
                 response message as defined in
                 {{bibref|IEEE1905.1a|Table 6-30: Device
                 Identification Type TLV}}.";
            }
            leaf ManufacturerName {
              type string {
                length "0..128";
              }
              description
                "Manufacturer Name String received in Higher Layer
                 response message as defined in
                 {{bibref|IEEE1905.1a|Table 6-30: Device
                 Identification Type TLV}}.";
            }
            leaf ManufacturerModel {
              type string {
                length "0..128";
              }
              description
                "Manufacturer Model String received in Higher Layer
                 response message as defined in
                 {{bibref|IEEE1905.1a|Table 6-30: Device
                 Identification Type TLV}}.";
            }
            leaf ControlURL {
              type string {
                length "0..1024";
              }
              description
                "Control URL received in Higher Layer response
                 message as defined in defined in
                 {{bibref|IEEE1905.1a|Table 6-31: Control URL
                 Type TLV}}.";
            }

            list IPv4Address {
              key "MACAddress IPv4Address";
              description
                "This object represents represents all IPv4
                 addresses reported for a MAC address (AL or
                 interface) in a Higher Layer response message
                 for the IEEE1905Device as defined in
                 {{bibref|IEEE1905.1a|Table 6-32: IPv4 type
                 TLV}}.";
              leaf MACAddress {
                type types:MACAddress;
                description
                  "MAC Address.";
              }
              leaf IPv4Address {
                type types:IPv4Address;
                description
                  "IPv4 Address.";
              }
              leaf IPv4AddressType {
                type enumeration {
                  enum "Unknown";
                  enum "DHCP";
                  enum "Static";
                  enum "Auto-IP";
                }
                description
                  "The IPv4 Address Type of this
                   {{param|IPv4Address}}.  {{enum}}";
              }
              leaf DHCPServer {
                type types:IPAddress;
                description
                  "Either IPv4 address of DHCPv4 server or IPv6
                   address of DHCPv6 server.";
              }
            }

            list IPv6Address {
              key "MACAddress IPv6Address";
              description
                "This object represents represents all IPv6
                 addresses reported for a MAC address (AL or
                 interface) in a Higher Layer response message
                 for the IEEE1905Device as defined in
                 {{bibref|IEEE1905.1a|Table 6-34: IPv6 type
                 TLV}}.";
              leaf MACAddress {
                type types:MACAddress;
                description
                  "MAC Address.";
              }
              leaf IPv6Address {
                type types:IPv6Address;
                description
                  "IPv6 Address.";
              }
              leaf IPv6AddressType {
                type enumeration {
                  enum "Unknown";
                  enum "LinkLocal";
                  enum "DHCP";
                  enum "Static";
                  enum "SLAAC";
                }
                description
                  "The IPv6 Address Type of this
                   {{param|IPv6Address}}.  {{enum}}";
              }
              leaf IPv6AddressOrigin {
                type types:IPv6Address;
                description
                  "\"::\" or the IPv6 address of the origin of this
                   IPv6 address.";
              }
            }

            list VendorProperties {
              description
                "This object represents vendor specific information
                 received in a message with a Vendor specific TLV
                 (as defined in in {{bibref|IEEE1905.1a|Table
                 6-7: Vendor specific TLV}}).";
              leaf MessageType {
                type yang:hex-string {
                  length "1";
                }
                description
                  "The Message type of a message received from this
                   IEEE1905Device that contained a Vendor
                   specific TLV, as defined in
                   {{bibref|IEEE1905.1a|Table 6-4: Message
                   type}}.";
              }
              leaf OUI {
                type string {
                  length "6";
                  pattern "[0-9A-F]{6}";
                }
                description
                  "This is the value of the Vendor specific OUI
                   defined in {{bibref|IEEE1905.1a|Table 6-7:
                   Vendor specific TLV}}.  {{pattern}}";
              }
              leaf Information {
                type yang:hex-string {
                  length "0..65535";
                }
                description
                  "A hexbinary string used to provide vendor
                   specific information.  This is the value of
                   the Vendor specific information parameter
                   defined in {{bibref|IEEE1905.1a|Table 6-7:
                   Vendor specific TLV}}.";
              }
            }

            list Interface {
              key "InterfaceId";
              description
                "This object represents an instance of an interface
                 for the {{object|##.IEEE1905Device}}.";
              leaf InterfaceId {
                type types:MACAddress;
                description
                  "MAC Address of the interface.  This comes from
                   the Topology response message as defined in
                   {{bibref|IEEE1905.1a|Table 6-10: 1905 device
                   information type TLV}}.";
              }
              leaf MediaType {
                type enumeration {
                  enum "IEEE 802.3u";
                  enum "IEEE 802.3ab";
                  enum "IEEE 802.11b";
                  enum "IEEE 802.11g";
                  enum "IEEE 802.11a";
                  enum "IEEE 802.11n 2.4";
                  enum "IEEE 802.11n 5.0";
                  enum "IEEE 802.11ac";
                  enum "IEEE 802.11ad";
                  enum "IEEE 802.11af";
                  enum "IEEE 1901 Wavelet";
                  enum "IEEE 1901 FFT";
                  enum "MoCAv1.1";
                  enum "Generic PHY";
                }
                description
                  "Media type of this {{object}}.  This comes from
                   the Topology response message as defined in
                   {{bibref|IEEE1905.1a|Table 6-10: 1905 device
                   information type TLV}}.  {{enum}}";
              }
              leaf PowerState {
                type enumeration {
                  enum "On";
                  enum "Power_Save";
                  enum "Off";
                  enum "Unsupported";
                }
                description
                  "The Power State of this {{object}}.
                   \"{{enum|Off}}\" is used for interfaces
                   identified in a Power Off Interface TLV as
                   defined in {{bibref|IEEE1905.1a|Table 6-38}}.
                   \"{{enum|On}}\" is used for all other
                   interfaces.  \"{{enum|Power_Save}}\" and
                   \"{{enum|Unsupported}}\" are not used at this
                   time.  Updated as a result of a received
                   Interface Power Change response with “request
                   completed” or “alternate change made”
                   Interface Power Change status as defined in
                   {{bibref|IEEE1905.1a|Table 6-40: Interface
                   Power Change status TLV}}.  {{enum}}";
              }
              leaf GenericPhyOUI {
                type string {
                  length "6";
                  pattern "[0-9A-F]{6}";
                }
                description
                  "{{param}} of this {{object|#.Interface}}.
                   {{pattern}}";
              }
              leaf GenericPhyVariant {
                type yang:hex-string {
                  length "1";
                }
                description
                  "Variant Index of the Generic Phy networking
                   technology of this {{object|#.Interface}}.
                   This value is from a Generic Phy response
                   message variant index field as defined in
                   {{bibref|IEEE1905.1a|Table 6-29: Generic Phy
                   device information type TLV}}.";
              }
              leaf GenericPhyURL {
                type string {
                  length "0..1024";
                }
                description
                  "URL to Generic Phy XML Description of the Generic
                   Phy networking technology of this
                   {{object|#.Interface}}.  This value is from a
                   Generic Phy response message URL to generic
                   phy field as defined in
                   {{bibref|IEEE1905.1a|Table 6-29: Generic Phy
                   device information type TLV}}.";
              }
              leaf NetworkMembership {
                type types:MACAddress;
                description
                  "MACAddress Field from Media specific information
                   for an 802.11 interface provided in a Topology
                   response message 1905 device information type
                   TLV as defined in {{bibref|IEEE1905.1a|Table
                   6-13: IEEE 802.11 specific information}}.";
              }
              leaf Role {
                type enumeration {
                  enum "AP";
                  enum "non-AP/non-PCP STA";
                  enum "Wi-Fi P2P Client";
                  enum "Wi-Fi P2P Group Owner";
                  enum "802.11adPCP";
                }
                description
                  "Field from Media specific information for an
                   802.11 interface provided in a Topology
                   response message 1905 device information type
                   TLV as defined in {{bibref|IEEE1905.1a|Table
                   6-13: IEEE 802.11 specific information}}.
                   {{enum}}";
              }
              leaf APChannelBand {
                type yang:hex-string {
                  length "1";
                }
                description
                  "Hexadecimal digit.  Field from Media specific
                   information for an 802.11 interface provided
                   in a Topology response message 1905 device
                   information type TLV as defined in
                   {{bibref|IEEE1905.1a|Table 6-13: IEEE 802.11
                   specific information}}";
              }
              leaf FrequencyIndex1 {
                type yang:hex-string {
                  length "1";
                }
                description
                  "Field from Media specific information for an
                   802.11 interface provided in a Topology
                   response message 1905 device information type
                   TLV as defined in {{bibref|IEEE1905.1a|Table
                   6-13: IEEE 802.11 specific information}}";
              }
              leaf FrequencyIndex2 {
                type yang:hex-string {
                  length "1";
                }
                description
                  "Field from Media specific information for an
                   802.11 interface provided in a Topology
                   response message 1905 device information type
                   TLV as defined in {{bibref|IEEE1905.1a|Table
                   6-13: IEEE 802.11 specific information}}";
              }
            }

            list NonIEEE1905Neighbor {
              key "LocalInterface NeighborInterfaceId";
              description
                "This object represents an instance of a
                 Non-IEEE1905 Neighbor for the
                 {{object|##.IEEE1905Device}}.  These fields come
                 from a Topology response message as defined in
                 {{bibref|IEEE1905.1a|Table 6-14: Non-1905
                 neighbor device TLV}}.";
              leaf LocalInterface {
                type string {
                  length "0..256";
                }
                description
                  "{{reference}}";
              }
              leaf NeighborInterfaceId {
                type types:MACAddress;
                description
                  "MAC Address of the interface for the {{object}}.";
              }
            }

            list L2Neighbor {
              key "LocalInterface NeighborInterfaceId";
              description
                "This object represents an instance of an L2
                 Neighbor for the {{object|##.IEEE1905Device}}.
                 These fields come from a Topology response
                 message as defined in {{bibref|IEEE1905.1a|Table
                 6-41: L2 neighbor device TLV}}.";
              leaf LocalInterface {
                type string {
                  length "0..256";
                }
                description
                  "{{reference}}";
              }
              leaf NeighborInterfaceId {
                type types:MACAddress;
                description
                  "MAC Address of the {{object}}.";
              }
              leaf BehindInterfaceIds {
                type types:MACAddress;
                description
                  "{{list}} Behind MAC Addresses of the {{object}}.";
              }
            }

            list IEEE1905Neighbor {
              key "LocalInterface NeighborDeviceId";
              description
                "This object represents an instance of an {{object}}
                 for the {{object|##.IEEE1905Device}}.  These
                 values are from the Topology response message as
                 defined in {{bibref|IEEE1905.1a|Table 6-15: 1905
                 neighbor device TLV}}.";
              leaf LocalInterface {
                type string {
                  length "0..256";
                }
                description
                  "{{reference}}";
              }
              leaf NeighborDeviceId {
                type types:MACAddress;
                description
                  "1905 AL MAC Address of the Neighbor.";
              }

              list Metric {
                key "NeighborMACAddress";
                description
                  "This object represents the metrics included in a
                   Link metric response from the IEEE1905Device
                   where {{param|#.LocalInterface}} is the MAC
                   address of an interface in the receiving 1905
                   AL as defined in {{bibref|IEEE1905.1a|Table
                   6-17: 1905 transmitter link metric TLV}}.";
                leaf NeighborMACAddress {
                  type types:MACAddress;
                  description
                    "The MAC address of an interface in a neighbor
                     1905 device as defined in
                     {{bibref|IEEE1905.1a|Table 6-17: 1905
                     transmitter link metric TLV or Table 6-19:
                     1905 receiver link metric TLV}}.";
                }
                leaf IEEE802dot1Bridge {
                  type boolean;
                  description
                    "Indicates whether or not the 1905 link includes
                     one or more IEEE 802.1 bridges.  If
                     {{false}}, the 1905 link does not include an
                     IEEE 802.1 bridge.  If {{true}}, the 1905
                     link does include one or more IEEE 802.1
                     bridges.";
                }
                leaf PacketErrors {
                  type types:StatsCounter32;
                  description
                    "Estimated number of lost {{units}} on the
                     transmit side of the link
                     {{bibref|IEEE1905.1a|Table 6-18: 1905
                     transmitter link metrics}} during a
                     measurement period.";
                }
                leaf PacketErrorsReceived {
                  type types:StatsCounter32;
                  description
                    "Estimated number of lost {{units}} on the
                     receive side of the link
                     {{bibref|IEEE1905.1a|Table 6-20: 1905
                     receiver link metrics}} during a measurement
                     period.";
                }
                leaf TransmittedPackets {
                  type types:StatsCounter32;
                  description
                    "Estimated number of {{units}} sent to the
                     Neighbor on this link, in the same
                     measurement period used to estimate
                     {{param|PacketErrors}}.";
                }
                leaf PacketsReceived {
                  type types:StatsCounter32;
                  description
                    "Estimated number of {{units}} received from
                     this Neighbor {{bibref|IEEE1905.1a|Table
                     6-20: 1905 receiver link metrics}} on this
                     link, in the same measurement period used to
                     estimate {{param|PacketErrors}}.";
                }
                leaf MACThroughputCapacity {
                  type uint32;
                  description
                    "The maximum MAC throughput in {{units}} between
                     this Interface and the Neighbor on this link
                     that is estimated at this Interface.";
                }
                leaf LinkAvailability {
                  type uint32 {
                    range "0..100";
                  }
                  description
                    "The estimated average {{units}} of time that
                     this link is idle.";
                }
                leaf PHYRate {
                  type uint32;
                  description
                    "The Physical Layer (PHY) rate in {{units}}
                     between this Interface and the Neighbor on
                     this link that is estimated at this
                     Interface.";
                }
                leaf RSSI {
                  type uint32 {
                    range "0..255";
                  }
                  description
                    "The estimated Received Signal Strength
                     Indicator (RSSI) ratio in {{units}} between
                     this Interface and the Neighbor on this link
                     that is estimated at the receive side of
                     this Interface.  Note: This parameter is
                     valid only for IEEE 802.11 Neighbors.";
                }
              }
            }

            list BridgingTuple {
              description
                "This object represents an instance of an {{object}}
                 for the {{object|##.IEEE1905Device}}.  These
                 values come from the 1905 Device’s Topology
                 response message as defined in
                 {{bibref|IEEE1905.1a|Table 6-11: Device bridging
                 capability TLV}}.";
              leaf InterfaceList {
                type string {
                  length "0..256";
                }
                description
                  "{{list}} {{reference}}";
              }
            }
          }
        }

        container Security {
          description
            "This object represents the Security configuration for
             the 1905 device as defined in
             {{bibref|IEEE1905.1a|Section 9.2 Security Setup
             Methods}}.";
          leaf SetupMethod {
            type enumeration {
              enum "UCPK";
              enum "PBC";
              enum "NFCNK";
            }
            description
              "{{list}} Supported security setup method(s) for the
               network.  {{enum}}";
          }
          leaf Password {
            type string;
            description
              "1905 network passphrase for generating security keys.";
          }
        }

        container NetworkingRegistrar {
          config false;
          description
            "This object represents the detected Network Registrars
             detection function for the IEEE 1905 network.  They
             are determined by received AP-autoconfiguration
             response messages with Registrar role, with
             supported band as defined in
             {{bibref|IEEE1905.1a|Table 6-25: SupportedFreqBand
             TLV}}";
          leaf Registrar2dot4 {
            type types:MACAddress;
            description
              "{{list}} 1905 AL MAC addresses as determined by
               source MAC address in received
               AP-autoconfiguration response messages with
               supported frequency band of 802.11 2.4 GHz.";
          }
          leaf Registrar5 {
            type types:MACAddress;
            description
              "{{list}} 1905 AL MAC addresses as determined by
               source MAC address in received
               AP-autoconfiguration response messages with
               supported frequency band of 802.11 5 GHz.";
          }
          leaf Registrar60 {
            type types:MACAddress;
            description
              "{{list}} 1905 AL MAC addresses as determined by
               source MAC address in received
               AP-autoconfiguration response messages with
               supported frequency band of 802.11 60 GHz.";
          }
        }
      }
    }

    container MQTT {
      description
        "MQTT Base object describing all MQTT related parameters and
         objects {{bibref|MQTT31}},";

      container Capabilities {
        config false;
        description
          "Indicates the MQTT capabilities of the device";
        leaf ProtocolVersionsSupported {
          type enumeration {
            enum "3.1";
            enum "3.1.1";
          }
          description
            "Indicates the supported protocol versions {{enum}}";
        }
        leaf TransportProtocolSupported {
          type enumeration {
            enum "TCP/IP";
            enum "TLS";
            enum "WebSocket";
          }
          description
            "Indicates the supported transport protocols.  {{enum}}";
        }
        leaf MaxNumberOfClientSubscriptions {
          type uint32;
          description
            "Indicates the maximum number of subscriptions per
             client, which can be stored in the
             {{object|#.Client.{i}.Subscription.}} table.  A
             value of 0 means no limit.";
        }
        leaf MaxNumberOfBrokerBridges {
          type uint32;
          description
            "Indicates the maximum number of bridges, which can be
             configured in the {{object|#.Broker.{i}.Bridge.}}
             table.  A value of 0 means no limit.";
        }
        leaf MaxNumberOfBrokerBridgeSubscriptions {
          type uint32;
          description
            "Indicates the maximum number of subscriptions, which
             can be stored per bridge instance in the
             {{object|#.Broker.{i}.Bridge.{i}.Subscription.}}
             table.  A value of 0 means no limit.";
        }
      }

      list Client {
        key "Alias";
        description
          "MQTT Client table.  Contains a list of configured MQTT
           clients.";
        leaf Name {
          type string {
            length "0..64";
          }
          description
            "The textual name of the MQTT client.";
        }
        leaf Enable {
          type boolean;
          description
            "Allows to enable or disable the MQTT client.";
        }
        leaf Status {
          type enumeration {
            enum "Disabled";
            enum "Connecting";
            enum "Connected";
            enum "Error_Misconfigured";
            enum "Error_Broker_Unreachable";
            enum "Error";
          }
          config false;
          description
            "Indicates the status of this MQTT client.  {{enum}}
          
             The {{enum|Error_Misconfigured}} value indicates
             that a necessary configuration value is undefined or
             invalid (e.g.  The client can not use the defined
             port, because it is blocked)
          
             The {{enum|Error_Broker_Unreachable}} value
             indicates that the connection to the broker could
             not be established.
          
             The {{enum|Error}} value MAY be used by the CPE to
             indicate a locally defined error condition.";
        }
        leaf BrokerAddress {
          type string {
            length "0..256";
          }
          description
            "Host name or IP address of the MQTT Broker.";
        }
        leaf BrokerPort {
          type uint32 {
            range "1..65535";
          }
          default "1883";
          description
            "Port number of the MQTT broker.";
        }
        leaf ClientID {
          type string {
            length "1..23";
          }
          description
            "The client identifier used in the CONNECT message.
             This parameter may not be {{empty}}, the client has
             to provide a default value for the parameter, which
             may be changed by the ACS.
          
             A change of this parameter is only communicated to
             the broker with the next MQTT CONNECT message.  If
             the change shall be applied immediately, the
             {{param|ForceReconnect}} has to be set, too.";
        }
        leaf Username {
          type string {
            length "0..256";
          }
          description
            "Username used to authenticate the CPE when making a
             connection to the MQTT broker.  According to
             {{bibref|MQTT31}} the username should be 12
             characters or fewer, but this is not required.
          
             If this parameter is {{empty}} no authentication
             parameters are send in the MQTT CONNECT message.";
        }
        leaf Password {
          type string {
            length "0..256";
          }
          description
            "Password used to authenticate the CPE when making a
             connection to the MQTT broker.
          
             This password is only send in the MQTT CONNECT
             message if {{param|Username}} is not {{empty}}";
        }
        leaf TransportProtocol {
          type string;
          default "TCP/IP";
          description
            "Indicates the transport protocol to be used for the
             broker connection.";
        }
        leaf CleanSession {
          type boolean;
          default "true";
          description
            "The value of the MQTT clean session flag in the MQTT
             Connect message.  If this flag is set to {{true}}
             (default), the broker will delete all subscription
             information after a Disconnect.
          
             A change of this parameter is only effective after
             the next MQTT CONNECT message to the broker.  If the
             change should be applied immediately, the
             {{param|ForceReconnect}} has to be set, too.";
        }
        leaf MessageRetryTime {
          type uint32 {
            range "1..max";
          }
          default "5";
          description
            "Message retry time in {{units}} defines the wait time
             before a MQTT message that expects a response (QoS >
             0 PUBLISH, PUBREL, SUBSCRIBE, UNSUBSCRIBE) is
             resend, because the response is not received.
          
             The sender should set the DUP flag on the resend
             message.";
        }
        leaf ConnectRetryTime {
          type uint32 {
            range "1..max";
          }
          default "30";
          description
            "Connect retry time in {{units}} defines the wait time
             before a failed broker connection is retired.
          
             A failure can either be on the connection level (the
             TCP/IP or TLS can not be established) or on the
             Protocol level, the client does not receive a MQTT
             CONNACK message on a MQTT CONNECT message send.";
        }
        leaf KeepAliveTime {
          type uint32 {
            range "min..65535";
          }
          default "60";
          description
            "Keep Alive Time in {{units}} defines the max after
             which the client has to send a message to the
             broker.  If no regular messages can be send a MQTT
             PINGREQ is send.
          
             A value of zero (0) means no keep alive message are
             send and the client is not disconnected by the
             server.
          
             A change of this parameter is only effective after
             the next MQTT CONNECT message to the broker.  If the
             change should be applied immediately, the
             {{param|ForceReconnect}} has to be set, too.";
        }
        leaf ProtocolVersion {
          type string;
          description
            "Specifies the MQTT protocol version used in the
             communication with the broker.";
        }
        leaf ForceReconnect {
          type boolean;
          description
            "Disconnects the client from the broker and reconnects
             it again (toogle connection).  It is only effective
             if the client is currently connected to the broker
             (Parameter {{param|Status|}} is
             {{enum|Connected|Status}}).
          
             If the client is in a different state, the parameter
             has no effect.
          
             This parameter may be used to apply changes in the
             MQTT connection settings.";
        }
        leaf WillEnable {
          type boolean;
          description
            "Enables or disables the will handling.  Changing this
             parameter while the client is connected will cause
             the client to disconnect and reconnect.
          
             A change of this parameter is only communicated to
             the broker with the next MQTT CONNECT message.  If
             the change should be applied immediately, the
             {{param|ForceReconnect}} has to be set, too.";
        }
        leaf WillTopic {
          type string;
          description
            "The Topic send in the Will Message.  This parameter is
             only used if {{param|WillEnable}} is set to
             {{true}}.
          
             A change of this parameter is only communicated to
             the broker with the next MQTT CONNECT message.  If
             the change should be applied immediately, the
             {{param|ForceReconnect}} has to be set, too.";
        }
        leaf WillValue {
          type string;
          description
            "The value send in the Will Message.  This parameter is
             only used if {{param|WillEnable}} is set to
             {{true}}.
          
             A change of this parameter is only communicated to
             the broker with the next MQTT CONNECT message.  If
             the change should be applied immediately, the
             {{param|ForceReconnect}} has to be set, too.";
        }
        leaf WillQoS {
          type uint32 {
            range "0..2";
          }
          description
            "The MQTT QoS level assigned with the will message.
             This parameter is only used if {{param|WillEnable}}
             is set to {{true}}.
          
             A change of this parameter is only communicated to
             the broker with the next MQTT CONNECT message.  If
             the change should be applied immediately, the
             {{param|ForceReconnect}} has to be set, too.";
        }
        leaf WillRetain {
          type boolean;
          description
            "Indicate to the broker that the Will shall be retained
             over a Disconnect.  This parameter is only used if
             {{param|WillEnable}} is set to {{true}}.
          
             A change of this parameter is only communicated to
             the broker with the next MQTT CONNECT message.  If
             the change should be applied immediately, the
             {{param|ForceReconnect}} has to be set, too.";
        }

        list Subscription {
          key "Alias";
          description
            "List of MQTT subscriptions handled by the client.";
          leaf Topic {
            type string {
              length "0..65535";
            }
            description
              "Name of the Subscribed Topic";
          }
          leaf QoS {
            type uint32 {
              range "0..2";
            }
            description
              "The MQTT QoS level assigned with the subscription";
          }
          leaf Enable {
            type boolean;
            description
              "Setting Enable to {{true}} means the topic is
               subscribed at the broker with a MQTT SUBSCRIBE
               message, setting it to {{false}} will unsubscribe
               the topic from the broker with a MQTT UNSUBSCRIBE
               message.";
          }
        }

        container Stats {
          config false;
          description
            "Contains the MQTT client statistics and usage
             information";
          leaf BrokerConnectionEstablished {
            type yang:date-and-time;
            description
              "Time when the broker connection was established.";
          }
          leaf LastPublishMessageSent {
            type yang:date-and-time;
            description
              "Time when the last publish message was send to the
               broker.";
          }
          leaf LastPublishMessageReceived {
            type yang:date-and-time;
            description
              "Time when the last publish message was received from
               the broker.";
          }
          leaf PublishSent {
            type types:StatsCounter64;
            description
              "Number of publish messages send to the broker.";
          }
          leaf PublishReceived {
            type types:StatsCounter64;
            description
              "Number of publish messages received from to the
               broker.";
          }
          leaf SubscribeSent {
            type types:StatsCounter64;
            description
              "Number of subscribe messages send to the broker.";
          }
          leaf UnSubscribeSent {
            type types:StatsCounter64;
            description
              "Number of unsubscribe messages send to the broker.";
          }
          leaf MQTTMessagesSent {
            type types:StatsCounter64;
            description
              "Total number of MQTT messages send to the broker.";
          }
          leaf MQTTMessagesReceived {
            type types:StatsCounter64;
            description
              "Total number of MQTT messages received from the
               broker.";
          }
          leaf ConnectionErrors {
            type types:StatsCounter64;
            description
              "Number of connection errors.";
          }
          leaf PublishErrors {
            type types:StatsCounter64;
            description
              "Number of errors, which prevented sending publish
               messages";
          }
        }
      }

      list Broker {
        key "Alias";
        description
          "MQTT Broker related data";
        leaf Name {
          type string {
            length "0..64";
          }
          description
            "The textual name of the Broker.";
        }
        leaf Enable {
          type boolean;
          description
            "Allows to enable or disable the MQTT broker.";
        }
        leaf Status {
          type enumeration {
            enum "Disabled";
            enum "Enabled";
            enum "Error_Misconfigured";
            enum "Error";
          }
          config false;
          description
            "Indicates the status of the MQTT broker.  {{enum}}
          
             The \"{{enum|Error_Misconfigured}}\" value indicates
             that a necessary configuration value is undefined or
             invalid.
          
             The \"{{enum|Error}}\" value MAY be used by the CPE
             to indicate a locally defined error condition.";
        }
        leaf Port {
          type uint32 {
            range "1..65535";
          }
          default "1883";
          description
            "Port used by the MQTT Broker.";
        }
        leaf Interface {
          type string {
            length "0..256";
          }
          description
            "{{reference|the IP-layer interface used by the broker}}
          
             The value of this parameter MUST be either a valid
             interface or {{empty}}.  An attempt to set this
             parameter to a different value MUST be rejected as
             an invalid parameter value.
          
             If {{empty}} is specified, the CPE MUST bind the
             MQTT broker to all available interfaces.";
        }
        leaf Username {
          type string {
            length "0..256";
          }
          description
            "Username used to authenticate the clients, which
             connect to the broker.
          
             If this parameter is {{empty}} no authentication is
             used.";
        }
        leaf Password {
          type string {
            length "0..256";
          }
          description
            "Password used used to authenticate the clients, which
             connect to the broker.
          
             This password is only used if {{param|Username}} is
             not {{empty}}";
        }

        list Bridge {
          key "Name";
          description
            "Configures the bridges, which may be used to
             communicate with other brokers";
          leaf Name {
            type string {
              length "0..64";
            }
            description
              "A name of the bridge used for identification.";
          }
          leaf Enable {
            type boolean;
            description
              "Allows to enable or disable the MQTT Bridge.";
          }
          leaf Status {
            type enumeration {
              enum "Disabled";
              enum "Connecting";
              enum "Connected";
              enum "Error_Misconfigured";
              enum "Error_Broker_Unreachable";
              enum "Error";
            }
            config false;
            description
              "Indicates the status of this MQTT Bridge.  {{enum}}
            
               The {{enum|Disabled}} values indicates that the
               bridge is not in service; parameter
               {{param|Enable}} is set to {{false}}.
            
               The {{enum|Connecting}} values indicates that the
               bridge is currently established.
            
               The {{enum|Connected}} values indicates that the
               bridge is currently active.
            
               The {{enum|Error_Misconfigured}} value indicates
               that a necessary configuration value is undefined
               or invalid (e.g.  No active Server entry, the
               broker can not use the defined bridge port,
               because it is blocked)
            
               The {{enum|Error_Broker_Unreachable}} value
               indicates that the bridge connection to the remote
               broker could not be established.
            
               The {{enum|Error}} value MAY be used to indicate a
               locally defined error condition.";
          }
          leaf ClientID {
            type string {
              length "1..23";
            }
            description
              "The client identifier used in the bridge connection.";
          }
          leaf Username {
            type string {
              length "0..256";
            }
            description
              "Username used to authenticate the broker when making
               a connection over the bridge.
            
               If this parameter is {{empty}} no authentication
               is used.";
          }
          leaf Password {
            type string {
              length "0..256";
            }
            description
              "Password used used to authenticate the broker when
               making a connection over the bridge.
            
               This password is only send if {{param|Username}}
               is not {{empty}}";
          }
          leaf CleanSession {
            type boolean;
            default "true";
            description
              "The value of the MQTT clean session flag in the
               bridge connection.  If this flag is set to
               {{true}} (default), the broker will delete all
               subscription information after a Disconnect.";
          }
          leaf TransportProtocol {
            type string;
            default "TCP/IP";
            description
              "Indicates the transport protocol to be used for the
               broker connection.";
          }
          leaf ProtocolVersion {
            type string;
            description
              "Specifies the MQTT protocol version used in the
               bridge connection.";
          }
          leaf ServerSelectionAlgorithm {
            type enumeration {
              enum "FirstMatch";
              enum "RoundRobin";
              enum "Random";
            }
            description
              "The algorithm used to select a server entry from the
               {{object|#.Bridge.{i}.Server.{i}.}} table";
          }
          leaf ServerConnection {
            type string;
            config false;
            description
              "{{reference|the {{object|#.Bridge.{i}.Server.}}
               instance that is used for this {{object}}, while
               the {{param|Status}} is {{enum|Connecting|Status}}
               or {{enum|Connected|Status}}.  If the bridge is
               not connected the value must be an empty string.}}";
          }

          list Server {
            key "Address Port";
            description
              "The {{object}} represents a MQTT Bridge server to be
               used for a {{object|##.Bridge}}.  A remote MQTT
               broker, which is connected by a bridge may be
               reachable over several host addresses each
               represented by an own {{object}} table entry.  For
               an active bridge at least one enabled entry has to
               exist.
            
               If a bridge gets enabled by setting the parameter
               {{param|##.Bridge.{i}.Enable}} to {{true}}, which
               either has an empty {{object}} table or the
               {{object}} table only contains instances whose
               {{param|Enable}} is set to {{false}}, the
               {{param|##.Bridge.{i}.Status}} has to set
               {{enum|Error_Misconfigured|##.Bridge.{i}.Status}}.
            
               Any attempt to delete an instance with
               DeleteObject RPC, which is currently in use
               ({{param|##.Bridge.{i}.ServerConnection}} referes
               to the instance to be deleted), has to be rejected
               with a 9001 error code.";
            leaf Enable {
              type boolean;
              default "false";
              description
                "Enables or disables this {{object}}.
              
                 This parameter is based on ''ifAdminStatus''
                 from {{bibref|RFC2863}}.";
            }
            leaf Priority {
              type uint32 {
                range "0..65535";
              }
              description
                "The priority of this {{object}} that is used by the
                 {{object|##.Bridge}} when determining the
                 {{object}} to connect to.  The
                 {{object|##.Bridge}} MUST contact the {{object}}
                 with the lowest-numbered priority that the
                 {{object|##.Bridge}} can reach as defined in
                 {{bibref|RFC2782}}.  The selection of
                 {{object}}s with the same {{param}} value
                 utilizes the {{param|Weight}} parameter to
                 determine which {{object}} is selected by the
                 {{object|##.Bridge}}.";
            }
            leaf Weight {
              type int64 {
                range "-1..65535";
              }
              description
                "This parameter specifies a relative weight for
                 entries with the same {{param|Priority}}.  The
                 mechanism is defined in {{bibref|RFC2782}}.  A
                 value of -1 indicates that the implementation of
                 this parameter is specific to the Vendor.";
            }
            leaf Address {
              type string {
                length "0..256";
              }
              description
                "Fully Qualified Domain Name (FQDN) or IP address of
                 the MQTT broker server this {{object|##.Bridge}}
                 connects to.
              
                 If the value of this Parameter is a FQDN that
                 resolves to multiple addresses then each address
                 SHOULD be attempted (in an
                 implementation-specific order) until a
                 connection can be made or all addresses are
                 exhausted, in which case the next {{object}}
                 instance (based on {{param|Priority}} and
                 {{param|Weight}}) SHOULD be used.";
            }
            leaf Port {
              type uint32 {
                range "1..65535";
              }
              default "1883";
              description
                "Port number of the MQTT broker server this
                 {{object|##.Bridge}} connects to.";
            }
          }

          list Subscription {
            key "Alias";
            description
              "List of MQTT subscriptions handled over the bridge";
            leaf Topic {
              type string {
                length "0..65535";
              }
              description
                "Name of the Subscribed Topic";
            }
            leaf Direction {
              type enumeration {
                enum "out";
                enum "in";
                enum "both";
              }
              description
                "The direction of the subscription.  {{enum}}.";
            }
            leaf Enable {
              type boolean;
              description
                "Setting Enable to {{true}} means the topic is
                 subscribed over the bridge.";
            }
            leaf QoS {
              type uint32 {
                range "0..2";
              }
              description
                "The MQTT QoS level assigned with the subscription";
            }
            leaf LocalPrefix {
              type string;
              description
                "For incoming topics from the bridge, the
                 LocalPrefix will added in front.
              
                 For outgoing topics, the broker will prepend the
                 topic with the local prefix for selection.  When
                 an outgoing message is processed, the
                 LocalPrefix will be removed from the topic.";
            }
            leaf RemotePrefix {
              type string;
              description
                "For incoming topics from the bridge, the broker
                 will prepend the topic with the remote prefix
                 and subscribe to the resulting topic on the
                 remote broker.  When a matching incoming message
                 is received, the remote prefix will be removed
                 from the topic.
              
                 For outgoing topics over the bridge, the
                 RemotePrefix will be added in front.";
            }
          }
        }

        container Stats {
          config false;
          leaf TotalNumberOfClients {
            type types:StatsCounter64;
            description
              "Total number of clients registered with the broker.";
          }
          leaf NumberOfActiveClients {
            type types:StatsCounter64;
            description
              "Number of clients, which have a connection with the
               broker established";
          }
          leaf NumberOfInActiveClients {
            type types:StatsCounter64;
            description
              "Number of clients, which have no connection with the
               broker established.";
          }
          leaf PublishSent {
            type types:StatsCounter64;
            description
              "Number of publish messages send to the broker.";
          }
          leaf PublishReceived {
            type types:StatsCounter64;
            description
              "Number of publish messages received from to the
               broker.";
          }
          leaf SubscribeSent {
            type types:StatsCounter64;
            description
              "Number of subscribe messages send to the broker.";
          }
          leaf UnSubscribeSent {
            type types:StatsCounter64;
            description
              "Number of unsubscribe messages send to the broker.";
          }
          leaf MQTTMessagesSent {
            type types:StatsCounter64;
            description
              "Total number of MQTT messages send to the broker.";
          }
          leaf MQTTMessagesReceived {
            type types:StatsCounter64;
            description
              "Total number of MQTT messages received from the
               broker.";
          }
          leaf ConnectionErrors {
            type types:StatsCounter64;
            description
              "Number of connection errors.";
          }
          leaf PublishErrors {
            type types:StatsCounter64;
            description
              "Number of errors, which prevented sending publish
               messages";
          }
        }
      }
    }

    container DynamicDNS {
      description
        "Properties for Dynamic DNS.";
      leaf SupportedServices {
        type string;
        config false;
        description
          "List of Dynamic DNS service names that are supported by
           the CPE.";
      }

      list Client {
        key "Server Username";
        description
          "Client properties for Dynamic DNS.
        
           A Dynamic DNS Client is responsible for verifying IP
           address changes and update information from a
           subscribed account on a Dynamic DNS Server.";
        leaf Enable {
          type boolean;
          description
            "Enables or disables this Dynamic DNS Client.";
        }
        leaf Status {
          type enumeration {
            enum "Connecting";
            enum "Authenticating";
            enum "Updated";
            enum "Error_Misconfigured";
            enum "Error";
            enum "Disabled";
          }
          config false;
          description
            "Status of this Dynamic DNS Client.";
        }
        leaf LastError {
          type enumeration {
            enum "NO_ERROR";
            enum "MISCONFIGURATION_ERROR";
            enum "DNS_ERROR";
            enum "CONNECTION_ERROR";
            enum "AUTHENTICATION_ERROR";
            enum "TIMEOUT_ERROR";
            enum "PROTOCOL_ERROR";
          }
          config false;
          description
            "The last error this Dynamic DNS Client has encountered.
          
             The parameter MAY instead indicate a vendor-specific
             cause, which MUST use the format defined in
             {{bibref|TR-106}}.";
        }
        leaf Interface {
          type string {
            length "0..256";
          }
          description
            "The IP Interface associated with this Dynamic DNS
             Client.
          
             {{reference}}";
        }
        leaf Server {
          type string {
            length "0..256";
          }
          description
            "The DynamicDNS server associated with this Dynamic DNS
             Client.
          
             {{reference}}";
        }
        leaf Username {
          type string {
            length "0..256";
          }
          description
            "Username used by this Dynamic DNS Client to
             authenticate with the Server.";
        }
        leaf Password {
          type string {
            length "0..256";
          }
          description
            "Password used by this Dynamic DNS Client to
             authenticate with the Server.";
        }

        list Hostname {
          key "Name";
          description
            "Each table entry represents a fully qualified domain
             name updated by this Dynamic DNS Client.";
          leaf Enable {
            type boolean;
            description
              "Enables or disables this Hostname.";
          }
          leaf Status {
            type enumeration {
              enum "Registered";
              enum "Update_needed";
              enum "Updating";
              enum "Error";
              enum "Disabled";
            }
            config false;
            description
              "Status of this Hostname.";
          }
          leaf Name {
            type string {
              length "0..256";
            }
            description
              "Fully qualified domain name that has to be updated
               with the IP address.
            
               If the name is set to another value, the Client
               MUST immediately send an update request to the
               Server.";
          }
          leaf LastUpdate {
            type yang:date-and-time;
            config false;
            description
              "The date time of the last successful update of this
               name to the Dynamic DNS Server.";
          }
        }
      }

      list Server {
        key "Name";
        description
          "Table of Dynamic DNS servers available for this CPE.";
        leaf Enable {
          type string {
            length "0..64";
          }
          description
            "Enables or disables Dynamic DNS Server.";
        }
        leaf Name {
          type string {
            length "0..64";
          }
          description
            "The textual name of the Dynamic DNS Server.";
        }
        leaf ServiceName {
          type string {
            length "0..256";
          }
          description
            "Dynamic DNS service used to contact this server.
          
             {{reference}}";
        }
        leaf ServerAddress {
          type string {
            length "0..256";
          }
          description
            "Host name or IP address of the Dynamic DNS server.";
        }
        leaf ServerPort {
          type uint32 {
            range "0..65535";
          }
          description
            "Port number of the Dynamic DNS server.";
        }
        leaf SupportedProtocols {
          type enumeration {
            enum "HTTP";
            enum "HTTPS";
          }
          config false;
          description
            "{{list}} Indicates the protocols that are supported by
             the CPE for sending requests to the Dynamic DNS
             server.";
        }
        leaf Protocol {
          type string;
          description
            "Indicates the protocol used to send requests to the
             Dynamic DNS server.";
        }
        leaf CheckInterval {
          type uint32;
          description
            "Interval (in {{units}}) between two checks for IP
             change.
          
             A value of zero indicates that the CPE knows when IP
             changes and doesn’t need to check it periodically.";
        }
        leaf RetryInterval {
          type uint32;
          description
            "Interval (in {{units}}) to retry after a failed
             request.";
        }
        leaf MaxRetries {
          type int32;
          description
            "Maximum number of retries after a failed request.";
        }
      }
    }
  }
}
